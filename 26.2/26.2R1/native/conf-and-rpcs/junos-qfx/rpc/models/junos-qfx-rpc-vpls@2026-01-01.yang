/*
 * Copyright (c) 2026 Juniper Networks, Inc.
 * All rights reserved.
 */
 module junos-qfx-rpc-vpls {
   namespace "http://yang.juniper.net/junos-qfx/rpc/vpls";

   prefix vpls;

   import junos-common-types {
     prefix jt;
     revision-date 2026-01-01;
   }

   organization "Juniper Networks, Inc.";

   contact "yang-support@juniper.net";

   description "Junos RPC YANG module for vpls command(s)";

   revision 2026-01-01 {
     description "Junos: 26.2R1.7";
   }

   rpc get-vpls-connection-information {
     description "Show VPLS connections information";
     input {
       choice daemon-select {
         case logical-system {
           leaf logical-system {
             description "Name of logical system, or 'all'";
             type string {
             }
           }
         }
       }
       leaf instance {
         description "Name of VPLS instance";
         default "all";
         type string;
       }
       leaf local-site {
         description "Name or ID of VPLS local site";
         default "all";
         type string;
       }
       leaf remote-site {
         description "ID of VPLS remote site";
         default "all";
         type string;
       }
       leaf state {
         default "up-down";
         type enumeration {
           enum "down" {
             description "Display nonoperational connections";
           }
           enum "up" {
             description "Display operational connections";
           }
           enum "up-down" {
             description "Display both non- and operational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and circuit status (default)";
           }
           enum "summary" {
             description "Display summary output";
           }
         }
       }
     }
     output {
       choice output-tags {
         case actual-tag {
           container vpls-connection-information {
             uses vpls-connection-information-block;
           }
         }
         case multichassis-tag {
           container multi-routing-engine-results {
             list multi-routing-engine-item {
               leaf re-name {
                 type string;
               }
               choice output-tags {
                 case actual-tag {
                   container vpls-connection-information {
                     uses vpls-connection-information-block;
                   }
                 }
               }
             }
           }
         }
       }
     }
   }
   rpc get-vpls-statistics-information {
     description "Show VPLS statistics information";
     input {
       choice daemon-select {
         case logical-system {
           leaf logical-system {
             description "Name of logical system, or 'all'";
             type string {
             }
           }
         }
       }
       leaf instance {
         description "Name of VPLS instance";
         default "all";
         type string;
       }
     }
     output {
       choice output-tags {
         case actual-tag {
           container vpls-statistics-information {
             uses vpls-statistics-information-block;
           }
         }
         case multichassis-tag {
           container multi-routing-engine-results {
             list multi-routing-engine-item {
               leaf re-name {
                 type string;
               }
               choice output-tags {
                 case actual-tag {
                   container vpls-statistics-information {
                     uses vpls-statistics-information-block;
                   }
                 }
               }
             }
           }
         }
       }
     }
   }
   rpc get-vpls-mac-table {
     description "Show media access control table";
     input {
       leaf instance {
         description "Display information for a specified vpls";
         default "all";
         type string;
       }
       leaf logical-system {
         description "Name of logical system, or 'all'";
         default "all";
         type string {
         }
       }
       leaf vlan-id {
         description "Display MAC address learned on a specified VLAN";
         type string;
       }
       leaf isid {
         description "Display Information for specified ISID or all ISID(s)";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "sync-check" {
             description "Sync check";
           }
           enum "summary" {
             description "Display summary output";
           }
         }
       }
     }
     output {
       choice output-tags {
         case actual-tag {
           container l2ald-rtb-macdb {
             uses l2ald-rtb-macdb-block;
           }
         }
         case multichassis-tag {
           container multi-routing-engine-results {
             list multi-routing-engine-item {
               leaf re-name {
                 type string;
               }
               choice output-tags {
                 case actual-tag {
                   container l2ald-rtb-macdb {
                     uses l2ald-rtb-macdb-block;
                   }
                 }
               }
             }
           }
         }
       }
     }
   }
   rpc get-vpls-interface-mac-table {
     description "Display MAC table for a specified interface";
     input {
       choice interface-choice {
         case interface-name {
           leaf interface-name {
             description "Name of interface for which to display table";
             type string;
           }
         }
         case all {
           leaf all {
             description "Display MAC table for all the interfaces";
             type empty;
           }
         }
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "sync-check" {
             description "Sync check";
           }
           enum "summary" {
             description "Display summary output";
           }
         }
       }
     }
     output {
       choice output-tags {
         case actual-tag {
           container l2ald-interface-macdb {
             uses l2ald-interface-macdb-block;
           }
         }
         case multichassis-tag {
           container multi-routing-engine-results {
             list multi-routing-engine-item {
               leaf re-name {
                 type string;
               }
               choice output-tags {
                 case actual-tag {
                   container l2ald-interface-macdb {
                     uses l2ald-interface-macdb-block;
                   }
                 }
               }
             }
           }
         }
       }
     }
   }
   rpc get-vpls-flood-information {
     description "Show VPLS flooding information";
     input {
       leaf logical-system {
         description "Name of logical system, or 'all'";
         default "all";
         type string {
         }
       }
       leaf instance {
         description "Display information for a specified vpls";
         default "all";
         type string;
       }
       leaf verbosity {
         default "detail";
         type enumeration {
           enum "detail" {
             description "Display detailed output";
           }
           enum "brief" {
             description "Display brief output";
           }
           enum "extensive" {
             description "Display extensive output";
           }
         }
       }
     }
     output {
       choice output-tags {
         case actual-tag {
           container l2ald-vpls-flood-instance {
             uses l2ald-vpls-flood-instance-block;
           }
         }
         case multichassis-tag {
           container multi-routing-engine-results {
             list multi-routing-engine-item {
               leaf re-name {
                 type string;
               }
               choice output-tags {
                 case actual-tag {
                   container l2ald-vpls-flood-instance {
                     uses l2ald-vpls-flood-instance-block;
                   }
                 }
               }
             }
           }
         }
       }
     }
   }
   rpc get-vpls-ce-flood-route-information {
     description "Show customer edge flood route";
     input {
       leaf interface {
         description "Interface for which to show CE flood route";
         type union {
           type jt:interface-unit;
           type string {
             pattern "<.*>|$.*";
           }
         }
         mandatory true;
       }
     }
     output {
       choice output-tags {
         case actual-tag {
           container l2ald-vpls-flood-route-information {
             uses l2ald-vpls-flood-route-information-block;
           }
         }
         case multichassis-tag {
           container multi-routing-engine-results {
             list multi-routing-engine-item {
               leaf re-name {
                 type string;
               }
               choice output-tags {
                 case actual-tag {
                   container l2ald-vpls-flood-route-information {
                     uses l2ald-vpls-flood-route-information-block;
                   }
                 }
               }
             }
           }
         }
       }
     }
   }
   rpc get-vpls-all-ce-flood-route-information {
     description "Show route for flooding traffic to all CE routers";
     input {
       leaf logical-system {
         description "Name of logical system";
         type string {
         }
       }
       leaf instance {
         description "Display information for a specified vpls";
         type string;
         mandatory true;
       }
     }
     output {
       choice output-tags {
         case actual-tag {
           container l2ald-vpls-flood-route-information {
             uses l2ald-vpls-flood-route-information-block;
           }
         }
         case multichassis-tag {
           container multi-routing-engine-results {
             list multi-routing-engine-item {
               leaf re-name {
                 type string;
               }
               choice output-tags {
                 case actual-tag {
                   container l2ald-vpls-flood-route-information {
                     uses l2ald-vpls-flood-route-information-block;
                   }
                 }
               }
             }
           }
         }
       }
     }
   }
   rpc get-vpls-event-queue-information {
     description "Show queue of pending VPLS flood events";
     output {
       choice output-tags {
         case actual-tag {
           container l2ald-vpls-flood-event-queue {
             uses l2ald-vpls-flood-event-queue-block;
           }
         }
         case multichassis-tag {
           container multi-routing-engine-results {
             list multi-routing-engine-item {
               leaf re-name {
                 type string;
               }
               choice output-tags {
                 case actual-tag {
                   container l2ald-vpls-flood-event-queue {
                     uses l2ald-vpls-flood-event-queue-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping vpls-connection-information-block {
     list instance {
       key "instance-name";
       description
         "Routing protocol instance";
       leaf instance-name {
         type string;
       }
       leaf instance-display-error {
         type string;
       }
       leaf edge-protection {
         type string;
       }
       leaf edge-protector {
         type string;
       }
       list reference-site {
         key "local-site-id vpls-id l2vpn-id";
         leaf automatic-site-name {
           type string;
           description
             "VPLS automatic site name";
         }
         leaf automatic-site-id-status {
           type string;
           description
             "VPLS automatic site identifier status";
         }
         leaf automatic-site-claim-id {
           type int32;
           description
             "Claim site identifier";
         }
         leaf automatic-site-collisions {
           type int32;
           description
             "Number of collisions";
         }
         leaf automatic-site-timer-status {
           type string;
           description
             "VPLS automatic site timer status";
         }
         leaf vpls-signaling-protocol-identifier {
           type string;
         }
         leaf local-site-id {
           type string;
         }
         leaf source-attachment-id {
           type string;
           description
             "Local source attachment identifier";
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         leaf target-attachment-id {
           type string;
           description
             "Remote target attachment identifier";
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list label-block {
           key "label-block-base";
           leaf-list label-block.heading {
             type string;
           }
           leaf label-block-base {
             type int32;
           }
           leaf label-block-offset {
             type int32;
           }
           leaf label-block-size {
             type int32;
           }
           leaf label-block-range {
             type int32;
           }
           leaf label-block-preference {
             type int32;
           }
           leaf label-block-status-vector {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container spe-info {
             leaf spe-info.heading {
               type string;
             }
             leaf local-ip-addr {
               type jt:ipaddr;
             }
             leaf remote-ip-addr {
               type jt:ipaddr;
             }
             leaf pw-status {
               type string;
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container automatic-site-timers {
           leaf automatic-site-timers.heading {
             type string;
           }
           leaf automatic-site-startup-wait-time {
             type string;
           }
           leaf automatic-site-new-site-wait-time {
             type string;
           }
           leaf automatic-site-collision-detect-time {
             type string;
           }
           leaf automatic-site-reclaim-wait-time {
             type string;
           }
         }
         container connections-summary {
           leaf vc-up-count {
             type int32;
           }
           leaf vc-down-count {
             type int32;
           }
         }
       }
       list ldp-vpls-reference-site {
         key "vpls-id";
         description
           "Information about LDP-VPLS";
         leaf vpls-signaling-protocol-identifier {
           type string;
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container connections-summary {
           leaf vc-up-count {
             type int32;
           }
           leaf vc-down-count {
             type int32;
           }
         }
       }
       container vpls-protocol-state {
         leaf vpls-signaling-protocol-identifier {
           type string;
         }
         leaf num-local-interfaces {
           type int32;
         }
         leaf num-local-interfaces-up {
           type int32;
         }
         leaf irb-present {
           type string;
         }
         leaf mesh-group-count {
           type int32;
         }
         leaf mesh-group-up-count {
           type int32;
         }
         list mesh-group-interfaces {
           description
             "Information about all interfaces associated with a mesh-group";
           list interface {
             key "interface-name";
             description
               "Interface name or address";
             leaf interface-name {
               type string;
               description
                 "Name of interface";
             }
             leaf interface-flags {
               type string;
             }
           }
         }
         list interface {
           key "interface-name";
           description
             "Interface name or address";
           leaf interface-name {
             type string;
             description
               "Name of interface";
           }
           leaf interface-flags {
             type string;
           }
         }
         list mesh-group-connection {
           key "mesh-group-name";
           description
             "Information about all vc-connections of a specific mesh-group";
           leaf mesh-group-name {
             type string;
             description
               "Name of mesh-group";
           }
           list connection {
             leaf-list connection.heading {
               type string;
             }
             leaf remote-pe {
               type jt:ipaddr;
             }
             leaf l2vpn-local-site-id {
               type int32;
               description
                 "Local site identifier";
             }
             leaf l2vpn-remote-site-id {
               type int32;
               description
                 "Remote site identifier";
             }
             leaf connection-status {
               type string;
             }
             leaf last-change {
               type string;
             }
             leaf inbound-label {
               type string;
             }
             leaf outbound-label {
               type string;
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
           container connections-summary {
             leaf vc-up-count {
               type int32;
             }
             leaf vc-down-count {
               type int32;
             }
           }
         }
         list reference-site {
           key "local-site-id vpls-id l2vpn-id";
           leaf automatic-site-name {
             type string;
             description
               "VPLS automatic site name";
           }
           leaf automatic-site-id-status {
             type string;
             description
               "VPLS automatic site identifier status";
           }
           leaf automatic-site-claim-id {
             type int32;
             description
               "Claim site identifier";
           }
           leaf automatic-site-collisions {
             type int32;
             description
               "Number of collisions";
           }
           leaf automatic-site-timer-status {
             type string;
             description
               "VPLS automatic site timer status";
           }
           leaf vpls-signaling-protocol-identifier {
             type string;
           }
           leaf local-site-id {
             type string;
           }
           leaf source-attachment-id {
             type string;
             description
               "Local source attachment identifier";
           }
           leaf vpls-id {
             type int32;
             description
               "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           leaf target-attachment-id {
             type string;
             description
               "Remote target attachment identifier";
           }
           list mesh-group-interfaces {
             key "mesh-group-name";
             description
               "Information about all interfaces associated with a 
               mesh-group";
             leaf mesh-group-name {
               type string;
               description
                 "Name of mesh-group";
             }
             leaf mesh-group-state {
               type string;
               description
                 "Mesh-group state";
             }
             leaf mesh-group-id {
               type int32;
               description
                 "Mesh-group Identifier";
             }
             list interface {
               key "interface-name";
               description
                 "Interface name or address";
               leaf interface-name {
                 type string;
                 description
                   "Name of interface";
               }
               leaf interface-description {
                 type string;
               }
               leaf interface-flags-description {
                 type string;
               }
               leaf interface-flags {
                 type string;
               }
             }
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           list connection {
             container history {
             }
           }
           list mesh-group-connection {
             description
               "Information about all vc-connections of a specific 
               mesh-group";
             list connection {
               container history {
               }
             }
           }
         }
       }
       container vpls-rsvp-te-ingress-p2mp-lsp {
         leaf vpls-ingress-p2mp-lsp-name {
           type string;
           description
             "Name of ingress point-to-multipoint LSP";
         }
         leaf vpls-rsvp-te-p2mp-flood-nexthop-id {
           type int32;
           description
             "Identifier for VPLS RSVP traffic-engineering ingress flood 
             next hop";
         }
       }
       container multihome {
         leaf multihome.heading {
           type string;
         }
         list multihome-site {
           key "multihome-site-name";
           leaf multihome-site-name {
             type string;
             description
               "Name of site";
           }
           leaf multihome-site-id {
             type int32;
             description
               "Site Identifier";
           }
           leaf multihome-site-preference {
             type int32;
             description
               "Site Preference";
           }
           leaf multihome-site-state {
             type string;
             description
               "Site state";
           }
           leaf multihome-num-interfaces {
             type int32;
           }
           leaf multihome-num-interfaces-up {
             type int32;
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           container remote-advertisements {
             leaf remote-advertisements.heading {
               type string;
             }
             list remote-adv {
               key "remote-adv-addr";
               leaf remote-adv-addr {
                 type string;
               }
               leaf remote-adv-preference {
                 type int32;
                 description
                   "Remote PE preference";
               }
               leaf remote-adv-ctrl-flag {
                 type string;
                 description
                   "Remote PE Control flags";
               }
               leaf remote-adv-ctrl-flag-description {
                 type string;
                 description
                   "Control flags description";
               }
             }
           }
         }
       }
       container history {
         leaf history.category-heading {
           type string;
         }
         leaf history.heading {
           type string;
         }
         list history-element {
           key "log-time-stamp log-event";
           leaf log-time-stamp {
             type string;
           }
           leaf log-event {
             type string;
           }
           leaf changed-entity {
             type string;
           }
         }
       }
     }
   }
   grouping vpls-statistics-information-block {
     list instance {
       key "instance-name";
       description
         "Routing protocol instance";
       leaf instance-name {
         type string;
       }
       leaf instance-display-error {
         type string;
       }
       leaf edge-protection {
         type string;
       }
       leaf edge-protector {
         type string;
       }
       list reference-site {
         key "local-site-id vpls-id l2vpn-id";
         leaf automatic-site-name {
           type string;
           description
             "VPLS automatic site name";
         }
         leaf automatic-site-id-status {
           type string;
           description
             "VPLS automatic site identifier status";
         }
         leaf automatic-site-claim-id {
           type int32;
           description
             "Claim site identifier";
         }
         leaf automatic-site-collisions {
           type int32;
           description
             "Number of collisions";
         }
         leaf automatic-site-timer-status {
           type string;
           description
             "VPLS automatic site timer status";
         }
         leaf vpls-signaling-protocol-identifier {
           type string;
         }
         leaf local-site-id {
           type string;
         }
         leaf source-attachment-id {
           type string;
           description
             "Local source attachment identifier";
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         leaf target-attachment-id {
           type string;
           description
             "Remote target attachment identifier";
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list label-block {
           key "label-block-base";
           leaf-list label-block.heading {
             type string;
           }
           leaf label-block-base {
             type int32;
           }
           leaf label-block-offset {
             type int32;
           }
           leaf label-block-size {
             type int32;
           }
           leaf label-block-range {
             type int32;
           }
           leaf label-block-preference {
             type int32;
           }
           leaf label-block-status-vector {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container spe-info {
             leaf spe-info.heading {
               type string;
             }
             leaf local-ip-addr {
               type jt:ipaddr;
             }
             leaf remote-ip-addr {
               type jt:ipaddr;
             }
             leaf pw-status {
               type string;
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container automatic-site-timers {
           leaf automatic-site-timers.heading {
             type string;
           }
           leaf automatic-site-startup-wait-time {
             type string;
           }
           leaf automatic-site-new-site-wait-time {
             type string;
           }
           leaf automatic-site-collision-detect-time {
             type string;
           }
           leaf automatic-site-reclaim-wait-time {
             type string;
           }
         }
         container connections-summary {
           leaf vc-up-count {
             type int32;
           }
           leaf vc-down-count {
             type int32;
           }
         }
       }
       list ldp-vpls-reference-site {
         key "vpls-id";
         description
           "Information about LDP-VPLS";
         leaf vpls-signaling-protocol-identifier {
           type string;
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container connections-summary {
           leaf vc-up-count {
             type int32;
           }
           leaf vc-down-count {
             type int32;
           }
         }
       }
       container vpls-protocol-state {
         leaf vpls-signaling-protocol-identifier {
           type string;
         }
         leaf num-local-interfaces {
           type int32;
         }
         leaf num-local-interfaces-up {
           type int32;
         }
         leaf irb-present {
           type string;
         }
         leaf mesh-group-count {
           type int32;
         }
         leaf mesh-group-up-count {
           type int32;
         }
         list mesh-group-interfaces {
           description
             "Information about all interfaces associated with a mesh-group";
           list interface {
             key "interface-name";
             description
               "Interface name or address";
             leaf interface-name {
               type string;
               description
                 "Name of interface";
             }
             leaf interface-flags {
               type string;
             }
           }
         }
         list interface {
           key "interface-name";
           description
             "Interface name or address";
           leaf interface-name {
             type string;
             description
               "Name of interface";
           }
           leaf interface-flags {
             type string;
           }
         }
         list mesh-group-connection {
           key "mesh-group-name";
           description
             "Information about all vc-connections of a specific mesh-group";
           leaf mesh-group-name {
             type string;
             description
               "Name of mesh-group";
           }
           list connection {
             leaf-list connection.heading {
               type string;
             }
             leaf remote-pe {
               type jt:ipaddr;
             }
             leaf l2vpn-local-site-id {
               type int32;
               description
                 "Local site identifier";
             }
             leaf l2vpn-remote-site-id {
               type int32;
               description
                 "Remote site identifier";
             }
             leaf connection-status {
               type string;
             }
             leaf last-change {
               type string;
             }
             leaf inbound-label {
               type string;
             }
             leaf outbound-label {
               type string;
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
           container connections-summary {
             leaf vc-up-count {
               type int32;
             }
             leaf vc-down-count {
               type int32;
             }
           }
         }
         list reference-site {
           key "local-site-id vpls-id l2vpn-id";
           leaf automatic-site-name {
             type string;
             description
               "VPLS automatic site name";
           }
           leaf automatic-site-id-status {
             type string;
             description
               "VPLS automatic site identifier status";
           }
           leaf automatic-site-claim-id {
             type int32;
             description
               "Claim site identifier";
           }
           leaf automatic-site-collisions {
             type int32;
             description
               "Number of collisions";
           }
           leaf automatic-site-timer-status {
             type string;
             description
               "VPLS automatic site timer status";
           }
           leaf vpls-signaling-protocol-identifier {
             type string;
           }
           leaf local-site-id {
             type string;
           }
           leaf source-attachment-id {
             type string;
             description
               "Local source attachment identifier";
           }
           leaf vpls-id {
             type int32;
             description
               "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           leaf target-attachment-id {
             type string;
             description
               "Remote target attachment identifier";
           }
           list mesh-group-interfaces {
             key "mesh-group-name";
             description
               "Information about all interfaces associated with a 
               mesh-group";
             leaf mesh-group-name {
               type string;
               description
                 "Name of mesh-group";
             }
             leaf mesh-group-state {
               type string;
               description
                 "Mesh-group state";
             }
             leaf mesh-group-id {
               type int32;
               description
                 "Mesh-group Identifier";
             }
             list interface {
               key "interface-name";
               description
                 "Interface name or address";
               leaf interface-name {
                 type string;
                 description
                   "Name of interface";
               }
               leaf interface-description {
                 type string;
               }
               leaf interface-flags-description {
                 type string;
               }
               leaf interface-flags {
                 type string;
               }
             }
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           list connection {
             container history {
             }
           }
           list mesh-group-connection {
             description
               "Information about all vc-connections of a specific 
               mesh-group";
             list connection {
               container history {
               }
             }
           }
         }
       }
       container vpls-rsvp-te-ingress-p2mp-lsp {
         leaf vpls-ingress-p2mp-lsp-name {
           type string;
           description
             "Name of ingress point-to-multipoint LSP";
         }
         leaf vpls-rsvp-te-p2mp-flood-nexthop-id {
           type int32;
           description
             "Identifier for VPLS RSVP traffic-engineering ingress flood 
             next hop";
         }
       }
       container multihome {
         leaf multihome.heading {
           type string;
         }
         list multihome-site {
           key "multihome-site-name";
           leaf multihome-site-name {
             type string;
             description
               "Name of site";
           }
           leaf multihome-site-id {
             type int32;
             description
               "Site Identifier";
           }
           leaf multihome-site-preference {
             type int32;
             description
               "Site Preference";
           }
           leaf multihome-site-state {
             type string;
             description
               "Site state";
           }
           leaf multihome-num-interfaces {
             type int32;
           }
           leaf multihome-num-interfaces-up {
             type int32;
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           container remote-advertisements {
             leaf remote-advertisements.heading {
               type string;
             }
             list remote-adv {
               key "remote-adv-addr";
               leaf remote-adv-addr {
                 type string;
               }
               leaf remote-adv-preference {
                 type int32;
                 description
                   "Remote PE preference";
               }
               leaf remote-adv-ctrl-flag {
                 type string;
                 description
                   "Remote PE Control flags";
               }
               leaf remote-adv-ctrl-flag-description {
                 type string;
                 description
                   "Control flags description";
               }
             }
           }
         }
       }
       container history {
         leaf history.category-heading {
           type string;
         }
         leaf history.heading {
           type string;
         }
         list history-element {
           key "log-time-stamp log-event";
           leaf log-time-stamp {
             type string;
           }
           leaf log-event {
             type string;
           }
           leaf changed-entity {
             type string;
           }
         }
       }
     }
     list interface-statistics {
       leaf l2bd-vlan-id {
         type string;
         description
           "Bridge domain VLAN";
       }
       leaf vn-id {
         type uint32;
         description
           "VXLAN identifier";
       }
       leaf remote-pe {
         type jt:ipaddr;
       }
       leaf broadcast-packets {
         type uint64;
         description
           "Broadcast packets";
       }
       leaf broadcast-bytes {
         type uint64;
         description
           "Broadcast bytes";
       }
       leaf multicast-packets {
         type uint64;
         description
           "Multicast packets";
       }
       leaf multicast-bytes {
         type uint64;
         description
           "Multicast bytes";
       }
       leaf flooded-packets {
         type uint64;
         description
           "Flooded packets";
       }
       leaf flooded-bytes {
         type uint64;
         description
           "Flooded bytes";
       }
       leaf unicast-packets {
         type uint64;
         description
           "Unicast packets";
       }
       leaf unicast-bytes {
         type uint64;
         description
           "Unicast bytes";
       }
       leaf data-vlan-mlp-drop-count {
         type int32;
         description
           "Number of mac learning packets dropped in data vlan";
       }
       leaf num-mac-count {
         type int32;
         description
           "Number of addresses learned on the interface";
       }
       leaf mac-limit {
         type int32;
         description
           "Limit of number of addresses learned on interface";
       }
       list interface {
         key "interface-name";
         description
           "Interface name or address";
         leaf interface-name {
           type string;
           description
             "Name of interface";
         }
         leaf local-interface-index {
           type int32;
           description
             "SNMP ifIndex of local interface";
         }
         leaf interface-flags {
           type string;
         }
       }
     }
   }
   grouping l2ald-rtb-macdb-block {
     leaf l2ald-macdb-rtb-name {
       type string;
       description
         "Bridging MAC database for a routing instance";
     }
     list l2ald-mac-entry {
       key "l2-mac-address l2-mac-logical-interface l2-mac-routing-instance l2-mac-bridging-domain";
       leaf l2-mac-address {
         type jt:mac-addr;
         description
           "Media access control address learned from another source";
       }
       leaf l2-mac-logical-interface {
         type string;
         description
           "Name of logical interface on which MAC address was learned";
       }
       leaf l2-mac-logical-system {
         type string;
         description
           "Name of logical system in which this MAC address was learned";
       }
       leaf l2-mac-routing-instance {
         type string;
         description
           "Routing instance in which the MAC address was learned";
       }
       leaf l2-mac-bridging-domain {
         type string;
         description
           "Bridging domain in which the MAC address was learned";
       }
       leaf l2-mac-flags {
         type string;
         description
           "Forwarding entry flags associated with MACs displayed in short 
           form";
       }
       leaf l2-mac-fwd-next-hop {
         type uint32;
         description
           "Forwarding next hop for Control MAC to be routed to";
       }
       leaf l2-mac-property {
         type string;
         description
           "Property of MAC route";
       }
       leaf l2-mac-pvlan-port-role {
         type string;
         description
           "The PVLAN port role for interface associated with these MAC 
           addresses";
       }
       leaf l2-mac-pvlan-vlan-id {
         type string;
         description
           "The PVLAN vlan ID associated with these MAC addresses";
       }
       leaf l2-mac-ifl-generation {
         type uint32;
         description
           "Creation time of the logical interface when this MAC address was
           learned";
       }
       container l2-mac-entry {
         leaf l2-mac-address {
           type jt:mac-addr;
           description
             "Media access control address learned from another source";
         }
         leaf l2-mac-flags {
           type string;
           description
             "Forwarding entry flags associated with MACs displayed in short
             form";
         }
         leaf l2-mac-gbptag {
           type int32;
           description
             "L2 MAC gbp tag value";
         }
         leaf l2-mac-logical-interface {
           type string;
           description
             "Name of logical interface on which MAC address was learned";
         }
         leaf l2-mac-fwd-next-hop {
           type uint32;
           description
             "Forwarding next hop for Control MAC to be routed to";
         }
         leaf l2-mac-property {
           type string;
           description
             "Property of MAC route";
         }
         leaf l2-active-source {
           type string;
           description
             "Remote VXLAN tunnel endpoint ip address or ESI value";
         }
       }
       leaf l2-bridge-vlan {
         type string;
         description
           "Vlan for the bridging domain";
       }
       leaf l2-mac-gbptag {
         type int32;
         description
           "L2 MAC gbp tag value";
       }
       leaf l2-active-source {
         type string;
         description
           "Remote VXLAN tunnel endpoint ip address or ESI value";
       }
       leaf l2-bridge-isid {
         type uint32;
         description
           "ISID for the bridging domain";
       }
       leaf l2-remote-beb-mac-address {
         type jt:mac-addr;
         description
           "Media access control address of remote backbone edge bridge 
           (BEB)";
       }
       leaf l2-mac-elp-nh {
         type uint32;
         description
           "ELP NH Id of the MAC address";
       }
       leaf l2-mac-base-logical-interface {
         type string;
         description
           "Name of logical interface on which MAC address was learnt first";
       }
       leaf l2-mac-entry-flags {
         type string;
         description
           "Forwarding entry flags associated with these MAC addresses";
       }
       leaf l2-mac-epoch {
         type uint32;
         description
           "Spanning Tree Protocol (STP) epoch number when MAC address was 
           learned";
       }
       leaf l2-mac-sequence-number {
         type uint32;
         description
           "Sequence number assigned to this MAC address";
       }
       leaf l2-mac-learn-mask {
         type string;
         description
           "Mask of Packet Forwarding Engines where this MAC address was 
           learned";
       }
       leaf l2-mac-mcae-id {
         type uint32;
         description
           "MCAE ID of the mac entry";
       }
       leaf l2-mac-mcae-ifl-unit {
         type uint32;
         description
           "MCAE IFL unit of the mac entry";
       }
       leaf l2-mac-svc-id {
         type uint32;
         description
           "MCAE SVC ID of the mac entry";
       }
       leaf l2-mac-rg-id {
         type uint32;
         description
           "RG ID of the mac entry";
       }
       leaf l2-mac-rtm-op {
         type uint32;
         description
           "MCAE mac operation of the mac entry";
       }
       leaf l2-mac-time-info {
         type string;
         description
           "Mac learning time";
       }
       container l2ald-mac-source-address-statistics {
         description
           "MAC source address statistics";
         leaf packet-count {
           type uint64;
           description
             "Packet count";
         }
         leaf byte-count {
           type uint64;
           description
             "Byte count";
         }
       }
       container l2ald-mac-destination-address-statistics {
         description
           "MAC destination address statistics";
         leaf packet-count {
           type uint64;
           description
             "Packet count";
         }
         leaf byte-count {
           type uint64;
           description
             "Byte count";
         }
       }
       leaf l2-remote-vtep-address {
         type string;
         description
           "Remote VXLAN tunnel endpoint ip address";
       }
     }
   }
   grouping l2ald-interface-macdb-block {
     leaf l2ald-macdb-if-name {
       type string;
     }
     list l2ald-mac-entry {
       key "l2-mac-address l2-mac-logical-interface l2-mac-routing-instance l2-mac-bridging-domain";
       leaf l2-mac-address {
         type jt:mac-addr;
         description
           "Media access control address learned from another source";
       }
       leaf l2-mac-logical-interface {
         type string;
         description
           "Name of logical interface on which MAC address was learned";
       }
       leaf l2-mac-logical-system {
         type string;
         description
           "Name of logical system in which this MAC address was learned";
       }
       leaf l2-mac-routing-instance {
         type string;
         description
           "Routing instance in which the MAC address was learned";
       }
       leaf l2-mac-bridging-domain {
         type string;
         description
           "Bridging domain in which the MAC address was learned";
       }
       leaf l2-mac-flags {
         type string;
         description
           "Forwarding entry flags associated with MACs displayed in short 
           form";
       }
       leaf l2-mac-fwd-next-hop {
         type uint32;
         description
           "Forwarding next hop for Control MAC to be routed to";
       }
       leaf l2-mac-property {
         type string;
         description
           "Property of MAC route";
       }
       leaf l2-mac-pvlan-port-role {
         type string;
         description
           "The PVLAN port role for interface associated with these MAC 
           addresses";
       }
       leaf l2-mac-pvlan-vlan-id {
         type string;
         description
           "The PVLAN vlan ID associated with these MAC addresses";
       }
       leaf l2-mac-ifl-generation {
         type uint32;
         description
           "Creation time of the logical interface when this MAC address was
           learned";
       }
       container l2-mac-entry {
         leaf l2-mac-address {
           type jt:mac-addr;
           description
             "Media access control address learned from another source";
         }
         leaf l2-mac-flags {
           type string;
           description
             "Forwarding entry flags associated with MACs displayed in short
             form";
         }
         leaf l2-mac-gbptag {
           type int32;
           description
             "L2 MAC gbp tag value";
         }
         leaf l2-mac-logical-interface {
           type string;
           description
             "Name of logical interface on which MAC address was learned";
         }
         leaf l2-mac-fwd-next-hop {
           type uint32;
           description
             "Forwarding next hop for Control MAC to be routed to";
         }
         leaf l2-mac-property {
           type string;
           description
             "Property of MAC route";
         }
         leaf l2-active-source {
           type string;
           description
             "Remote VXLAN tunnel endpoint ip address or ESI value";
         }
       }
       leaf l2-bridge-vlan {
         type string;
         description
           "Vlan for the bridging domain";
       }
       leaf l2-mac-gbptag {
         type int32;
         description
           "L2 MAC gbp tag value";
       }
       leaf l2-active-source {
         type string;
         description
           "Remote VXLAN tunnel endpoint ip address or ESI value";
       }
       leaf l2-bridge-isid {
         type uint32;
         description
           "ISID for the bridging domain";
       }
       leaf l2-remote-beb-mac-address {
         type jt:mac-addr;
         description
           "Media access control address of remote backbone edge bridge 
           (BEB)";
       }
       leaf l2-mac-elp-nh {
         type uint32;
         description
           "ELP NH Id of the MAC address";
       }
       leaf l2-mac-base-logical-interface {
         type string;
         description
           "Name of logical interface on which MAC address was learnt first";
       }
       leaf l2-mac-entry-flags {
         type string;
         description
           "Forwarding entry flags associated with these MAC addresses";
       }
       leaf l2-mac-epoch {
         type uint32;
         description
           "Spanning Tree Protocol (STP) epoch number when MAC address was 
           learned";
       }
       leaf l2-mac-sequence-number {
         type uint32;
         description
           "Sequence number assigned to this MAC address";
       }
       leaf l2-mac-learn-mask {
         type string;
         description
           "Mask of Packet Forwarding Engines where this MAC address was 
           learned";
       }
       leaf l2-mac-mcae-id {
         type uint32;
         description
           "MCAE ID of the mac entry";
       }
       leaf l2-mac-mcae-ifl-unit {
         type uint32;
         description
           "MCAE IFL unit of the mac entry";
       }
       leaf l2-mac-svc-id {
         type uint32;
         description
           "MCAE SVC ID of the mac entry";
       }
       leaf l2-mac-rg-id {
         type uint32;
         description
           "RG ID of the mac entry";
       }
       leaf l2-mac-rtm-op {
         type uint32;
         description
           "MCAE mac operation of the mac entry";
       }
       leaf l2-mac-time-info {
         type string;
         description
           "Mac learning time";
       }
       container l2ald-mac-source-address-statistics {
         description
           "MAC source address statistics";
         leaf packet-count {
           type uint64;
           description
             "Packet count";
         }
         leaf byte-count {
           type uint64;
           description
             "Byte count";
         }
       }
       container l2ald-mac-destination-address-statistics {
         description
           "MAC destination address statistics";
         leaf packet-count {
           type uint64;
           description
             "Packet count";
         }
         leaf byte-count {
           type uint64;
           description
             "Byte count";
         }
       }
       leaf l2-remote-vtep-address {
         type string;
         description
           "Remote VXLAN tunnel endpoint ip address";
       }
     }
   }
   grouping l2ald-vpls-flood-instance-block {
     container l2ald-vpls-lr-information {
       list logical-system-info {
         key "logical-system-name";
         leaf logical-system-name {
           type string;
           description
             "Logical System";
         }
       }
       list l2ald-vpls-flood-instance-information {
         key "instance-name bridge-domain-name";
         leaf instance-name {
           type string;
         }
         leaf num-active-ce-iffs {
           type int32;
         }
         leaf num-active-ve-iffs {
           type int32;
         }
         list flood-route {
           key "route-prefix";
           leaf route-prefix {
             type string;
           }
           leaf route-type {
             type string;
           }
           leaf owner {
             type string;
           }
           leaf nhtype {
             type string;
           }
           leaf nhindex {
             type int32;
           }
           list flood-nh-group {
             key "flood-nh-group-name";
             leaf flood-nh-group-name {
               type string;
             }
             leaf flood-nh-group-type {
               type string;
             }
             leaf nhtype {
               type string;
             }
             leaf nhindex {
               type int32;
             }
             leaf flood-group-composite-function {
               type string;
             }
             list flood-nh-components {
               key "interface-name interface-type";
               leaf interface-name {
                 type string;
                 description
                   "Bridging media access control address interface";
               }
               leaf interface-type {
                 type string;
               }
               leaf nhtype {
                 type string;
               }
               leaf nhindex {
                 type int32;
               }
               leaf interface-esi {
                 type string;
                 description
                   "ESI";
               }
               leaf nh-guid {
                 type uint64;
               }
               leaf remote-vtep-address {
                 type string;
                 description
                   "Remote VXLAN tunnel endpoint IP address";
               }
               leaf shared-rvtep-interface-name {
                 type string;
               }
             }
             list flood-nh-p2mp-components {
               key "component-nhindex";
               leaf component-nhindex {
                 type int32;
               }
             }
             list flood-nh-evpn-core-components {
               key "component-nhindex";
               leaf component-nhindex {
                 type int32;
               }
               leaf peer {
                 type string;
               }
               leaf nh-type {
                 type string;
               }
               leaf interface-esi {
                 type string;
                 description
                   "ESI";
               }
             }
             leaf nh-guid {
               type uint64;
             }
           }
           list flood-nh-components {
             key "interface-name interface-type";
             leaf interface-name {
               type string;
               description
                 "Bridging media access control address interface";
             }
             leaf interface-type {
               type string;
             }
             leaf nhtype {
               type string;
             }
             leaf nhindex {
               type int32;
             }
             leaf interface-esi {
               type string;
               description
                 "ESI";
             }
             leaf nh-guid {
               type uint64;
             }
             leaf remote-vtep-address {
               type string;
               description
                 "Remote VXLAN tunnel endpoint IP address";
             }
             leaf shared-rvtep-interface-name {
               type string;
             }
           }
           leaf route-flood-group-name {
             type string;
           }
           leaf route-flood-group-index {
             type int32;
           }
           leaf df-indirect-index {
             type int32;
           }
           leaf df-composite-index {
             type int32;
           }
           leaf ndf-indirect-index {
             type int32;
           }
           leaf ndf-composite-index {
             type int32;
           }
           leaf make-before-break {
             type string;
           }
           leaf make-before-break-state {
             type string;
           }
           list flood-nh-evpn-core-components {
             key "component-nhindex";
             leaf component-nhindex {
               type int32;
             }
             leaf peer {
               type string;
             }
             leaf nh-type {
               type string;
             }
             leaf interface-esi {
               type string;
               description
                 "ESI";
             }
           }
           list flood-nh-p2mp-components {
             key "component-nhindex";
             leaf component-nhindex {
               type int32;
             }
           }
           leaf nh-guid {
             type uint64;
           }
         }
         leaf bridge-domain-name {
           type string;
           description
             "Name of the bridging domain";
         }
         leaf bridge-domain-evpn-extension {
           type string;
           description
             "EVPN extension for the BD";
         }
       }
     }
   }
   grouping l2ald-vpls-flood-route-information-block {
     list flood-route {
       key "route-prefix";
       leaf route-prefix {
         type string;
       }
       leaf route-type {
         type string;
       }
       leaf owner {
         type string;
       }
       leaf nhtype {
         type string;
       }
       leaf nhindex {
         type int32;
       }
       list flood-nh-group {
         key "flood-nh-group-name";
         leaf flood-nh-group-name {
           type string;
         }
         leaf flood-nh-group-type {
           type string;
         }
         leaf nhtype {
           type string;
         }
         leaf nhindex {
           type int32;
         }
         leaf flood-group-composite-function {
           type string;
         }
         list flood-nh-components {
           key "interface-name interface-type";
           leaf interface-name {
             type string;
             description
               "Bridging media access control address interface";
           }
           leaf interface-type {
             type string;
           }
           leaf nhtype {
             type string;
           }
           leaf nhindex {
             type int32;
           }
           leaf interface-esi {
             type string;
             description
               "ESI";
           }
           leaf nh-guid {
             type uint64;
           }
           leaf remote-vtep-address {
             type string;
             description
               "Remote VXLAN tunnel endpoint IP address";
           }
           leaf shared-rvtep-interface-name {
             type string;
           }
         }
         list flood-nh-p2mp-components {
           key "component-nhindex";
           leaf component-nhindex {
             type int32;
           }
         }
         list flood-nh-evpn-core-components {
           key "component-nhindex";
           leaf component-nhindex {
             type int32;
           }
           leaf peer {
             type string;
           }
           leaf nh-type {
             type string;
           }
           leaf interface-esi {
             type string;
             description
               "ESI";
           }
         }
         leaf nh-guid {
           type uint64;
         }
       }
       list flood-nh-components {
         key "interface-name interface-type";
         leaf interface-name {
           type string;
           description
             "Bridging media access control address interface";
         }
         leaf interface-type {
           type string;
         }
         leaf nhtype {
           type string;
         }
         leaf nhindex {
           type int32;
         }
         leaf interface-esi {
           type string;
           description
             "ESI";
         }
         leaf nh-guid {
           type uint64;
         }
         leaf remote-vtep-address {
           type string;
           description
             "Remote VXLAN tunnel endpoint IP address";
         }
         leaf shared-rvtep-interface-name {
           type string;
         }
       }
       leaf route-flood-group-name {
         type string;
       }
       leaf route-flood-group-index {
         type int32;
       }
       leaf df-indirect-index {
         type int32;
       }
       leaf df-composite-index {
         type int32;
       }
       leaf ndf-indirect-index {
         type int32;
       }
       leaf ndf-composite-index {
         type int32;
       }
       leaf make-before-break {
         type string;
       }
       leaf make-before-break-state {
         type string;
       }
       list flood-nh-evpn-core-components {
         key "component-nhindex";
         leaf component-nhindex {
           type int32;
         }
         leaf peer {
           type string;
         }
         leaf nh-type {
           type string;
         }
         leaf interface-esi {
           type string;
           description
             "ESI";
         }
       }
       list flood-nh-p2mp-components {
         key "component-nhindex";
         leaf component-nhindex {
           type int32;
         }
       }
       leaf nh-guid {
         type uint64;
       }
     }
   }
   grouping l2ald-vpls-flood-event-queue-block {
     container l2ald-vpls-flood-next-event {
       list l2ald-vpls-flood-event-info {
         leaf event-name {
           type string;
         }
         leaf event-owner {
           type string;
         }
         leaf event-type {
           type string;
         }
         leaf event-op {
           type string;
         }
         leaf event-error {
           type string;
         }
       }
     }
     container l2ald-vpls-flood-event-list {
       list l2ald-vpls-flood-event-info {
         leaf event-name {
           type string;
         }
         leaf event-type {
           type string;
         }
         leaf event-op {
           type string;
         }
         leaf event-owner {
           type string;
         }
         leaf event-error {
           type string;
         }
       }
     }
   }
 }
