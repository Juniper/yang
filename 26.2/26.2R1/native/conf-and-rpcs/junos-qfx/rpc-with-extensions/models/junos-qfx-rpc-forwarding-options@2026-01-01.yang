/*
 * Copyright (c) 2026 Juniper Networks, Inc.
 * All rights reserved.
 */
 module junos-qfx-rpc-forwarding-options {
   namespace "http://yang.juniper.net/junos-qfx/rpc/forwarding-options";

   prefix forwarding-options;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for forwarding-options command(s)";

   revision 2026-01-01 {
     description "Junos: 26.2R1.7";
   }

   rpc get-hash-info {
     description "Show enhanced-hash-key parameters";
     junos:command "show forwarding-options enhanced-hash-key";
     output {
       choice output-tags {
         case actual-tag {
           container hash-info {
             uses hash-info-block;
           }
         }
         case multichassis-tag {
           container multi-routing-engine-results {
             list multi-routing-engine-item {
               leaf re-name {
                 type string;
               }
               choice output-tags {
                 case actual-tag {
                   container hash-info {
                     uses hash-info-block;
                   }
                 }
               }
             }
           }
         }
       }
     }
   }
   rpc get-flex-hash-information {
     description "Show flex-hash configuration";
     junos:command "show forwarding-options enhanced-hash-key flex-hash";
     input {
       leaf profile-name {
         description "Flex profile name";
         junos:cli-feature "nokeyword";
         type string;
       }
     }
     output {
       choice output-tags {
         case output-tag {
           leaf output {
             type string;
           }
         }
         case multichassis-tag {
           anyxml multi-routing-engine-results;
         }
       }
     }
   }
   rpc get-conditional-match-information {
     description "Show conditional-match configuartion";
     junos:command "show forwarding-options enhanced-hash-key conditional-match";
     input {
       leaf profile-name {
         description "Conditional match profile name";
         junos:cli-feature "nokeyword";
         type string;
       }
     }
     output {
       choice output-tags {
         case output-tag {
           leaf output {
             type string;
           }
         }
         case multichassis-tag {
           anyxml multi-routing-engine-results;
         }
       }
     }
   }
   rpc get-hash-information {
     description "Show hash-key parameters";
     junos:command "show forwarding-options hash-key";
     output {
       choice output-tags {
         case actual-tag {
           container hash-info {
             uses hash-info-block;
           }
         }
         case multichassis-tag {
           container multi-routing-engine-results {
             list multi-routing-engine-item {
               leaf re-name {
                 type string;
               }
               choice output-tags {
                 case actual-tag {
                   container hash-info {
                     uses hash-info-block;
                   }
                 }
               }
             }
           }
         }
       }
     }
   }
   rpc get-native-analyzer-information {
     description "Show native analyzer information";
     junos:command "show forwarding-options analyzer";
     input {
       leaf analyzer-name {
         description "Analyzer name";
         junos:cli-feature "nokeyword";
         type string;
       }
     }
     output {
       choice output-tags {
         case actual-tag {
           container analyzer {
             uses analyzer-block;
           }
         }
         case multichassis-tag {
           container multi-routing-engine-results {
             list multi-routing-engine-item {
               leaf re-name {
                 type string;
               }
               choice output-tags {
                 case actual-tag {
                   container analyzer {
                     uses analyzer-block;
                   }
                 }
               }
             }
           }
         }
       }
     }
   }
   rpc get-forwarding-options-next-hop-group {
     description "Show next-hop-group information";
     junos:command "show forwarding-options next-hop-group";
     input {
       leaf verbosity {
         junos:cli-feature "nokeyword";
         default "brief";
         type enumeration {
           enum "terse" {
             description "Display terse output";
           }
           enum "brief" {
             description "Display brief output";
           }
           enum "detail" {
             description "Display detail output";
           }
         }
       }
       leaf group-name {
         description "Name of next-hop-group";
         junos:cli-feature "nokeyword";
         type string;
       }
     }
     output {
       choice output-tags {
         case actual-tag {
           container smpl-next-hop-group {
             uses smpl-next-hop-group-block;
           }
         }
         case multichassis-tag {
           container multi-routing-engine-results {
             list multi-routing-engine-item {
               leaf re-name {
                 type string;
               }
               choice output-tags {
                 case actual-tag {
                   container smpl-next-hop-group {
                     uses smpl-next-hop-group-block;
                   }
                 }
               }
             }
           }
         }
       }
     }
   }
   rpc get-forwarding-options-port-mirroring {
     description "Show port-mirroring information";
     junos:command "show forwarding-options port-mirroring";
     input {
       leaf verbosity {
         junos:cli-feature "nokeyword";
         default "detail";
         type enumeration {
           enum "terse" {
             description "Display terse output";
           }
           enum "detail" {
             description "Display detail output";
           }
         }
       }
       leaf instance-name {
         description "Name of port-mirroring instance";
         junos:cli-feature "nokeyword";
         type string;
       }
     }
     output {
       choice output-tags {
         case actual-tag {
           container smpl-port-mirroring {
             uses smpl-port-mirroring-block;
           }
         }
         case multichassis-tag {
           container multi-routing-engine-results {
             list multi-routing-engine-item {
               leaf re-name {
                 type string;
               }
               choice output-tags {
                 case actual-tag {
                   container smpl-port-mirroring {
                     uses smpl-port-mirroring-block;
                   }
                 }
               }
             }
           }
         }
       }
     }
   }
   rpc get-forwarding-options-port-mirroring-self {
     description "Show port-mirroring self-mirror information";
     junos:command "show forwarding-options port-mirroring self-mirror";
     input {
       leaf verbosity {
         junos:cli-feature "nokeyword";
         default "detail";
         type enumeration {
           enum "detail" {
             description "Display detail output";
           }
           enum "statistics" {
             description "Display statistics output";
           }
           enum "start" {
             description "Display start output";
           }
           enum "stop" {
             description "Display stop statistics";
           }
         }
       }
       leaf instance-name {
         description "Name of port-mirroring instance";
         junos:cli-feature "nokeyword";
         type string;
       }
     }
     output {
       choice output-tags {
         case actual-tag {
           container smpl-port-mirroring-self {
             uses smpl-port-mirroring-self-block;
           }
         }
         case multichassis-tag {
           container multi-routing-engine-results {
             list multi-routing-engine-item {
               leaf re-name {
                 type string;
               }
               choice output-tags {
                 case actual-tag {
                   container smpl-port-mirroring-self {
                     uses smpl-port-mirroring-self-block;
                   }
                 }
               }
             }
           }
         }
       }
     }
   }
   rpc get-tap-aggregation {
     description "Show tap interfaces";
     junos:command "show forwarding-options tap-aggregation";
     input {
       choice which-cmd {
         case group-name {
           leaf group-name {
             description "Enter group name";
             junos:cli-feature "nokeyword";
             type string;
           }
         }
         case statistics {
           leaf statistics {
             description "Statistics of all tap and tool interfaces traffic stats";
             type empty;
           }
         }
       }
     }
     output {
       choice output-tags {
         case output-tag {
           leaf output {
             type string;
           }
         }
         case actual-tag {
           anyxml tap-aggregation;
         }
         case multichassis-tag {
           anyxml multi-routing-engine-results;
         }
       }
     }
   }
   rpc get-switch-information {
     description "Show active switch mode";
     junos:command "show forwarding-options switch-mode";
     output {
       choice output-tags {
         case output-tag {
           leaf output {
             type string;
           }
         }
         case actual-tag {
           anyxml switch-information;
         }
         case multichassis-tag {
           anyxml multi-routing-engine-results;
         }
       }
     }
   }
   rpc get-mirror-profile {
     description "Show mirror-profile";
     junos:command "show forwarding-options mirror-profile";
     input {
       leaf mirror-profile-name {
         description "Name of mirror-profile";
         junos:cli-feature "nokeyword";
         type string;
       }
     }
     output {
       choice output-tags {
         case actual-tag {
           container mirror-profile {
             uses mirror-profile-block;
           }
         }
         case multichassis-tag {
           container multi-routing-engine-results {
             list multi-routing-engine-item {
               leaf re-name {
                 type string;
               }
               choice output-tags {
                 case actual-tag {
                   container mirror-profile {
                     uses mirror-profile-block;
                   }
                 }
               }
             }
           }
         }
       }
     }
   }
   rpc get-mirror-on-drop-buffer-stats {
     description "Show mod buffer stats";
     junos:command "show forwarding-options mod-buffer-stats";
     output {
       choice output-tags {
         case actual-tag {
           container mirror-on-drop-buffer-stats {
             uses mirror-on-drop-buffer-stats-block;
           }
         }
         case multichassis-tag {
           container multi-routing-engine-results {
             list multi-routing-engine-item {
               leaf re-name {
                 type string;
               }
               choice output-tags {
                 case actual-tag {
                   container mirror-on-drop-buffer-stats {
                     uses mirror-on-drop-buffer-stats-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping hash-info-block {
     container enhanced-hash-key-information {
       description
         "Enhanced hash info";
       leaf-list hash-mode {
         type string;
       }
       container hash-seed {
         leaf resilient-seed-value {
           type int32;
         }
         leaf seed-value {
           type int32;
         }
       }
       container inet-packet-fields {
         leaf protocol {
           type string;
         }
         leaf source-l4-port {
           type string;
         }
         leaf destination-l4-port {
           type string;
         }
         leaf ipv4-source-addr {
           type string;
         }
         leaf ipv4-destination-addr {
           type string;
         }
         leaf vlan-id {
           type string;
         }
       }
       container gtp-hash-information {
         leaf inet-gtp-tunnel-endpoint-identifier {
           type string;
         }
         leaf inet6-gtp-tunnel-endpoint-identifier {
           type string;
         }
         leaf gtp-header-offset-value {
           type int32;
         }
       }
       container inet6-packet-fields {
         leaf next-header {
           type string;
         }
         leaf source-l4-port {
           type string;
         }
         leaf destination-l4-port {
           type string;
         }
         leaf ipv6-source-addr {
           type string;
         }
         leaf ipv6-destination-addr {
           type string;
         }
         leaf flow-label {
           type string;
         }
         leaf vlan-id {
           type string;
         }
       }
       container mpls-rtag7-settings {
         container mpls-packet-fields {
           leaf source-port {
             type string;
           }
           leaf destination-port {
             type string;
           }
           leaf label {
             type string;
           }
           leaf ip-payload {
             type string;
           }
           leaf source-devcie {
             type string;
           }
           leaf destination-devcie {
             type string;
           }
         }
       }
       container hash-parameter-settings-ecmp {
         leaf hash-function {
           type string;
         }
         leaf hash-offset {
           type int32;
         }
         leaf hash-preprocess {
           type int32;
         }
       }
       container hash-parameter-settings-lag {
         leaf hash-function {
           type string;
         }
         leaf hash-offset {
           type int32;
         }
         leaf hash-preprocess {
           type int32;
         }
       }
       container vxlan-packet-fields {
         leaf vxlan-id {
           type string;
         }
       }
       container layer2-packet-fields {
         leaf source-mac-addr {
           type string;
         }
         leaf destination-mac-addr {
           type string;
         }
         leaf vlan-id {
           type string;
         }
         leaf inner-vlan-id {
           type string;
         }
         leaf incoming-port {
           type string;
         }
         leaf inner-source-mac {
           type string;
         }
         leaf inner-destination-mac {
           type string;
         }
         leaf inner-in-vlan {
           type string;
         }
         leaf inner-out-vlan {
           type string;
         }
       }
     }
   }
   grouping analyzer-block {
     list analyzer-information {
       leaf analyzer-name {
         type string;
         description
           "Name of the analyzer";
       }
       leaf analyzer-mirror-ratio {
         type uint32;
         description
           "Mirror ratio (for N, mirror 1 packet out of N)";
       }
       leaf analyzer-loss-priority {
         type string;
         description
           "Loss priority of the analyzer";
       }
       list analyzer-ingress-interface-list {
         leaf analyzer-ingress-interface-name {
           type string;
           description
             "Monitored ingress interface";
         }
       }
       list analyzer-egress-interface-list {
         leaf analyzer-egress-interface-name {
           type string;
           description
             "Monitored egress interface";
         }
       }
       list analyzer-ingress-vlan-list {
         leaf analyzer-ingress-vlan-name {
           type string;
           description
             "Monitored ingress VLAN";
         }
       }
       list analyzer-egress-vlan-list {
         leaf analyzer-egress-vlan-name {
           type string;
           description
             "Monitored egress VLAN";
         }
       }
       container analyzer-monitor {
         leaf analyzer-monitor-port {
           type string;
           description
             "Monitored interface";
         }
         leaf analyzer-monitor-vlan {
           type string;
           description
             "Monitored VLAN";
         }
         leaf analyzer-monitor-ipaddr {
           type jt:ipaddr;
           description
             "Monitored IP address";
         }
         leaf analyzer-monitor-erspan {
           type string;
           description
             "ERSPAN Destination IP Address";
         }
         leaf analyzer-monitor-erspan-src-addr {
           type string;
           description
             "ERSPAN Source IP Address";
         }
         leaf analyzer-monitor-erspan-dscp {
           type string;
           description
             "ERSPAN dscp value";
         }
         leaf analyzer-monitor-next-hop-group {
           type string;
           description
             "Monitored next hop group";
         }
         leaf analyzer-monitor-forwarding-class {
           type string;
           description
             "Analyzer forwarding class name";
         }
       }
       leaf analyzer-rate {
         type uint32;
         description
           "Mirror ratio (for N, mirror 1 packet out of N)";
       }
       leaf analyzer-max-pkt-len {
         type uint32;
         description
           "Maximum length of the mirrored packet";
       }
       leaf analyzer-output-state {
         type string;
         description
           "State of destination";
       }
       container analyzer-output-mirror-profile {
         leaf analyzer-output-mirror-profile-name {
           type string;
           description
             "Output Mirror Profile";
         }
       }
     }
   }
   grouping smpl-next-hop-group-block {
     list smpl-nhgroup {
       leaf smpl-nhgroup-name {
         type string;
         description
           "Name of the next-hop-group";
       }
       leaf smpl-nhgroup-type {
         type string;
         description
           "Type of the next-hop-group";
       }
       leaf smpl-nhgroup-state {
         type string;
         description
           "State of the next-hop-group";
       }
       leaf smpl-nhgroup-num-members-configured {
         type int32;
         description
           "Number of members interfaces that are configured";
       }
       leaf smpl-nhgroup-num-members-up {
         type int32;
         description
           "Number of members interfaces that are up";
       }
       leaf smpl-nhgroup-subgroups-configured {
         type int32;
         description
           "Number of subgroups that are configured";
       }
       leaf smpl-nhgroup-subgroups-up {
         type int32;
         description
           "Number of subgroups that are up";
       }
       leaf smpl-nhgroup-nhid-header {
         type string;
         description
           "Next-hop index header";
       }
       list smpl-nhgroup-subgroup {
         leaf smpl-nhgroup-nexthop-state {
           type string;
           description
             "State of the next-hop";
         }
         leaf smpl-nhgroup-name {
           type string;
           description
             "Name of the next-hop-group";
         }
         list smpl-subgroup-member-list {
           leaf smpl-nhgroup-member-interface {
             type string;
             description
               "Name of the next-hop-group member interface";
           }
           leaf smpl-nhgroup-nexthop-address {
             type string;
             description
               "Nexthop address of the next-hop-group member interface";
           }
           leaf smpl-nhgroup-nexthop-state {
             type string;
             description
               "State of the next-hop";
           }
           leaf smpl-nexthop-index {
             type string;
             description
               "Next-hop index value";
           }
         }
         leaf smpl-nhgroup-state {
           type string;
           description
             "State of the next-hop-group";
         }
         leaf smpl-nexthop-index {
           type string;
           description
             "Next-hop index value";
         }
         leaf smpl-subgroup-num-members-configured {
           type int32;
           description
             "Number of subgroup members interfaces that are configured";
         }
         leaf smpl-subgroup-num-members-up {
           type int32;
           description
             "Number of subgroup members interfaces that are up";
         }
         leaf smpl-nhgroup-nhid-header {
           type string;
           description
             "Next-hop index header";
         }
       }
       list smpl-nhgroup-member-list {
         leaf smpl-nhgroup-member-vlan {
           type string;
           description
             "Name of the next-hop-group member vlan";
         }
         leaf smpl-nhgroup-member-interface {
           type string;
           description
             "Name of the next-hop-group member interface";
         }
         leaf smpl-nhgroup-nexthop-address {
           type string;
           description
             "Nexthop address of the next-hop-group member interface";
         }
         leaf smpl-nhgroup-nexthop-state {
           type string;
           description
             "State of the next-hop";
         }
         leaf smpl-nexthop-index {
           type string;
           description
             "Next-hop index value";
         }
       }
     }
   }
   grouping smpl-port-mirroring-block {
     list smpl-port-mirroring-instance {
       leaf smpl-instance-name {
         type string;
         description
           "Name of the instance";
       }
       leaf smpl-instance-id {
         type int32;
         description
           "Instance identifier";
       }
       leaf smpl-instance-input-rate {
         type int32;
         description
           "Ratio of packets to be sampled (1 out of N)";
       }
       leaf smpl-instance-input-run-length {
         type int32;
         description
           "Number of samples after initial trigger";
       }
       leaf smpl-instance-input-maximum-packet-length {
         type int32;
         description
           "Maximum length of the mirrored packet";
       }
       leaf smpl-instance-nhid-header {
         type string;
         description
           "Next-hop index header";
       }
       leaf smpl-instance-state {
         type string;
         description
           "State of the instance";
       }
       list smpl-port-mirror-output-family-list {
         leaf smpl-output-family-name {
           type string;
           description
             "Family of the desintation";
         }
         leaf smpl-output-family-state {
           type string;
           description
             "State of desintation";
         }
         leaf smpl-output-family-destination {
           type string;
           description
             "Destination interface/group of the family";
         }
         leaf smpl-output-nexthop-address {
           type string;
           description
             "Nexthop address of the family";
         }
         leaf smpl-nexthop-index {
           type string;
           description
             "Next-hop index value";
         }
         leaf smpl-output-erspan-src-addr {
           type string;
           description
             "ERSPAN Source IP Address";
         }
         leaf smpl-output-erspan-dscp {
           type int32;
           description
             "ERSPAN dscp value";
         }
         leaf smpl-output-forwarding-class {
           type string;
           description
             "Port-mirror forwarding class name";
         }
         list smpl-nhgroup-member-list {
           leaf smpl-nhgroup-member-interface {
             type string;
             description
               "Name of the next-hop-group member interface";
           }
           leaf smpl-nhgroup-nexthop-address {
             type string;
             description
               "Nexthop address of the next-hop-group member interface";
           }
           leaf smpl-nexthop-index {
             type string;
             description
               "Next-hop index value";
           }
         }
       }
       list smpl-port-mirror-profile-output {
         leaf smpl-mirror-profile-name {
           type string;
           description
             "Name of the mirror-profile";
         }
         leaf smpl-output-mirror-type {
           type string;
           description
             "Type of the mirroring";
         }
         leaf smpl-output-observation-domain-id {
           type int32;
           description
             "Observation domain id";
         }
         leaf smpl-output-destination-routing-instance {
           type string;
           description
             "Routing-instance of the destination";
         }
         leaf smpl-output-family-state {
           type string;
           description
             "State of desintation";
         }
         leaf smpl-output-family-destination {
           type string;
           description
             "Destination interface/group of the family";
         }
         leaf smpl-output-l4-destination-port {
           type int32;
           description
             "UDP/TCP port of the collector";
         }
       }
     }
   }
   grouping smpl-port-mirroring-self-block {
     list smpl-port-mirroring-self-instance {
       leaf smpl-instance-name {
         type string;
         description
           "Name of the instance";
       }
       leaf smpl-instance-id {
         type int32;
         description
           "Instance identifier";
       }
       leaf smpl-instance-input-rate {
         type int32;
         description
           "Ratio of packets to be sampled (1 out of N)";
       }
       leaf smpl-instance-input-run-length {
         type int32;
         description
           "Number of samples after initial trigger";
       }
       leaf smpl-instance-input-maximum-packet-length {
         type int32;
         description
           "Maximum length of the mirrored packet";
       }
       leaf smpl-instance-state {
         type string;
         description
           "State of the instance";
       }
       list smpl-port-mirror-output-family-list {
       }
       list smpl-port-mirror-output-file-list {
         leaf smpl-family-name {
           type string;
           description
             "Instance family";
         }
         leaf smpl-start-time {
           type string;
           description
             "Start time of recording";
         }
         leaf smpl-duration {
           type string;
           description
             "Duration of recoring";
         }
         leaf smpl-stop-time {
           type string;
           description
             "Stop time of recording";
         }
         leaf smpl-actual-duration {
           type string;
           description
             "Actual recording time";
         }
         leaf smpl-file-name {
           type string;
           description
             "File name";
         }
         leaf smpl-file-size {
           type int32;
           description
             "User defined Size limit";
         }
         leaf smpl-mode {
           type string;
           description
             "Type of recording";
         }
         leaf smpl-run {
           type string;
           description
             "Recording state";
         }
         leaf smpl-packet-count {
           type int32;
           description
             "Number of packets captured";
         }
         leaf smpl-total-bytes-written {
           type int32;
           description
             "Size of packets captured";
         }
       }
     }
   }
   grouping mirror-profile-block {
     list mirror-profile-information {
       leaf mirror-profile-name {
         type string;
         description
           "Name of the mirror-profile";
       }
       leaf mirror-mtp-destination {
         type string;
         description
           "Mod Mtp Destination";
       }
       leaf mirror-mtp-routing-instance {
         type string;
         description
           "Mod MTP routing Instance";
       }
       leaf mirror-mtp-l4-port-num {
         type uint32;
         description
           "Mod Mtp L4 Port Number";
       }
       leaf mirror-observdomain-id {
         type uint32;
         description
           "Mod Observation domain Id";
       }
       leaf mirror-sample-rate {
         type uint32;
         description
           "Sample rate for mirror traffic";
       }
       list mirror-profile-mod {
         leaf mod-type {
           type string;
           description
             "Stateless or Statefull";
         }
         leaf mod-stage {
           type string;
           description
             "Ingress/Egress/MMU";
         }
         leaf mmu-sample-rate {
           type uint32;
           description
             "MMU sample rate";
         }
         leaf mmu-drop-reasons {
           type string;
           description
             "MMU drop reasons";
         }
       }
       list mirror-profile-lm {
         leaf latency-monitoring-mode {
           type string;
           description
             "Mode of flow latency monitoring";
         }
       }
     }
   }
   grouping mirror-on-drop-buffer-stats-block {
     leaf mod-pool-buffer {
       type uint32;
       description
         "Allocated buffer for MOD";
     }
     leaf mod-dropped-pkts {
       type uint32;
       description
         "MOD dropped packets";
     }
     leaf mod-mirrored-pkts {
       type uint32;
       description
         "MOD Mirrored Packets";
     }
     leaf mod-pool-bytes-current {
       type uint32;
       description
         "MOD buffer usage in bytes";
     }
   }
 }
