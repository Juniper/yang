module junos-genstate-dynamic-tunnels-information {
   yang-version 1;
   namespace "http://yang.juniper.net/junos/genstate/dynamic-tunnels-information";
   prefix jgdti;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for dynamic-tunnels-information.

      Copyright (c) 2026 Juniper Networks, Inc.
      All rights reserved.";

   revision 2026-01-01 {
     description "Junos: 26.2R1.7";
   }

   grouping dynamic-tunnels-information-top {
     description
       "Top-level grouping";
     container dynamic-tunnels-information {
       description
         "Top-level container";
       container dynamic-tunnel-statistics {
         leaf dyn-total-count {
           type int32;
         }
         leaf dyn-ifl-type {
           type empty;
         }
         leaf dyn-tunnel-mode-gre {
           type string;
         }
         leaf dyn-total-count-ifl {
           type int32;
         }
         leaf dyn-up-count-ifl {
           type int32;
         }
         leaf dyn-down-count-ifl {
           type int32;
         }
         leaf dyn-total-count-gre-nhb {
           type int32;
         }
         leaf dyn-up-count-gre-nhb {
           type int32;
         }
         leaf dyn-down-count-gre-nhb {
           type string;
         }
         leaf dyn-rsvp-auto {
           type empty;
         }
         leaf dyn-total-count-rsvp {
           type int32;
         }
         leaf dyn-spring-te {
           type empty;
         }
         leaf dyn-total-count-spring-te {
           type uint32;
         }
         leaf dyn-up-count-spring-te {
           type uint32;
         }
         leaf dyn-down-count-spring-te {
           type uint32;
         }
         leaf dyn-nhb-udp {
           type empty;
         }
         leaf dyn-total-count-udp-nhb {
           type int32;
         }
         leaf dyn-up-count-udp-nhb {
           type int32;
         }
         leaf dyn-down-count-udp-nhb {
           type string;
         }
         leaf dyn-nhb-ipip {
           type empty;
         }
         leaf dyn-total-count-ipip-nhb {
           type int32;
         }
         leaf dyn-up-count-ipip-nhb {
           type int32;
         }
         leaf dyn-down-count-ipip-nhb {
           type string;
         }
         leaf dyn-nhb-gre-ip6 {
           type empty;
         }
         leaf dyn-tunnel-mode-gre-ip6 {
           type string;
         }
         leaf dyn-total-count-gre-ip6-ifl {
           type int32;
         }
         leaf dyn-up-count-gre-ip6-ifl {
           type int32;
         }
         leaf dyn-down-count-gre-ip6-ifl {
           type string;
         }
         leaf dyn-total-count-gre-ip6-nhb {
           type int32;
         }
         leaf dyn-up-count-gre-ip6-nhb {
           type int32;
         }
         leaf dyn-down-count-gre-ip6-nhb {
           type string;
         }
         leaf dyn-nhb-udp-ip6 {
           type empty;
         }
         leaf dyn-total-count-udp-ip6-nhb {
           type int32;
         }
         leaf dyn-up-count-udp-ip6-nhb {
           type int32;
         }
         leaf dyn-down-count-udp-ip6-nhb {
           type string;
         }
         leaf dyn-nhb-ipip-ip6 {
           type empty;
         }
         leaf dyn-total-count-ipip-ip6-nhb {
           type int32;
         }
         leaf dyn-up-count-ipip-ip6-nhb {
           type int32;
         }
         leaf dyn-down-count-ipip-ip6-nhb {
           type string;
         }
         leaf dyn-nhb-srv6 {
           type empty;
         }
         leaf dyn-total-count-srv6-nhb {
           type int32;
         }
         leaf dyn-up-count-srv6-nhb {
           type int32;
         }
         leaf dyn-down-count-srv6-nhb {
           type int32;
         }
       }
       list dynamic-tunnel-encap-pkt-stats {
         key "tunnel-encap-str-terse";
         leaf tunnel-encap-str-terse {
           type string;
           description
             "Tunnel encapsulation strings";
         }
         leaf tunnel-encap-pkts-terse {
           type uint64;
           description
             "Outgoing traffic packets on the tunnel";
         }
         leaf tunnel-encap-bytes-terse {
           type uint64;
           description
             "Outgoing traffic bytes on the tunnel";
         }
         leaf tunnel-encap-info-terse {
           type string;
           description
             "Tunnel information";
         }
       }
       list dynamic-tunnel-table {
         key "table-name";
         leaf table-name {
           type string;
           description
             "Unicast routing table";
         }
         list destination-network {
           key "prefix";
           leaf prefix {
             type jt:ipaddr;
           }
           leaf destination-network-deleted {
             type empty;
             description
               "Whether this destination network has been unconfigured";
           }
           list dynamic-tunnel {
             key "tunnel-destination";
             leaf tunnel-destination {
               type jt:ipaddr;
               description
                 "Tunnel destination";
             }
             leaf tunnel-state {
               type string;
               description
                 "State of the tunnel";
             }
             leaf tunnel-expiry {
               type int32;
               description
                 "Time after which the tunnel will be removed";
             }
             leaf tunnel-reference-count {
               type int32;
               description
                 "Number of references on this tunnel";
             }
             leaf tunnel-aggr-traffic-stats-str {
               type empty;
             }
             leaf tunnel-aggr-traffic-encap-str {
               type string;
               description
                 "Aggregate traffic statistics encap info.";
             }
             leaf tunnel-aggr-traffic-stats {
               type string;
               description
                 "Nexthop based tunnel out-going aggregate traffic 
                 statistics";
             }
             list tunnel-nexthop {
               key "tunnel-nh-type";
               leaf tunnel-nh-type {
                 type string;
                 description
                   "Type of next hop";
               }
               leaf tunnel-nh-subtype {
                 type string;
                 description
                   "Tunnel Subtype";
               }
               leaf via {
                 type string;
                 description
                   "Reachable via a local interface";
               }
               leaf tunnel-nh-info {
                 type string;
                 description
                   "Nexthop information";
               }
               leaf tunnel-nh-src {
                 type jt:ipaddr;
                 description
                   "Source address for this tunnel next hop";
               }
               leaf tunnel-id-index {
                 type int32;
                 description
                   "Tunnel Index";
               }
               leaf tunnel-gre-key {
                 type int32;
                 description
                   "RFC 2890 GRE Key applied via export policy";
               }
               leaf tunnel-attr-anchor-pfe {
                 type string;
                 description
                   "TCNH localized PFE name";
               }
               leaf tunnel-attr-vpn-label {
                 type string;
                 description
                   "VPN label for L3VPN over dynamic tunnel";
               }
               leaf tunnel-attr-reference-count {
                 type int32;
                 description
                   "Number of references on this tunnel-attr";
               }
               leaf tunnel-forwarding-ingress-route {
                 type string;
                 description
                   "Forwarding nexthop information for nexthop based tunnel";
               }
               leaf tunnel-endpoint-forwarding-ingress-route {
                 type string;
                 description
                   "Forwarding nexthop information for nexthop based tunnel";
               }
               leaf tunnel-traffic-stats {
                 type string;
                 description
                   "Nexthop based tunnel out-going traffic statistics";
               }
               leaf tunnel-nh-state {
                 type string;
                 description
                   "State of the tunnel next hop";
               }
               leaf tunnel-nh-reason {
                 type string;
                 description
                   "Reason why the tunnel next hop is not up";
               }
               leaf tunnel-nh-lsp-name {
                 type string;
                 description
                   "Name of the LSP nexthop of this tunnel";
               }
             }
           }
           list dynamic-tunnel-terse {
             key "tunnel-dest-terse";
             leaf tunnel-dest-terse {
               type jt:ipaddr;
             }
             leaf tunnel-src-terse {
               type jt:ipaddr;
             }
             leaf tunnel-nh-terse {
               type string;
             }
             leaf tunnel-type-terse {
               type string;
             }
             leaf tunnel-state-terse {
               type string;
             }
             leaf tunnel-nh-reason-terse {
               type string;
             }
           }
         }
       }
     }
   }
   augment "/jgs:genstate" {
     description
       "Adds dynamic-tunnels-information container to top-level genstate 
       container";
     uses dynamic-tunnels-information-top;
   }
 }
