module junos-genstate-isis-authentication-information {
   yang-version 1;
   namespace "http://yang.juniper.net/junos/genstate/isis-authentication-information";
   prefix jgiai;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for isis-authentication-information.

      Copyright (c) 2026 Juniper Networks, Inc.
      All rights reserved.";

   revision 2026-01-01 {
     description "Junos: 26.2R1.7";
   }

   grouping isis-authentication-information-top {
     description
       "Top-level grouping";
     container isis-authentication-information {
       description
         "ISIS authentication information";
       list isis-interface-authentication {
         key "interface-name";
         leaf interface-name {
           type string;
           description
             "Name of interface";
         }
         list isis-interface-level-authentication {
           key "level";
           leaf level {
             type int32;
             description
               "IS-IS Level";
           }
           leaf isis-interface-level-iih-authentication {
             type string;
             description
               "Authentication type for IIH packets";
           }
           leaf isis-interface-level-csn-authentication {
             type string;
             description
               "Authentication type for CSN packets";
           }
           leaf isis-interface-level-psn-authentication {
             type string;
             description
               "Authentication type for PSN packets";
           }
         }
       }
       list isis-lsp-authentication {
         key "level";
         description
           "Authentication type for LSP packets";
         leaf level {
           type int32;
           description
             "IS-IS Level";
         }
         leaf isis-level-lsp-authentication {
           type string;
           description
             "Authentication type for LSP packets";
         }
       }
     }
   }
   augment "/jgs:genstate" {
     description
       "Adds isis-authentication-information container to top-level genstate
       container";
     uses isis-authentication-information-top;
   }
 }
