module junos-genstate-krt-state-information {
   yang-version 1;
   namespace "http://yang.juniper.net/junos/genstate/krt-state-information";
   prefix jgksi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for krt-state-information.

      Copyright (c) 2026 Juniper Networks, Inc.
      All rights reserved.";

   revision 2026-01-01 {
     description "Junos: 26.2R1.7";
   }

   grouping krt-state-information-top {
     description
       "Top-level grouping";
     container krt-state-information {
       description
         "Top-level container";
       leaf krt-fib-state {
         type string;
       }
       leaf krt-options {
         type string;
         description
           "Kernel routing table options";
       }
       leaf krt-re-mode {
         type string;
       }
       leaf krt-block-count {
         type int32;
       }
       leaf krt-unblock-count {
         type int32;
       }
       leaf krt-install-job-not-running {
         type empty;
       }
       leaf krt-install-job-state {
         type string;
       }
       leaf krt-install-job-priority {
         type string;
       }
       leaf rtsock-time-until-next-scan {
         type string;
         description
           "Time until next scan for kernel routing table routing socket 
           lossage";
       }
       leaf krt-mcnh-delete-defer-timeout {
         type int32;
       }
       container krt-io-tx-job-state {
         leaf krt-io-tx-job-running {
           type empty;
           description
             "KRT io tx job is running";
         }
         leaf krt-io-tx-job-not-running {
           type empty;
           description
             "KRT io tx job is not running";
         }
       }
       container krt-queue-state {
         leaf krtq-operations-queued {
           type int32;
           description
             "Number of queued operations";
         }
         leaf krtq-rt-table-adds {
           type int32;
           description
             "Number of routing table additions";
         }
         leaf krtq-interface-routes {
           type int32;
           description
             "Number of queued interface routes";
         }
         leaf krtq-high-multicast-adds-changes {
           type int32;
           description
             "Number of queued high-priority multicast additions and changes";
         }
         leaf krtq-indirect-adds-changes {
           type int32;
           description
             "Number of queued indirect next-hop additions and changes";
         }
         leaf krtq-indirect-deletes {
           type int32;
           description
             "Number of queued indirect next-hop deletions";
         }
         leaf krtq-high-mpls-adds {
           type int32;
           description
             "Number of queued high-priority MPLS additions";
         }
         leaf krtq-high-mpls-changes {
           type int32;
           description
             "Number of queued high-priority MPLS changes";
         }
         leaf krtq-high-priority-adds {
           type int32;
           description
             "Number of queued high-priority additions";
         }
         leaf krtq-high-priority-changes {
           type int32;
           description
             "Number of queued high-priority changes";
         }
         leaf krtq-high-priority-deletes {
           type int32;
           description
             "Number of queued high-priority deletions";
         }
         leaf krtq-normal-priority-indirects {
           type int32;
           description
             "Number of queued normal-priority indirect next-hops";
         }
         leaf krtq-normal-priority-adds {
           type int32;
           description
             "Number of queued normal-priority additions";
         }
         leaf krtq-normal-priority-changes {
           type int32;
           description
             "Number of queued normal-priority changes";
         }
         leaf krtq-normal-priority-deletes {
           type int32;
           description
             "Number of queued normal-priority deletions";
         }
         leaf krtq-rt-table-deletes {
           type int32;
           description
             "Number of queued routing table deletions";
         }
         leaf krtq-normal-priority-gmp {
           type int32;
           description
             "Number of queued normal-priority GMP objects";
         }
         leaf krtq-operations-deferred {
           type int32;
           description
             "Number of deferred operations";
         }
         leaf krtq-operations-canceled {
           type int32;
           description
             "Number of canceled operations";
         }
         leaf krtq-async-count {
           type int32;
           description
             "Number of async queue entry";
         }
         leaf krtq-async-non-q-count {
           type int32;
           description
             "Number of async non queue entry";
         }
         leaf krtq-time-until-next-run {
           type string;
           description
             "Time until queue next runs";
         }
         leaf krtq-kernel-rt-learnt {
           type int32;
           description
             "Number of routes learned from kernel";
         }
         leaf krtq-top-indirect-adds-changes {
           type int32;
           description
             "Number of queued prioritized indirect next-hop additions and 
             changes";
         }
         leaf krtq-top-priority-deletes {
           type int32;
           description
             "Number of queued top-priority deletions";
         }
         leaf krtq-top-priority-changes {
           type int32;
           description
             "Number of queued top-priority changes";
         }
         leaf krtq-top-priority-adds {
           type int32;
           description
             "Number of queued top-priority adds";
         }
         leaf krtq-least-priority-deletes {
           type int32;
           description
             "Number of queued least-priority deletions";
         }
         leaf krtq-least-priority-changes {
           type int32;
           description
             "Number of queued least-priority changes";
         }
         leaf krtq-least-priority-adds {
           type int32;
           description
             "Number of queued least-priority adds";
         }
         leaf krtq-normal-priority-cnh-deletes {
           type int32;
           description
             "Number of queued normal-priority composite nexthop deletions";
         }
       }
       container krt-dfwd-connection-state {
         leaf krt-dfwd-connection-status {
           type string;
           description
             "Show the status of dfwd connection establishment";
         }
         leaf krt-dfwd-connection-timestamp {
           type int32;
           description
             "Time between the first retry and connection establishment";
         }
       }
     }
   }
   augment "/jgs:genstate" {
     description
       "Adds krt-state-information container to top-level genstate container";
     uses krt-state-information-top;
   }
 }
