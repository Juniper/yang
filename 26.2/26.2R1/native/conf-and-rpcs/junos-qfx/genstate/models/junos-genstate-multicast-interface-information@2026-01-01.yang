module junos-genstate-multicast-interface-information {
   yang-version 1;
   namespace "http://yang.juniper.net/junos/genstate/multicast-interface-information";
   prefix jgmii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-interface-information.

      Copyright (c) 2026 Juniper Networks, Inc.
      All rights reserved.";

   revision 2026-01-01 {
     description "Junos: 26.2R1.7";
   }

   grouping multicast-interface-information-top {
     description
       "Top-level grouping";
     container multicast-interface-information {
       description
         "Information about one or more multicast interfaces";
       list multicast-interface {
         key "interface-name";
         description
           "Information about a multicast interface";
         leaf interface-name {
           type string;
           description
             "Name of interface";
         }
         leaf interface-max-bandwidth {
           type uint64;
           description
             "Maximum bandwidth for multicast flows";
         }
         leaf interface-local-bandwidth-deduction {
           type int64;
           description
             "Bandwidth deduction for local multicast flows";
         }
         leaf interface-mapped-bandwidth-deduction {
           type int64;
           description
             "Bandwidth deduction for mapped multicast flows";
         }
         leaf interface-remaining-bandwidth {
           type int64;
           description
             "Remaining bandwidth for multicast flows";
         }
         leaf interface-reverse-oif-mapping {
           type string;
           description
             "Reverse OIF mapping is enabled";
         }
         leaf interface-reverse-oif-mapping-no-qos-adjust {
           type string;
           description
             "Reverse OIF mapping no QoS adjust is enabled";
         }
         leaf interface-subscriber-leave-timer {
           type uint32;
           description
             "Bw restore waiting time after subscriber leaves group";
         }
         leaf interface-no-qos-adjust {
           type string;
           description
             "Interface no QoS adjustment is enabled";
         }
       }
     }
   }
   augment "/jgs:genstate" {
     description
       "Adds multicast-interface-information container to top-level genstate
       container";
     uses multicast-interface-information-top;
   }
 }
