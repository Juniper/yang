module junos-genstate-msdp-peer-information {
   yang-version 1;
   namespace "http://yang.juniper.net/junos/genstate/msdp-peer-information";
   prefix jgmpi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for msdp-peer-information.

      Copyright (c) 2026 Juniper Networks, Inc.
      All rights reserved.";

   revision 2026-01-01 {
     description "Junos: 26.2R1.7";
   }

   grouping msdp-peer-information-top {
     description
       "Top-level grouping";
     container msdp-peer-information {
       description
         "Top-level container";
       list msdp-peer {
         key "msdp-peer-address";
         leaf msdp-peer-address {
           type jt:ipaddr;
         }
         leaf msdp-local-address {
           type jt:ipaddr;
         }
         leaf msdp-state {
           type string;
         }
         leaf msdp-state-change {
           type string;
         }
         leaf msdp-group-name {
           type string;
         }
         leaf msdp-sa-accepted {
           type int32;
           description
             "Number of SAs accepted from peer";
         }
         leaf msdp-sa-received {
           type int32;
           description
             "Number of SAs received from peer";
         }
         leaf msdp-active-source-limit-exceeded {
           type int32;
         }
         leaf msdp-connect-retries {
           type int32;
         }
         leaf msdp-state-timeout {
           type int32;
         }
         leaf msdp-peer-timeout {
           type int32;
         }
         leaf msdp-active-source-limit-maximum {
           type uint32;
         }
         leaf msdp-active-source-limit-threshold {
           type uint32;
         }
         leaf msdp-active-source-limit-log-warning {
           type uint32;
         }
         leaf msdp-active-source-limit-log-interval {
           type uint32;
         }
       }
     }
   }
   augment "/jgs:genstate" {
     description
       "Adds msdp-peer-information container to top-level genstate container";
     uses msdp-peer-information-top;
   }
 }
