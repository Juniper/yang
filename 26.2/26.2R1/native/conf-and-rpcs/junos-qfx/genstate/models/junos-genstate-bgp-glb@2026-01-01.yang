module junos-genstate-bgp-glb {
   yang-version 1;
   namespace "http://yang.juniper.net/junos/genstate/bgp-glb";
   prefix jgbg;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bgp-glb.

      Copyright (c) 2026 Juniper Networks, Inc.
      All rights reserved.";

   revision 2026-01-01 {
     description "Junos: 26.2R1.7";
   }

   grouping bgp-glb-top {
     description
       "Top-level grouping";
     container bgp-glb {
       description
         "BGP global load balancing";
       leaf bgp-glb-state {
         type string;
       }
       leaf bgp-glb-role {
         type string;
       }
       leaf bgp-glb-hw-profiles {
         type uint32;
       }
       leaf bgp-glb-shared-hw-profiles {
         type uint32;
       }
       leaf bgp-glb-unshared-hw-profiles {
         type uint32;
       }
       leaf bgp-glb-pending-eval-profiles {
         type uint32;
       }
       leaf bgp-glb-profile-limit-eval-profiles {
         type uint32;
       }
       leaf bgp-glb-profile-space-others-eval-profiles {
         type uint32;
       }
       container bgp-glb-profile-sharing {
         description
           "Profile sharing related options";
         leaf bgp-glb-profile-sharing-state {
           type string;
         }
         container bgp-glb-profile-sharing-except {
           leaf except-aspath-length {
             type uint32;
           }
           leaf except-policy {
             type string;
           }
         }
       }
       list bgp-glb-profile-space {
         key "bgp-glb-profile-space-name";
         leaf bgp-glb-profile-space-name {
           type string;
         }
         leaf bgp-glb-profile-space-id {
           type uint32;
         }
         leaf bgp-glb-profile-space-unalloc-bits {
           type string;
         }
         leaf bgp-glb-profile-space-max-hw-id {
           type string;
         }
       }
       list bgp-glb-path {
         key "bgp-glb-path-id";
         leaf bgp-glb-path-id {
           type uint32;
         }
         leaf bgp-glb-path-ifindex {
           type int32;
         }
         leaf bgp-glb-path-nh-node-id {
           type jt:ipaddr;
         }
       }
       list bgp-glb-path-monitor {
         key "bgp-glb-path-monitor-ifindex bgp-glb-path-monitor-local-node-id bgp-glb-path-monitor-remote-node-id";
         leaf bgp-glb-path-monitor-ifindex {
           type int32;
         }
         leaf bgp-glb-path-monitor-local-node-id {
           type jt:ipaddr;
         }
         leaf bgp-glb-path-monitor-remote-node-id {
           type jt:ipaddr;
         }
       }
       list bgp-glb-profile {
         key "bgp-glb-profile-id";
         leaf bgp-glb-profile-pointer {
           type string;
         }
         leaf bgp-glb-profile-id {
           type uint32;
         }
         leaf bgp-glb-profile-lookahead-count {
           type uint32;
         }
         leaf bgp-glb-profile-lookahead-list {
           type empty;
         }
         leaf bgp-glb-profile-lookahead-unalloc-list {
           type empty;
         }
         leaf bgp-glb-profile-nnh-node-id {
           type jt:ipaddr;
         }
         leaf bgp-glb-profile-space-name {
           type string;
         }
         leaf bgp-glb-profile-space-id {
           type uint32;
         }
         leaf bgp-glb-profile-hw-id {
           type uint32;
         }
         leaf bgp-glb-profile-path-count {
           type uint32;
         }
         leaf bgp-glb-profile-path-list {
           type empty;
         }
         leaf bgp-glb-profile-path-unalloc-list {
           type empty;
         }
         list bgp-glb-profile-lookahead-entry {
           key "bgp-glb-profile-lookahead-profile-id";
           leaf bgp-glb-profile-lookahead-profile-id {
             type uint32;
           }
           leaf bgp-glb-profile-lookahead-profile-nnh-node-id {
             type jt:ipaddr;
           }
           leaf bgp-glb-profile-lookahead-profile-space-id {
             type uint32;
           }
           leaf bgp-glb-profile-lookahead-profile-hw-id {
             type uint32;
           }
         }
         list bgp-glb-profile-lookahead-unalloc-entry {
           key "bgp-glb-profile-lookahead-profile-nnh-node-id";
           leaf bgp-glb-profile-lookahead-profile-nnh-node-id {
             type jt:ipaddr;
           }
           leaf bgp-glb-profile-lookahead-profile-space-id {
             type uint32;
           }
           leaf bgp-glb-profile-lookahead-profile-hw-id {
             type uint32;
           }
         }
         list bgp-glb-profile-path-entry {
           key "bgp-glb-profile-path-id";
           leaf bgp-glb-profile-path-id {
             type uint32;
           }
           leaf bgp-glb-profile-path-ifindex {
             type uint32;
           }
           leaf bgp-glb-profile-path-nh-node-id {
             type jt:ipaddr;
           }
           leaf bgp-glb-profile-path-refcnt {
             type uint32;
           }
         }
         list bgp-glb-profile-path-unalloc-entry {
           key "bgp-glb-profile-path-ifindex bgp-glb-profile-path-nh-node-id";
           leaf bgp-glb-profile-path-ifindex {
             type uint32;
           }
           leaf bgp-glb-profile-path-nh-node-id {
             type jt:ipaddr;
           }
           leaf bgp-glb-profile-path-refcnt {
             type uint32;
           }
         }
       }
     }
   }
   augment "/jgs:genstate" {
     description
       "Adds bgp-glb container to top-level genstate container";
     uses bgp-glb-top;
   }
 }
