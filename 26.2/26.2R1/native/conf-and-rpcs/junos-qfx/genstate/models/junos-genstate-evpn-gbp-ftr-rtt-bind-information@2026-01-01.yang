module junos-genstate-evpn-gbp-ftr-rtt-bind-information {
   yang-version 1;
   namespace "http://yang.juniper.net/junos/genstate/evpn-gbp-ftr-rtt-bind-information";
   prefix jgegfrbi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for evpn-gbp-ftr-rtt-bind-information.

      Copyright (c) 2026 Juniper Networks, Inc.
      All rights reserved.";

   revision 2026-01-01 {
     description "Junos: 26.2R1.7";
   }

   grouping evpn-gbp-ftr-rtt-bind-information-top {
     description
       "Top-level grouping";
     container evpn-gbp-ftr-rtt-bind-information {
       description
         "Top-level container";
       list evpn-gbptagdb-filter-rtt-bind {
         key "evpn-filter-bind-name";
         leaf evpn-filter-name {
           type string;
         }
         leaf evpn-filter-bind-type {
           type string;
         }
         leaf evpn-filter-bind-name {
           type string;
         }
       }
     }
   }
   augment "/jgs:genstate" {
     description
       "Adds evpn-gbp-ftr-rtt-bind-information container to top-level 
       genstate container";
     uses evpn-gbp-ftr-rtt-bind-information-top;
   }
 }
