module junos-genstate-mld-snooping-evpn-proxy-information-root {
   yang-version 1;
   namespace "http://yang.juniper.net/junos/genstate/mld-snooping-evpn-proxy-information-root";
   prefix jgmsepir;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mld-snooping-evpn-proxy-information-root.

      Copyright (c) 2026 Juniper Networks, Inc.
      All rights reserved.";

   revision 2026-01-01 {
     description "Junos: 26.2R1.7";
   }

   grouping mld-snooping-evpn-proxy-information-root-top {
     description
       "Top-level grouping";
     container mld-snooping-evpn-proxy-information-root {
       description
         "Top-level container";
       leaf mld-snooping-evpn-proxy-information-banner {
         type empty;
         description
           "The banner before the show command";
       }
       list mld-snooping-evpn-proxy-information-per-instance {
         key "instance-name";
         leaf instance-name {
           type string;
         }
         list mld-snooping-evpn-proxy-information-per-ld {
           key "evpn-bridge-domain";
           leaf evpn-bridge-domain {
             type string;
           }
           leaf vlan-id {
             type int32;
           }
           leaf vni-id {
             type int32;
           }
           list evpn-source-group-proxy {
             key "proxy-group-ip";
             leaf proxy-group-ip {
               type jt:ipaddr;
             }
             leaf proxy-source-ip {
               type jt:ipaddr;
             }
             leaf proxy-local-adv {
               type string;
             }
             leaf proxy-remote-adv {
               type string;
             }
             leaf proxy-flags {
               type string;
             }
           }
         }
       }
     }
   }
   augment "/jgs:genstate" {
     description
       "Adds mld-snooping-evpn-proxy-information-root container to top-level
       genstate container";
     uses mld-snooping-evpn-proxy-information-root-top;
   }
 }
