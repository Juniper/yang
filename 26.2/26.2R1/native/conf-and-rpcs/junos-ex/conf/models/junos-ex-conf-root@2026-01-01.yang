/*
 * Copyright (c) 2026 Juniper Networks, Inc.
 * All rights reserved.
 */
 module junos-ex-conf-root {
   namespace "http://yang.juniper.net/junos-ex/conf/root";

   prefix jc;

   import junos-common-types {
     prefix jt;
     revision-date 2026-01-01;
   }

   organization "Juniper Networks, Inc.";

   contact "yang-support@juniper.net";

   description "Junos YANG module for configuration hierarchies.";

   revision 2026-01-01 {
     description "Junos: 26.2R1.7";
   }

   container configuration {
     config true;
     uses juniper-config;
     list groups {
       key name;
       ordered-by user;
       description "Configuration groups";
       uses juniper-group;
     }
   }
   grouping juniper-config {
     leaf rcsid {
       description "Revision control system identifier";
       type string;
     }
     leaf version {
       description "Software version information";
       type string;
     }
     leaf-list apply-groups {
       ordered-by user;
       description "Groups from which to inherit configuration data";
       type string;
     }
     list apply-macro {
       key name;
       ordered-by user;
       description "Macro and parameters for commit script expansion";
       uses apply-macro-type;
     }
     list logical-systems {
       key name;
       description "Logical systems";
       uses juniper-logical-system;
     }
     container chassis {
       description "Chassis configuration";
       uses chassis_type;
     }
     container services {
       description "System services";
       uses apply-advanced;
       container inband-flow-telemetry {
         presence "enable inband-flow-telemetry";
         description "Inband telemetry services";
         uses apply-advanced;
         container traceoptions {
           presence "enable traceoptions";
           description "Inband telemetry trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container device-id {
           description "Inband telemetry global unique identifier";
           uses apply-advanced;
           choice device_id_choice {
             case case_1 {
               leaf auto {
                 description "Device router-id will be considered";
                 type empty;
               }
             }
             case case_2 {
               leaf id {
                 description "Specify unique device identifier";
                 type union {
                   type string {
                     pattern "<.*>|$.*";
                   }
                   type uint32 {
                     range "1 .. 1048575";
                   }
                 }
               }
             }
           }
         }
         leaf meta-data-stack-length {
           description "Maximum length for meta data";
           default "240";
           type union {
             type string {
               pattern "<.*>|$.*";
             }
             type uint32 {
               range "8 .. 255";
             }
           }
         }
         leaf hop-limit {
           description "Maximum hop limits allowed";
           default "250";
           type union {
             type string {
               pattern "<.*>|$.*";
             }
             type uint32 {
               range "1 .. 250";
             }
           }
         }
         leaf mode {
           description "Configure IFA initiator mode type";
           type enumeration {
             enum "live" {
               description "IFA Metadata insertion in the live or inband packet";
             }
             enum "probe" {
               description "IFA Metadata insertion in the probe or clone packet";
             }
           }
         }
         leaf flow-type {
           description "Configure IFA traffic type";
           type enumeration {
             enum "l3" {
               description "L3 traffic type";
             }
             enum "vxlan" {
               description "Vxlan traffic type";
             }
           }
         }
         leaf no-ipv6-address-match {
           description "Configure if no ipv6 address match is used";
           type empty;
         }
         leaf clock-source {
           description "Configure clock source for timestamping";
           type enumeration {
             enum "ntp" {
               description "Use Network Time Protocol";
             }
             enum "ptp" {
               description "Use Precision Time Protocol";
             }
           }
         }
         list profile {
           key name;
           description "Profile options";
           max-elements 32;
           uses inband-telemetry-profile-type;
         }
       }
       container pfe {
         presence "enable pfe";
         uses apply-advanced;
         container traffic {
           presence "enable traffic";
           description "PFE traffic monitor services";
           uses apply-advanced;
           container traceoptions {
             presence "enable traceoptions";
             description "PFE Monitor trace options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 units "bytes";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
           }
           container monitor-timer {
             presence "enable monitor-timer";
             description "PFE monitor timer to uninstall the filter";
             uses apply-advanced;
             leaf time {
               description "Default is 5 mins, max configurable time is 60 mins";
               default "300";
               units "seconds";
               type union {
                 type string {
                   pattern "<.*>|$.*";
                 }
                 type uint32 {
                   range "300 .. 3600";
                 }
               }
             }
           }
         }
       }
       container rpm {
         presence "enable rpm";
         description "Real-time performance monitoring";
         uses apply-advanced;
         container traceoptions {
           description "RMOPD trace options";
           uses rmopd-traceoptions;
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
                 mandatory true;
               }
               choice target-type {
                 case case_1 {
                   container target {
                     presence "enable target";
                     description "Target address generation for scale test config";
                     uses apply-advanced;
                     leaf address-base {
                       description "Base address of target host in a.b.c.d format";
                       type jt:ipv4addr;
                       mandatory true;
                     }
                     leaf step {
                       description "Steps to increment target address in a.b.c.d format";
                       type jt:ipv4addr;
                       mandatory true;
                     }
                     leaf count {
                       description "Target address count";
                       type union {
                         type string {
                           pattern "<.*>|$.*";
                         }
                         type uint32 {
                           range "1 .. 500000";
                         }
                       }
                       mandatory true;
                     }
                   }
                 }
                 case case_2 {
                   container target-inet6 {
                     presence "enable target-inet6";
                     description "IPv6 target address generation for scale test config";
                     uses apply-advanced;
                     leaf address-base {
                       description "Base address of target host in a:b:c:d:e:f:g:h format";
                       type jt:ipv6addr;
                       mandatory true;
                     }
                     leaf step {
                       description "Steps to increment target address in a:b:c:d:e:f:g:h format";
                       type jt:ipv6addr;
                       mandatory true;
                     }
                     leaf count {
                       description "Target address count";
                       type union {
                         type string {
                           pattern "<.*>|$.*";
                         }
                         type uint32 {
                           range "1 .. 500000";
                         }
                       }
                       mandatory true;
                     }
                   }
                 }
               }
               choice source-type {
                 case case_1 {
                   container source {
                     presence "enable source";
                     description "Source address generation in scale tests";
                     uses apply-advanced;
                     leaf address-base {
                       description "Base address of host in a.b.c.d format";
                       type jt:ipv4addr;
                       mandatory true;
                     }
                     leaf step {
                       description "Steps to increment src address in a.b.c.d format";
                       type jt:ipv4addr;
                       mandatory true;
                     }
                     leaf count {
                       description "Source-address count";
                       type union {
                         type string {
                           pattern "<.*>|$.*";
                         }
                         type uint32 {
                           range "1 .. 500000";
                         }
                       }
                       mandatory true;
                     }
                   }
                 }
                 case case_2 {
                   container source-inet6 {
                     presence "enable source-inet6";
                     description "IPv6 source address generation in scale tests";
                     uses apply-advanced;
                     leaf address-base {
                       description "Base address of host in a:b:c:d:e:f:g:h format";
                       type jt:ipv6addr;
                       mandatory true;
                     }
                     leaf step {
                       description "Steps to increment src address in a:b:c:d:e:f:g:h format";
                       type jt:ipv6addr;
                       mandatory true;
                     }
                     leaf count {
                       description "Source-address count";
                       type union {
                         type string {
                           pattern "<.*>|$.*";
                         }
                         type uint32 {
                           range "1 .. 500000";
                         }
                       }
                       mandatory true;
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                   mandatory true;
                 }
                 leaf subunit-cnt {
                   description "Subunit count for destination interface for scale test";
                   type union {
                     type string {
                       pattern "<.*>|$.*";
                     }
                     type uint32 {
                       range "1 .. 500000";
                     }
                   }
                   mandatory true;
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     type jt:ipv4addr;
                   }
                 }
                 case case_2 {
                   leaf inet6-address {
                     description "Inet6 Address of target host";
                     type jt:ipv6addr;
                   }
                 }
                 case case_3 {
                   leaf url {
                     description "Fully formed target URL";
                     type string;
                   }
                 }
                 case case_4 {
                   leaf inet6-url {
                     description "Fully formed target IPV6 URL";
                     type string;
                   }
                 }
                 case case_5 {
                   leaf fqdn {
                     description "FQDN for IPV4 target address";
                     type string;
                   }
                 }
                 case case_6 {
                   leaf fqdnv6 {
                     description "FQDN for IPV6 target address";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               type jt:ipv4addr;
             }
             leaf routing-instance {
               description "Routing instance used by probes";
               type string {
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 512";
                 }
               }
             }
             leaf dscp-code-points {
               description "Differentiated Services code point bits or alias";
               default "000000";
               type string {
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf one-way-hardware-timestamp {
               description "Enable hardware timestamps for one-way measurements";
               type empty;
             }
             leaf next-hop {
               description "Next-hop to which probe should be sent";
               type jt:ipv4addr;
             }
           }
         }
         container probe-server {
           description "ICMP/TCP/UDP probe server";
           uses apply-advanced;
           container tcp {
             description "TCP probe server";
             uses apply-advanced;
             leaf port {
               description "Port number 7 through 65535";
               type union {
                 type uint16;
                 type string {
                   pattern "<.*>|$.*";
                 }
               }
               mandatory true;
             }
           }
           container udp {
             description "UDP probe server";
             uses apply-advanced;
             leaf port {
               description "Port number 7 through 65535";
               type union {
                 type uint16;
                 type string {
                   pattern "<.*>|$.*";
                 }
               }
               mandatory true;
             }
           }
         }
         leaf probe-limit {
           description "Maximum number of concurrent probes allowed";
           default "100";
           type union {
             type string {
               pattern "<.*>|$.*";
             }
             type uint32 {
               range "1 .. 2000";
             }
           }
         }
       }
       container trace {
         presence "enable trace";
         description "Enable tracing";
         uses apply-advanced;
         leaf evpn-vxlan {
           description "Enable evpn-vxlan tracing";
           type empty;
         }
       }
       container evpn {
         description "Auto-configuration for various layer2 features";
         uses apply-advanced;
         container traceoptions {
           description "Trace options for evpn services";
           uses apply-advanced;
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           container flag {
             description "Type of operation to be traced";
             uses apply-advanced;
             leaf input-configuration {
               description "Trace input configuration";
               type empty;
             }
             leaf chassis {
               description "Trace chassis configuration";
               type empty;
             }
             leaf interfaces {
               description "Trace interfaces configuration";
               type empty;
             }
             leaf routing-instance {
               description "Trace routing-instance configuration";
               type empty;
             }
             leaf routing-options {
               description "Trace routing-options configuration";
               type empty;
             }
             leaf policy-options {
               description "Trace policy-options configuration";
               type empty;
             }
             leaf protocols {
               description "Trace protocols configuration";
               type empty;
             }
             leaf forwarding-options {
               description "Trace forwarding-options configuration";
               type empty;
             }
             leaf all {
               description "Trace all generated configuration";
               type empty;
             }
           }
         }
         container defaults-override {
           description "Select configuration generation override";
           uses apply-advanced;
           leaf no-platform-defaults-config {
             description "Do not auto-derive platform specific configurations";
             type empty;
           }
           leaf no-aggregate-device-count-config {
             description "Do not auto-derive aggregated device count configurations";
             type empty;
           }
           leaf no-policy-and-routing-options-config {
             description "Do not auto-derive routing-options and policy-options configurations";
             type empty;
           }
           leaf no-loop-detect-config {
             description "Do not auto-derive loop-detect configurations";
             type empty;
           }
           leaf no-storm-control-config {
             description "Do not auto-derive loop-detect configurations";
             type empty;
           }
           leaf no-underlay-config {
             description "Do not auto-derive underlay configurations";
             type empty;
           }
           leaf no-overlay-bgp-config {
             description "Do not auto-derive BGP overlay configurations";
             type empty;
           }
         }
         container global-parameters {
           description "Global parameters";
           uses apply-advanced;
           leaf start-aggregate-ethernet-index {
             description "Start index for aggregate interfaces";
             type union {
               type string {
                 pattern "<.*>|$.*";
               }
               type uint32 {
                 range "1 .. 255";
               }
             }
           }
           leaf default-vlan-id {
             description "Vlan-id to be used as a default vlan-id";
             type string;
           }
           leaf anycast-mac {
             description "Configure anycast MAC address";
             type jt:mac-unicast;
           }
           container virtual-gateway {
             description "Configure virtual gateway MAC address";
             leaf v4-mac {
               description "Configure virtual gateway IPV4 virtual MAC address";
               type jt:mac-unicast;
             }
             leaf v6-mac {
               description "Configure virtual gateway IPV6 virtual MAC address";
               type jt:mac-unicast;
             }
           }
           leaf virtual-gateway-mac {
             description "Configure virtual gateway IPV4 virtual MAC address";
             type jt:mac-unicast;
           }
           leaf no-irb-address-auto-derive {
             description "Do not auto-dervie address and use the subnet address as is";
             type empty;
           }
           container mtu {
             description "Configure maximum transmission unit";
             leaf underlay {
               description "Configure maximum transmission unit for underlay interfaces";
               type union {
                 type uint32;
                 type string {
                   pattern "<.*>|$.*";
                 }
               }
             }
             leaf overlay {
               description "Configure maximum transmission unit for overlay interfaces";
               type union {
                 type uint32;
                 type string {
                   pattern "<.*>|$.*";
                 }
               }
             }
           }
         }
         container device-attribute {
           description "Device specific attributes";
           uses apply-advanced;
           leaf peer-id {
             description "Assign an id for each PEER device";
             type union {
               type string {
                 pattern "<.*>|$.*";
               }
               type uint32 {
                 range "1 .. 2";
               }
             }
             mandatory true;
           }
           choice loopback-choice {
             case case_1 {
               leaf loopback-subnet {
                 description "Ipv4 address prefix for loopback subnet";
                 status deprecated;
                 type jt:ipv4prefix;
               }
             }
             case case_2 {
               container loopback {
                 description "Ipv4 address prefix for loopback subnet";
                 uses apply-advanced;
                 choice peer1-subnet-choice {
                   case case_1 {
                     leaf peer1-subnet {
                       description "Ipv4 address prefix for peer1 loopback subnet";
                       type jt:ipv4prefix;
                     }
                   }
                 }
                 choice peer2-subnet-choice {
                   case case_1 {
                     leaf peer2-subnet {
                       description "Ipv4 address prefix for peer2 loopback subnet";
                       type jt:ipv4prefix;
                     }
                   }
                 }
               }
             }
           }
           leaf remote-peer-as {
             description " Autonomous system number in plain number or 'higher 16bits'.'Lower 16 bits' format";
             type string {
             }
           }
           leaf system-id {
             description "Node's System ID, encoded as a MAC address";
             type jt:mac-unicast;
             mandatory true;
           }
           container peer-to-peer {
             description "Interface between PEER to PEER";
             uses apply-advanced;
             container peer-subnet {
               description "PEER to PEER subnet";
               leaf inet {
                 description "IPv4 address prefix for aggregated-ethernet interface bundle";
                 type jt:ipv4prefix;
               }
               leaf inet6 {
                 description "IPv6 address prefix for aggregated-ethernet interface bundle";
                 type jt:ipv6prefix;
               }
               leaf-list interface-name {
                 description "Interface or list of peer to peer interfaces";
                 type union {
                   type jt:interface-device;
                   type string {
                     pattern "<.*>|$.*";
                   }
                 }
               }
             }
             container overlay-connectivity {
               uses apply-advanced;
               leaf ibgp {
                 description "Setup IBGP as OVERLAY";
                 type empty;
               }
             }
             container underlay-connectivity {
               uses apply-advanced;
               leaf ospf {
                 description "Setup OSPF as UNDERLAY";
                 type empty;
               }
             }
           }
         }
         container evpn-vxlan {
           description "EVPN VXLAN configurations";
           uses apply-advanced;
           list dhcp-relay {
             key name;
             description "Dynamic Host Configuration Protocol relay configuration";
             leaf name {
               description "Group name to identify a Server/Relay group";
               type string;
             }
             uses apply-advanced;
             leaf relay-source {
               description "Interface for relay source";
               type union {
                 type jt:interface-name;
                 type string {
                   pattern "<.*>|$.*";
                 }
               }
             }
             list dhcp-server-address {
               key name;
               description "IP Address of one or more DHCP servers";
               max-elements 32;
               leaf name {
                 description "IP Address of DHCP server";
                 type jt:ipaddr;
               }
               uses apply-advanced;
             }
             leaf vrf-instance {
               description "Identifier for VRF instance";
               type union {
                 type string {
                   pattern "<.*>|$.*";
                 }
                 type uint32 {
                   range "1 .. 255";
                 }
               }
               mandatory true;
             }
             leaf routing-instance {
               description "Name of the routing-instance from where server-group is reachable";
               type string {
               }
             }
           }
           list irb {
             key name;
             description "IRB settings";
             leaf name {
               description "IRB instance";
               type string {
               }
             }
             uses apply-advanced;
             leaf use-anycast-address {
               description "Use anycast address";
               type empty;
             }
             leaf no-dhcp-relay {
               description "Exclude this irb from dhcp-relay";
               type empty;
             }
             leaf vlan-id {
               description "IEEE 802.1q VLAN identifier for VLAN";
               type string;
               mandatory true;
             }
             container subnet-address {
               description "Subnet address";
               leaf-list inet {
                 description "Ipv4 subnet address";
                 type jt:ipv4prefix;
               }
               leaf virtual-gateway-v4-address {
                 description "Virtual Gateway IPv4 address";
                 type jt:ipv4addr;
               }
               leaf-list inet6 {
                 description "Ipv6 subnet address";
                 type jt:ipv6prefix;
               }
               leaf virtual-gateway-v6-address {
                 description "Virtual Gateway IPv6 address";
                 type jt:ipv6addr;
               }
               leaf no-irb-address-auto-derive {
                 description "Do not auto-dervie address and use the subnet address as is";
                 type empty;
               }
             }
             container instance {
               description "Specify mac-vrf-instance or vrf-instance instance";
               leaf vrf-instance {
                 description "VRF instance identifier";
                 type union {
                   type string {
                     pattern "<.*>|$.*";
                   }
                   type uint32 {
                     range "1 .. 255";
                   }
                 }
               }
               leaf mac-vrf-instance {
                 description "MAC-VRF instance identifier";
                 type union {
                   type string {
                     pattern "<.*>|$.*";
                   }
                   type uint32 {
                     range "1 .. 255";
                   }
                 }
               }
             }
             leaf apply-config-groups {
               description "Apply groups to the generated irb configuration";
               type string;
             }
           }
           list server {
             key name;
             description "Server configuration";
             leaf name {
               description "SERVER name";
               type string {
               }
               mandatory true;
             }
             uses apply-advanced;
             choice esi-lag-id-choice {
               case case_1 {
                 leaf esi-lag-id {
                   description "Assign an identifier for each server";
                   type union {
                     type string {
                       pattern "<.*>|$.*";
                     }
                     type uint32 {
                       range "1 .. 1024";
                     }
                   }
                 }
               }
               case case_2 {
                 leaf single-home-id {
                   description "Assign an identifier for a single home server";
                   type union {
                     type string {
                       pattern "<.*>|$.*";
                     }
                     type uint32 {
                       range "1 .. 1024";
                     }
                   }
                 }
               }
             }
             leaf-list vlan-id-list {
               description "Create VLAN for each of the vlan-id specified in the vlan-id-list";
               type jt:vlan-range;
             }
             leaf access-vlan-id {
               description "Access VLAN for routing instances";
               type union {
                 type string {
                   pattern "<.*>|$.*";
                 }
                 type uint32 {
                   range "1 .. 4094";
                 }
               }
             }
             list mac-vrf-instance {
               key name;
               description "MAC-VRF instance identifier";
               leaf name {
                 description "Instance identifier";
                 type union {
                   type string {
                     pattern "<.*>|$.*";
                   }
                   type uint32 {
                     range "1 .. 255";
                   }
                 }
                 mandatory true;
               }
               uses apply-advanced;
               leaf-list vlan-id-list {
                 description "Create VLAN for each of the vlan-id specified in the vlan-id-list";
                 type jt:vlan-range;
               }
               leaf access-vlan-id {
                 description "Access VLAN for routing instances";
                 type union {
                   type string {
                     pattern "<.*>|$.*";
                   }
                   type uint32 {
                     range "1 .. 4094";
                   }
                 }
               }
             }
             leaf-list interface {
               description "Interface or list of peer to server interfaces";
               type union {
                 type jt:interface-device;
                 type string {
                   pattern "<.*>|$.*";
                 }
               }
             }
             leaf enable-pxe-boot {
               description "Enable PXE boot";
               type empty;
             }
             leaf apply-config-groups {
               description "Apply groups to the generated interface configuration";
               type string;
             }
             leaf no-lacp {
               description "Do not configure LACP for this server";
               type empty;
             }
             leaf native-vlan-id {
               description "Virtual LAN identifier for untagged frames";
               type union {
                 type string {
                   pattern "<.*>|$.*";
                 }
                 type uint32 {
                   range "0 .. 4094";
                 }
               }
             }
           }
         }
       }
       container inline-napt {
         presence "enable inline-napt";
         description "Inline-NAPT configuration";
         uses apply-advanced;
         container nat44 {
           presence "enable nat44";
           uses apply-advanced;
           choice enable-disable {
             case case_1 {
               leaf disable {
                 description "Disable NAT44 on this interface";
                 type empty;
               }
             }
           }
         }
         container nat64 {
           presence "enable nat64";
           uses apply-advanced;
           choice enable-disable {
             case case_1 {
               leaf disable {
                 description "Disable NAT64 on this interface";
                 type empty;
               }
             }
           }
         }
       }
       container external-napt {
         presence "enable external-napt";
         description "External-NAPT configuration";
         uses apply-advanced;
         choice enable-disable {
           case case_1 {
             leaf disable {
               description "Disable External-NAPT";
               type empty;
             }
           }
         }
       }
       container rtlog {
         presence "enable rtlog";
         description "Secure log daemon options";
         uses apply-advanced;
         container traceoptions {
           description "Security log daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
             mandatory true;
           }
           uses apply-advanced;
           leaf transport-type {
             description "Transport type";
             type enumeration {
               enum "GRE" {
                 description "GRE";
               }
               enum "UDP" {
                 description "UDP";
               }
               enum "TCP" {
                 description "TCP";
               }
             }
             mandatory true;
           }
           leaf client-address {
             description "Client address";
             type jt:ipv4addr;
             mandatory true;
           }
           leaf hosted-service-identifier {
             description "Identifier for the service performed on the remote server";
             type union {
               type string {
                 pattern "<.*>|$.*";
               }
               type int32 {
                 range "1 .. 63";
               }
             }
             mandatory true;
           }
         }
         list server-profile {
           key name;
           ordered-by user;
           description "Configure server profile";
           leaf name {
             description "Server profile name";
             type string {
               length "3 .. 32";
             }
             mandatory true;
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
             }
             mandatory true;
           }
           leaf destination-port {
             description "Destination port of the collector";
             type union {
               type string {
                 pattern "<.*>|$.*";
               }
               type uint16 {
                 range "1 .. 65535";
               }
             }
             mandatory true;
           }
           leaf source-ip {
             description "Source IPv4 Address from which logging is to be done";
             type jt:ipv4addr;
             mandatory true;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             type string {
               length "1 .. 63";
             }
           }
           uses apply-advanced;
           leaf collector {
             description "Specify a collector name";
             type string {
               length "1 .. 63";
             }
           }
           leaf-list collector-group {
             ordered-by user;
             description "Specify a collector-group name";
             type string {
               length "1 .. 63";
             }
             max-elements 1;
           }
           leaf template-type {
             description "Allow jflow-log for applications";
             type enumeration {
               enum "nat" {
                 description "Enable jflow-logs for NAT events";
               }
             }
             mandatory true;
           }
           leaf version {
             description "Version of jflow-logging";
             type enumeration {
               enum "v9" {
                 description "Version 9";
               }
               enum "ipfix" {
                 description "Ipfix";
               }
             }
             mandatory true;
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
           leaf session-end-reason {
             description "Session end reason";
             type enumeration {
               enum "custom-reason" {
                 description "Custom specific session end reason";
               }
               enum "default-reason" {
                 description "Default session end reason";
               }
             }
           }
         }
       }
       container service-device-pools {
         description "Configure service device pools";
         uses apply-advanced;
         list pool {
           key name;
           ordered-by user;
           description "Define service device pool";
           uses service_device_pool_object;
         }
       }
       container port-extender {
         description "Port extender service configuration";
         uses apply-advanced;
         container jnu {
           presence "enable jnu";
           description " Enables juniper node unifier related setup for NGPE";
           uses apply-advanced;
           leaf loopback-ip-address-mgmt-ad {
             description "Loopback IPAddress of AD used for configuration and management";
             type jt:ipaddr;
           }
           leaf skip-lo0-config {
             description "Expects mgmt ip config on lo0 to exist, so skips configuring it";
             type empty;
           }
         }
         container fabric {
           presence "enable fabric";
           description "NGPE fabric configuration";
           uses apply-advanced;
           leaf loopback-ip-address-data-ad {
             description "Loopback IPAddress of AD for NGPE fabric connectivity";
             type jt:ipaddr;
           }
           choice evpn-work-modes {
             case case_1 {
               container evpn-vxlan {
                 presence "enable evpn-vxlan";
                 description "Tunnelling technology used for NGPE fabric";
                 uses apply-advanced;
                 leaf base-vni {
                   description "Optional vni to override the default value (0xffff00)";
                   type union {
                     type string {
                       pattern "<.*>|$.*";
                     }
                     type int32 {
                       range "1 .. 16777214";
                     }
                   }
                 }
               }
             }
           }
           leaf bfd-interval {
             description "BFD Minimum interval for fabric failure detection";
             units "milliseconds";
             type union {
               type string {
                 pattern "<.*>|$.*";
               }
               type uint32 {
                 range "100 .. 10000";
               }
             }
           }
           leaf bfd-disable {
             description "Disable BFD for fabric protocol sessions";
             type empty;
           }
         }
         list satellite {
           key name;
           ordered-by user;
           description "Satellite on board on NGPE";
           leaf name {
             description "Name of the satellite";
             type string;
           }
           uses apply-advanced;
           leaf satellite-mgmt-ip {
             description "IPAddress of SD";
             type jt:ipaddr;
           }
           leaf device-name {
             description "Name of this satellite - to be deprecated";
             type string;
           }
           leaf device-model {
             description "SD model that's expected to be connected";
             type enumeration {
               enum "ex4400-48p" {
                 description "Select EX4400-48P as the satellite";
               }
               enum "ex4400-48t" {
                 description "Select EX4400-48T as the satellite";
               }
               enum "qfx5120-48t-6c" {
                 description "Select QFX5120-48T-CHAS as the satellite";
               }
               enum "qfx5120-48y-8c" {
                 description "Select JNP48Y8C-CHAS as the satellite";
               }
             }
             mandatory true;
           }
           list connectivity-interface-ad {
             key name;
             ordered-by user;
             description "One or more cascade interfaces connecting to SD";
             leaf name {
               description "Interface on AD through which this SD is reachable";
               type string;
             }
             uses apply-advanced;
           }
           list connectivity-interface-sd {
             key name;
             ordered-by user;
             description "One or more uplink interfaces connecting to AD";
             leaf name {
               description "Interface on this SD through which AD is reachable";
               type string;
             }
             uses apply-advanced;
           }
           leaf ssh-key {
             description "Public-key of the SD thats connected";
             type string;
           }
           leaf loopback-ip-address-mgmt-sd {
             description "Loopback IPAddress of SD used for configuration and management";
             type jt:ipaddr;
           }
           leaf target-mode {
             description "EP IFD targeting";
             type empty;
           }
           leaf cascade-interface {
             description "AE interface (cascade port) on the AD that overrides the generated value";
             type string;
           }
           leaf fpc-slot {
             description "Virtual slot that's assigned for the SD that overrides the generated value";
             type union {
               type string {
                 pattern "<.*>|$.*";
               }
               type uint32 {
                 range "65 .. 254";
               }
             }
           }
           leaf loopback-ip-address-data-sd {
             description "Loopback IPAddress of this SD for NGPE fabric connectivity";
             type jt:ipaddr;
           }
           leaf mgmt-ip-address-ad {
             description "AD IPAddress of the logical interface for management";
             type jt:ipaddr;
           }
           leaf mgmt-ip-address-sd {
             description "SD IPAddress of the logical interface for management";
             type jt:ipaddr;
           }
           leaf data-ip-address-ad {
             description " AD IPAddress of the logical interface for data";
             type jt:ipaddr;
           }
           leaf data-ip-address-sd {
             description " SD IPAddress of the logical interface for data";
             type jt:ipaddr;
           }
           leaf speed {
             description "Set non-default port speed, takes a string. ex:<0:1g;1:1g;20:10g;47:10g>";
             type string;
           }
           list ports {
             key name;
             ordered-by user;
             description "One or more revenue ports on the SD";
             leaf name {
               description "Revenue port name";
               type string;
             }
             uses apply-advanced;
           }
           leaf fabric-disable {
             description "Disables the fabric config between AD and SD";
             type empty;
           }
           leaf ztp {
             description "Use this knob if the SD is ZTP capable";
             type empty;
           }
           leaf image {
             description "Image file present under /var/home/ftp to be loaded on SD during ZTP";
             type string;
           }
           leaf cp-mtu {
             description "Overrides the default MTU (9000) setting on the cascade,uplink interfaces";
             type union {
               type string {
                 pattern "<.*>|$.*";
               }
               type uint32 {
                 range "256 .. 16000";
               }
             }
           }
           leaf default-speed {
             description "Overrides EP default speed chosen based on the device-model";
             type enumeration {
               enum "1g" {
                 description "Changes the EP default speed to 1g";
               }
               enum "10g" {
                 description "Changes the EP default speed to 10g";
               }
               enum "100m" {
                 description "Changes the EP default speed to 100m";
               }
             }
           }
         }
       }
       container analytics {
         presence "enable analytics";
         description "Traffic analytics configuration options";
         uses apply-advanced;
         container na-grpc-server {
           presence "enable na-grpc-server";
           description "Configuration for na-grpcd";
           uses apply-advanced;
           container traceoptions {
             description "Traceoptions for na-grpcd";
             uses apply-advanced;
             container file {
               presence "enable file";
               description "Trace file information";
               uses apply-advanced;
               leaf size {
                 description "Maximum trace file size";
                 type string;
               }
               leaf files {
                 description "Maximum number of trace files";
                 default "5";
                 type union {
                   type string {
                     pattern "<.*>|$.*";
                   }
                   type uint32 {
                     range "2 .. 1000";
                   }
                 }
               }
             }
           }
         }
         container zero-suppression {
           description "Configure suppression of zeros for GRPC sensors";
           uses apply-advanced;
           leaf no-zero-suppression {
             description "Disable zero suppression";
             type empty;
             mandatory true;
           }
         }
         container gnmi {
           presence "enable gnmi";
           description "Gnmi telemetry";
           uses apply-advanced;
           container extension-message {
             presence "enable extension-message";
             description "Gnmi telemetry extension message information";
             uses apply-advanced;
             choice export-message {
               case case_1 {
                 leaf no-export {
                   description "To disable export of gnmi extension message";
                   type empty;
                 }
               }
             }
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:host;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
           container tls {
             presence "enable tls";
             description "Configure TLS credentials";
             uses apply-advanced;
             leaf certificate-id {
               description "Local client certificate ID to be used for dialout";
               type string {
               }
             }
             leaf-list ca-profiles {
               ordered-by user;
               description "List of CA profiles to be used to verify dialout server";
               type string;
             }
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipaddr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             status deprecated;
             type enumeration {
               enum "gpb" {
                 description "Use gpb format";
                 status deprecated;
               }
               enum "gpb-gnmi" {
                 description "Use gnmi format for gpb messages";
                 status deprecated;
               }
               enum "json-gnmi" {
                 description "Use gnmi format for json messages";
                 status deprecated;
               }
             }
           }
           leaf transport {
             description "Telemetry export transport protocol";
             status deprecated;
             type enumeration {
               enum "udp" {
                 description "Use UDP transport protocol";
                 status deprecated;
               }
               enum "grpc" {
                 description "Use grpc transport";
                 status deprecated;
               }
             }
           }
           leaf routing-instance {
             description "Routing instance to be used for grpc transport";
             type string;
           }
           leaf dialout-type {
             description "Type of dialout connection";
             type enumeration {
               enum "native-grpc-gpb" {
                 description "Dialout based on grpc over tcp transport";
               }
               enum "native-udp-compact" {
                 description "Dialout based on UDP compact protobuf";
               }
               enum "native-udp-gpb" {
                 description "Dialout based on UDP with native proto containing gNMI SubscribeResponse";
               }
             }
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 1024";
             }
             mandatory true;
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
             max-elements 30;
           }
           leaf target-defined {
             description "Allow target to decide periodic, on-change or mix";
             type empty;
           }
           leaf life-time {
             description "Denotes sensor life-time";
             type enumeration {
               enum "long-lived" {
                 description "A long-lived subscription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                         enum "interface-queue-statistics" {
                           description "Interface Queue statistics";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "0 .. 86400";
                       }
                     }
                   }
                   leaf sensors {
                     description "Space separated list of sensor paths";
                     type string {
                       length "1 .. 2048";
                     }
                     mandatory true;
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
         container traceoptions {
           description "Traffic analytics trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
               mandatory true;
             }
             leaf low {
               description "Low queue depth threshold";
               units "bytes";
               type union {
                 type string {
                   pattern "<.*>|$.*";
                 }
                 type uint32 {
                   range "1 .. 1250000000";
                 }
               }
               mandatory true;
             }
           }
           container latency-threshold {
             description "Latency threshold configuration";
             leaf high {
               description "High latency threshold";
               units "nanoseconds";
               type union {
                 type string {
                   pattern "<.*>|$.*";
                 }
                 type uint32 {
                   range "1 .. 100000000";
                 }
               }
               mandatory true;
             }
             leaf low {
               description "Low latency threshold";
               units "nanoseconds";
               type union {
                 type string {
                   pattern "<.*>|$.*";
                 }
                 type uint32 {
                   range "1 .. 100000000";
                 }
               }
               mandatory true;
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
       }
       container web-filter {
         description "Web Filtering service configuration";
         uses apply-advanced;
         leaf multi-tenant-support {
           description "Enable multi-tenant-support";
           type empty;
         }
         container multi-tenant-hash {
           description "Multi-tenant hashed file configuration";
           uses dnsf-multitenant-hash-object;
         }
         list profile {
           key name;
           ordered-by user;
           description "Web Filter profile";
           max-elements 8;
           uses urlf-profile-object;
         }
         list ip-address-list {
           key name;
           ordered-by user;
           description "SecIntel ip address list";
           uses si-ip-address-list-object;
         }
         container traceoptions {
           description "Trace options for Web Filter ";
           uses urlf-traceoptions-object;
         }
       }
     }
     container access-profile {
       description "Access profile for this instance";
       leaf access-profile-name {
         description "Profile name";
         type string;
       }
     }
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           leaf key-generation-self-test {
             description "Raise alarm for key generation self test failures";
             type empty;
           }
           leaf non-cryptographic-self-test {
             description "Raise alarm for non-cryptographic self test failures";
             type empty;
           }
           container policy {
             description "Raise alarm for flow policy violations";
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
         }
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             type string;
           }
           uses apply-advanced;
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       container pki {
         description "PKI service configuration";
         presence "enable pki";
         uses security-pki;
       }
       container group-vpn {
         description "Group VPN configuration";
         uses security-group-vpn;
       }
       container traceoptions {
         description "Trace options for IPSec key management";
         uses kmd-security-traceoptions;
       }
       container ipsec {
         description "IPSec configuration";
         uses security-ipsec-vpn;
       }
       container ike {
         description "IKE configuration";
         uses security-ike;
       }
       container macsec {
         description "MAC Security configuration";
         uses security-macsec;
       }
     }
     container interfaces {
       description "Interface configuration";
       uses apply-advanced;
       list interface-set {
         key name;
         description "Logical interface set configuration";
         leaf name {
           type string;
         }
         uses apply-advanced;
         list interface {
           key name;
           description "One or more interfaces that belong to interface set";
           leaf name {
             description "Interface name";
             type union {
               type jt:interface-device;
               type string {
                 pattern "<.*>|$.*";
               }
             }
           }
           uses apply-advanced;
           list unit {
             key name;
             description "One or more logical interface unit numbers";
             leaf name {
               description "Unit number";
               type union {
                 type string {
                   pattern "<.*>|$.*";
                 }
                 type uint32 {
                   range "0 .. 1073741823";
                 }
               }
             }
             uses apply-advanced;
           }
           list vlan-tags-outer {
             key name;
             description "One or more outer VLAN tags";
             leaf name {
               description "VLAN tag ID";
               type union {
                 type string {
                   pattern "<.*>|$.*";
                 }
                 type uint32 {
                   range "0 .. 4094";
                 }
               }
             }
             uses apply-advanced;
           }
         }
       }
       container stacked-interface-set {
         presence "enable stacked-interface-set";
         description "Stacked interface set configuration";
         uses apply-advanced;
         list interface-set {
           key name;
           ordered-by user;
           description "Stacked parent interface set configuration";
           leaf name {
             type string;
           }
           uses apply-advanced;
           list interface-set {
             key name;
             ordered-by user;
             description "Stacked child interface set configuration";
             leaf name {
               type string;
             }
             uses apply-advanced;
           }
         }
       }
       container traceoptions {
         description "Interface trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           description "Tracing parameters";
           leaf name {
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           type string {
             length "1 .. 128";
           }
         }
         list member {
           key name;
           ordered-by user;
           description "Interfaces belonging to the interface range";
           leaf name {
             description "Member interface name";
             type union {
               type jt:interface-range-wild;
               type string {
                 pattern "<.*>|$.*";
               }
             }
           }
           uses apply-advanced;
         }
         list member-range {
           key name;
           ordered-by user;
           description "Interfaces range in <start-range> to <end-range> format";
           leaf name {
             type union {
               type jt:interface-device;
               type string {
                 pattern "<.*>|$.*";
               }
             }
           }
           leaf end-range {
             type union {
               type jt:interface-device;
               type string {
                 pattern "<.*>|$.*";
               }
             }
             mandatory true;
           }
         }
         uses apply-advanced;
         leaf description {
           description "Text description of interface";
           type string;
         }
         leaf external-model-name {
           description "Name for interface as configured using 3rd-party model";
           type string;
         }
         container management-ethernet-redundancy {
           presence "enable management-ethernet-redundancy";
           description "Management Interface Redundancy";
           uses apply-advanced;
           choice enable_choice {
             case case_1 {
               leaf redundancy-enable {
                 description "Enable Managment Ethernet Redundancy";
                 type empty;
               }
             }
             case case_2 {
               leaf redundancy-disable {
                 description "Disable  Managment Ethernet Redundancy";
                 type empty;
               }
             }
           }
           leaf connectivity-test-interval {
             description "Connectivity test interval";
             default "5";
             units "seconds";
             type union {
               type string {
                 pattern "<.*>|$.*";
               }
               type uint32 {
                 range "1 .. 10";
               }
             }
           }
           leaf connectivity-test-response-interval {
             description "Connectivity test response wait time";
             default "5";
             units "seconds";
             type union {
               type string {
                 pattern "<.*>|$.*";
               }
               type uint32 {
                 range "1 .. 10";
               }
             }
           }
           leaf remote-ipv4-address {
             description "Destination IPV4 address to reach remote ";
             default "nil";
             type jt:ipv4addr;
           }
           leaf remote-ipv6-address {
             description "Destination IPV6 address to reach remote";
             default "nil";
             type jt:ipv6addr;
           }
           leaf number-of-connectivity-retries {
             description "Number of Connectivity retries ";
             default "2";
             type union {
               type string {
                 pattern "<.*>|$.*";
               }
               type uint32 {
                 range "1 .. 8";
               }
             }
           }
         }
         choice enable-disable {
           case case_1 {
             leaf disable {
               description "Disable this interface";
               type empty;
             }
           }
         }
         container traceoptions {
           presence "enable traceoptions";
           description "Interface trace options";
           uses apply-advanced;
           list flag {
             key name;
             ordered-by user;
             description "Tracing parameters";
             leaf name {
               type enumeration {
                 enum "ipc" {
                   description "Trace interface IPC messages";
                 }
                 enum "event" {
                   description "Trace interface events";
                 }
                 enum "media" {
                   description "Trace interface media changes";
                 }
                 enum "all" {
                   description "Enable all interface trace flags";
                 }
               }
             }
           }
         }
         leaf passive-monitor-mode {
           description "Use interface to tap packets from another router";
           type empty;
         }
         choice keepalive_choices {
           case case_1 {
             container keepalives {
               description "Send or demand keepalive messages";
               presence "enable keepalives";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           type string;
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               type empty;
             }
           }
           case case_3 {
             container hierarchical-scheduler {
               presence "enable hierarchical-scheduler";
               description "Enable hierarchical scheduling";
               leaf maximum-hierarchy-levels {
                 description "Maximum hierarchy levels";
                 type union {
                   type string {
                     pattern "<.*>|$.*";
                   }
                   type uint32;
                 }
               }
               leaf implicit-hierarchy {
                 description "Implicit hierarchy (follows interface hierarchy)";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf port-extender-cascade-port {
           description "NGPE Cascade port";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               type empty;
             }
           }
           case case_3 {
           }
           case case_4 {
           }
         }
         leaf number-of-sub-ports {
           description "Number of channels to create for a port";
           type union {
             type string {
               pattern "<.*>|$.*";
             }
             type uint32 {
               range "1 .. 8";
             }
           }
         }
         leaf speed {
           description "Link speed";
           type enumeration {
             enum "auto" {
               description "Enable auto negotiation of interface speed";
             }
             enum "auto-10m-100m" {
               description "Enable auto negotiation of limiting interface speed to 10m/100m";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
             enum "1.6t" {
             }
           }
         }
         leaf mtu {
           description "Maximum transmit packet size";
           type union {
             type string {
               pattern "<.*>|$.*";
             }
             type uint32;
           }
         }
         container hold-time {
           description "Hold time for link up and link down";
           leaf up {
             description "Link up hold time";
             units "milliseconds";
             type union {
               type uint32;
               type string {
                 pattern "<.*>|$.*";
               }
             }
             mandatory true;
           }
           leaf down {
             description "Link down hold time";
             units "milliseconds";
             type union {
               type uint32;
               type string {
                 pattern "<.*>|$.*";
               }
             }
             mandatory true;
           }
         }
         container port-extender {
           description "Tunnel binding information for the extended port";
           uses apply-advanced;
           container vxlan {
             presence "enable vxlan";
             description "VXLAN binding information for the extended port";
             uses apply-advanced;
             leaf end-point {
               description "Satellite loopback IP address";
               type jt:ipaddr;
               mandatory true;
             }
             leaf vni {
               description "VNI of the satellite extended-port";
               type union {
                 type string {
                   pattern "<.*>|$.*";
                 }
                 type uint32 {
                   range "0 .. 16777214";
                 }
               }
               mandatory true;
             }
           }
         }
         container link-degrade-monitor {
           presence "enable link-degrade-monitor";
           description "Enable link degrade monitoring";
           uses apply-advanced;
           choice enable_choice {
             case case_1 {
               leaf link-degrade-monitor-enable {
                 description "Enable Link Degrade Monitoring";
                 type empty;
               }
             }
             case case_2 {
               leaf no-link-degrade-monitor-enable {
                 description "Disable Link Degrade Monitoring";
                 type empty;
               }
             }
           }
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
               }
             }
             leaf clear {
               description "BER at which link considered improved(1..16)";
               default "1e-12";
               type string {
               }
             }
             leaf warning-set {
               description "BER at which link degrade warning raised(1..16)";
               default "1e-9";
               type string {
               }
             }
             leaf warning-clear {
               description "BER at which link degrade warning cleared(1..16)";
               default "1e-11";
               type string {
               }
             }
             leaf interval {
               description "Consecutive link degrade events";
               default "10";
               type union {
                 type string {
                   pattern "<.*>|$.*";
                 }
                 type uint32 {
                   range "1 .. 256";
                 }
               }
             }
           }
         }
         container satop-options {
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container clocking {
           description "Interface clock source";
           choice clocking_choices {
             case case_1 {
               leaf internal {
                 description "Clocking provided by local system";
                 type empty;
               }
             }
             case case_2 {
               container external {
                 presence "enable external";
                 description "Clocking provided by DCE (loop timing)";
               }
             }
           }
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf media-type {
           description "Interface media type (copper or fiber)";
           type enumeration {
             enum "copper" {
               description "Copper as media";
             }
             enum "fiber" {
               description "Fiber as media";
             }
           }
         }
         leaf encapsulation {
           description "Physical link-layer encapsulation";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
             }
             enum "cesopsn" {
               description "Structure-Agnostic TDM over Packet encapsulation";
             }
             enum "ima" {
               description "Inverse Multiplexing for ATM";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         leaf network-isolation-profile {
           description "Attach a network isolation profile on this interface";
           type string;
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
         }
         container lmi {
           description "Local Management Interface settings";
           uses apply-advanced;
           leaf n391dte {
             description "DTE full status polling interval";
             type union {
               type string {
                 pattern "<.*>|$.*";
               }
               type uint16 {
                 range "1 .. 255";
               }
             }
           }
           leaf n392dce {
             description "DCE error threshold";
             type union {
               type string {
                 pattern "<.*>|$.*";
               }
               type uint16 {
                 range "1 .. 10";
               }
             }
           }
           leaf n392dte {
             description "DTE error threshold";
             type union {
               type string {
                 pattern "<.*>|$.*";
               }
               type uint16 {
                 range "1 .. 10";
               }
             }
           }
           leaf n393dce {
             description "DCE monitored event count";
             type union {
               type string {
                 pattern "<.*>|$.*";
               }
               type uint16 {
                 range "1 .. 10";
               }
             }
           }
           leaf n393dte {
             description "DTE monitored event count";
             type union {
               type string {
                 pattern "<.*>|$.*";
               }
               type uint16 {
                 range "1 .. 10";
               }
             }
           }
           leaf t391dte {
             description "DTE polling timer";
             units "seconds";
             type union {
               type string {
                 pattern "<.*>|$.*";
               }
               type uint16 {
                 range "5 .. 30";
               }
             }
           }
           leaf t392dce {
             description "DCE polling verification timer";
             units "seconds";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           uses sonet_options_type;
         }
         container logical-tunnel-options {
           description "Logical Tunnel interface-specific options";
           uses apply-advanced;
           container link-protection {
             presence "enable link-protection";
             description "Enable link protection mode";
             uses apply-advanced;
             leaf revertive {
               description "Revert back (Default mode) from active backup link to primary, if primary is UP";
               type empty;
             }
             leaf non-revertive {
               description "Do not revert back from active backup link to primary, if primary is UP";
               type empty;
             }
           }
           leaf per-unit-mac-disable {
             description "Disable the creation of per unit mac address on LT IFLs for VPLS/CCC encaps";
             type empty;
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               description "Open this VPI in promiscuous mode";
               leaf name {
                 description "Virtual path index";
                 type union {
                   type string {
                     pattern "<.*>|$.*";
                   }
                   type uint32 {
                     range "0 .. 255";
                   }
                 }
               }
             }
           }
           list vpi {
             key name;
             ordered-by user;
             description "Define a virtual path";
             leaf name {
               description "Virtual path index";
               type union {
                 type string {
                   pattern "<.*>|$.*";
                 }
                 type uint32 {
                   range "0 .. 255";
                 }
               }
             }
             uses apply-advanced;
             leaf maximum-vcs {
               description "Maximum number of virtual circuits on this VP";
               type union {
                 type uint32;
                 type string {
                   pattern "<.*>|$.*";
                 }
               }
             }
             container shaping {
               description "Virtual path traffic-shaping options";
               uses dcd_shaping_config;
             }
             container oam-period {
               description "F4 OAM cell period";
               choice oam_period_choices {
                 case case_1 {
                   leaf oam-period {
                     description "F4 OAM cell period";
                     units "seconds";
                     type union {
                       type string {
                         pattern "<.*>|$.*";
                       }
                       type uint32 {
                         range "1 .. 900";
                       }
                     }
                   }
                 }
                 case case_2 {
                   container disable {
                     presence "enable disable";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             description "ATM2 CoS virtual circuit drop profiles";
             leaf name {
               description "Linear RED profile name";
               type string {
               }
             }
             leaf queue-depth {
               description "Maximum queue depth";
               units "cells";
               type string;
               mandatory true;
             }
             leaf high-plp-threshold {
               description "Fill level percentage when linear RED is applied for high PLP";
               type union {
                 type string {
                   pattern "<.*>|$.*";
                 }
                 type uint32 {
                   range "0 .. 100";
                 }
               }
               mandatory true;
             }
             leaf low-plp-threshold {
               description "Fill level percentage when linear RED is applied for low PLP";
               type union {
                 type string {
                   pattern "<.*>|$.*";
                 }
                 type uint32 {
                   range "0 .. 100";
                 }
               }
               mandatory true;
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             description "ATM2 CoS parameters assigned to forwarding classes";
             leaf name {
               description "ATM2 CoS scheduler map name";
               type string {
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 type string {
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               type empty;
             }
             leaf reset-on-flow-control {
               description "Reset interface during prolonged flow-control";
               type empty;
             }
             leaf down-on-flow-control {
               description "Bring interface down during prolonged flow-control";
               type empty;
             }
             leaf up-on-flow-control {
               description "Keep interface up during prolonged flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           uses ppp_options_type;
         }
         container lsq-failure-options {
           description "Link services queuing failure options";
           uses apply-advanced;
           list trigger-link-failure {
             key name;
             ordered-by user;
             description "Link on which to trigger failure";
             leaf name {
               description "Interface name";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container services-options {
           description "Services interface-specific options";
           uses apply-advanced;
           container syslog {
             description "Define system log parameters";
             uses log-object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           leaf fragment-limit {
             description "Maximum number of fragments allowed for a packet";
             default "64";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           leaf enable-subscriber-analysis {
             description "Enable subscriber analysis on the interface";
             type empty;
           }
           leaf disable-subscriber-analysis {
             description "Disable subscriber analysis on the interface";
             type empty;
           }
           leaf disable-usp-tracing {
             description "Disable usp tracing on this pic";
             type empty;
           }
           leaf disable-drop-flows {
             description "Disable drop flows on this pic";
             type empty;
           }
           container ignore-errors {
             presence "enable ignore-errors";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 description "Filter based on source-ip (and wildcard)";
                 leaf ip {
                   description "Source IP";
                   type jt:ipaddr;
                   mandatory true;
                 }
                 leaf wildcard {
                   description "Source IP wildcard";
                   type jt:ipaddr;
                 }
               }
               container dest-ip {
                 description "Filter based on dest-ip (and wildcard)";
                 leaf ip {
                   description "Dest IP";
                   type jt:ipaddr;
                   mandatory true;
                 }
                 leaf wildcard {
                   description "Dest IP wildcard";
                   type jt:ipaddr;
                 }
               }
               container sw-sip {
                 description "Filter based on source softwire ip (and wildcard)";
                 leaf ip {
                   description "Source softwire IP";
                   type jt:ipv6addr;
                   mandatory true;
                 }
                 leaf wildcard {
                   description "Source IP wildcard";
                   type jt:ipv6addr;
                 }
               }
               container sw-dip {
                 description "Filter based on destination softwire ip (and wildcard)";
                 leaf ip {
                   description "Destination softwire IP";
                   type jt:ipaddr;
                   mandatory true;
                 }
                 leaf wildcard {
                   description "Destination IP wildcard";
                   type jt:ipaddr;
                 }
               }
               container sport-range {
                 description "Filter based on source port";
                 leaf low {
                   description "Source port range start";
                   type union {
                     type uint16;
                     type string {
                       pattern "<.*>|$.*";
                     }
                   }
                   mandatory true;
                 }
                 leaf high {
                   description "Source port range end";
                   type union {
                     type uint16;
                     type string {
                       pattern "<.*>|$.*";
                     }
                   }
                   mandatory true;
                 }
               }
               container dport-range {
                 description "Filter based on destination port";
                 leaf low {
                   description "Destination port range start";
                   type union {
                     type uint16;
                     type string {
                       pattern "<.*>|$.*";
                     }
                   }
                   mandatory true;
                 }
                 leaf high {
                   description "Destination port range end";
                   type union {
                     type uint16;
                     type string {
                       pattern "<.*>|$.*";
                     }
                   }
                   mandatory true;
                 }
               }
               leaf proto {
                 description "Filter based on L4 protocol";
                 type enumeration {
                   enum "icmp" {
                   }
                   enum "tcp" {
                   }
                   enum "udp" {
                   }
                 }
               }
             }
           }
           container flow {
             description "Define flow parameters";
             uses apply-advanced;
             container traceoptions {
               description "Trace options for flow services";
             }
           }
           leaf fpc-pic-information {
             description "Include FPC and PIC slot number in the syslogs";
             type empty;
           }
           leaf utc-timestamp {
             description "Use UTC time for security log timestamps";
             type empty;
           }
           leaf syslog-local-system-timestamp {
             description "Use local system time for services syslog timestamp";
             type empty;
           }
         }
         container t3-options {
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           container compatibility-mode {
             description "Set CSU compatibility mode";
             choice vendor {
               case case_1 {
                 container larscom {
                   presence "enable larscom";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               type empty;
             }
             leaf no-cbit-parity {
               description "Don't enable C-bit parity mode";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             description "Set CSU compatibility mode";
             choice vendor {
               case case_1 {
                 leaf larscom {
                   description "Compatible with Larscom CSU (only non IQ E3 interfaces)";
                   type empty;
                 }
               }
               case case_2 {
                 container digital-link {
                   presence "enable digital-link";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           description "T1 interface-specific options";
           uses apply-advanced;
           leaf timeslots {
             description "Timeslots (1..24; for example, 1-3,4,9,22-24 (no space)";
             type string;
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
         }
         container ds0-options {
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   type empty;
                 }
                 container dtr {
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
             }
           }
           leaf dtr-circuit {
             description "Data Transmit Ready circuit mode";
             type enumeration {
               enum "balanced" {
                 description "Balanced signal";
               }
               enum "unbalanced" {
                 description "Unbalanced signal";
               }
             }
           }
           leaf dtr-polarity {
             description "Data Transmit Ready signal polarity";
             type enumeration {
               enum "positive" {
                 description "Positive polarity";
               }
               enum "negative" {
                 description "Negative polarity";
               }
             }
           }
           leaf rts-polarity {
             description "Request To Send signal polarity";
             type enumeration {
               enum "positive" {
                 description "Positive polarity";
               }
               enum "negative" {
                 description "Negative polarity";
               }
             }
           }
           leaf control-polarity {
             description "X.21 Control signal polarity";
             type enumeration {
               enum "positive" {
                 description "Positive polarity";
               }
               enum "negative" {
                 description "Negative polarity";
               }
             }
           }
           leaf dcd-polarity {
             description "Data Carrier Detect signal polarity";
             type enumeration {
               enum "positive" {
                 description "Positive polarity";
               }
               enum "negative" {
                 description "Negative polarity";
               }
             }
           }
           leaf dsr-polarity {
             description "Data Set Ready signal polarity";
             type enumeration {
               enum "positive" {
                 description "Positive polarity";
               }
               enum "negative" {
                 description "Negative polarity";
               }
             }
           }
           leaf cts-polarity {
             description "Clear To Send signal polarity";
             type enumeration {
               enum "positive" {
                 description "Positive polarity";
               }
               enum "negative" {
                 description "Negative polarity";
               }
             }
           }
           leaf indication-polarity {
             description "X.21 Indication signal polarity";
             type enumeration {
               enum "positive" {
                 description "Positive polarity";
               }
               enum "negative" {
                 description "Negative polarity";
               }
             }
           }
           leaf tm-polarity {
             description "Test Mode signal polarity";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         container ether-options {
           description "Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               description "Storm control profile name to bind";
               uses apply-advanced;
               leaf profile-name {
                 description "Profile name";
                 type string;
                 mandatory true;
               }
             }
             container recovery-timeout {
               description "Recovery timeout for this interface";
               leaf time-in-seconds {
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             description "Source address filters";
             leaf name {
               description "Remote MAC address";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
               enum "fec-etc" {
                 description "ETC fec based on IEEE 802.3 Clause 119 for 800G links";
               }
               enum "fec172" {
                 description "IEEE 802.3dj Clause 172, RS-FEC for 800G links";
               }
             }
           }
           container speed {
             description "Specify speed";
             choice automatic {
               case case_1 {
                 container auto-negotiation {
                   presence "enable auto-negotiation";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               uses apply-advanced;
               leaf subgroup-name {
                 description "Name of the subgroup";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           leaf mdi-mode {
             description "Cable cross-over mode";
             type enumeration {
               enum "auto" {
                 description "Automatic mdi/mdi-x mode";
               }
               enum "force" {
                 description "Enable auto-MDIX always";
               }
               enum "mdi" {
                 description "MDI(straight through) mode";
               }
               enum "mdix" {
                 description "MDI Cross-over mode";
               }
             }
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 description "Enable auto-negotiation";
                 leaf remote-fault {
                   type enumeration {
                     enum "local-interface-offline" {
                       description "Disable local interface";
                     }
                     enum "local-interface-online" {
                       description "Enable local interface";
                     }
                   }
                 }
               }
             }
           }
           leaf asynchronous-notification {
             description "Enable sending asynchronous notification to peer on CCC-down";
             type empty;
           }
           list source-address-filter {
             key name;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   ordered-by user;
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf ieee-802-3az-eee {
             description "IEEE 802.3az Energy Efficient Ethernet(EEE)";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
         }
         container optics-options {
           description "Optics options";
           uses apply-advanced;
           leaf wavelength {
             description "Wavelength of the optics (nanometers) for 50Ghz/100Ghz spacing";
             type enumeration {
               enum "1611.79" {
                 description "1611.79 nm/186.000000 THz 3.125/6.25/12.5/50/75/100GHz spacing";
               }
               enum "1611.76" {
                 description "1611.76 nm/186.003125 THz 3.125GHz spacing";
               }
               enum "1611.73" {
                 description "1611.73 nm/186.006250 THz 3.125/6.25GHz spacing";
               }
               enum "1611.71" {
                 description "1611.71 nm/186.009375 THz 3.125GHz spacing";
               }
               enum "1611.68" {
                 description "1611.68 nm/186.012500 THz 3.125/6.25/12.5GHz spacing";
               }
               enum "1611.65" {
                 description "1611.65 nm/186.015625 THz 3.125GHz spacing";
               }
               enum "1611.62" {
                 description "1611.62 nm/186.018750 THz 3.125/6.25GHz spacing";
               }
               enum "1611.60" {
                 description "1611.60 nm/186.021875 THz 3.125GHz spacing";
               }
               enum "1611.57" {
                 description "1611.57 nm/186.025000 THz 3.125/6.25/12.5GHz spacing";
               }
               enum "1611.54" {
                 description "1611.54 nm/186.028125 THz 3.125GHz spacing";
               }
               enum "1611.52" {
                 description "1611.52 nm/186.031250 THz 3.125/6.25GHz spacing";
               }
               enum "1611.49" {
                 description "1611.49 nm/186.034375 THz 3.125GHz spacing";
               }
               enum "1611.46" {
                 description "1611.46 nm/186.037500 THz 3.125/6.25/12.5GHz spacing";
               }
               enum "1611.44" {
                 description "1611.44 nm/186.040625 THz 3.125GHz spacing";
               }
               enum "1611.41" {
                 description "1611.41 nm/186.043750 THz 3.125/6.25GHz spacing";
               }
               enum "1611.38" {
                 description "1611.38 nm/186.046875 THz 3.125GHz spacing";
               }
               enum "1611.35" {
                 description "1611.35 nm/186.050000 THz 3.125/6.25/12.5/50/75GHz spacing";
               }
               enum "1611.33" {
                 description "1611.33 nm/186.053125 THz 3.125GHz spacing";
               }
               enum "1611.30" {
                 description "1611.30 nm/186.056250 THz 3.125/6.25GHz spacing";
               }
               enum "1611.27" {
                 description "1611.27 nm/186.059375 THz 3.125GHz spacing";
               }
               enum "1611.25" {
                 description "1611.25 nm/186.062500 THz 3.125/6.25/12.5GHz spacing";
               }
               enum "1611.22" {
                 description "1611.22 nm/186.065625 THz 3.125GHz spacing";
               }
               enum "1611.19" {
                 description "1611.19 nm/186.068750 THz 3.125/6.25GHz spacing";
               }
               enum "1611.16" {
                 description "1611.16 nm/186.071875 THz 3.125GHz spacing";
               }
               enum "1611.14" {
                 description "1611.14 nm/186.075000 THz 3.125/6.25/12.5GHz spacing";
               }
               enum "1611.11" {
                 description "1611.11 nm/186.078125 THz 3.125GHz spacing";
               }
               enum "1611.08" {
                 description "1611.08 nm/186.081250 THz 3.125/6.25GHz spacing";
               }
               enum "1611.06" {
                 description "1611.06 nm/186.084375 THz 3.125GHz spacing";
               }
               enum "1611.03" {
                 description "1611.03 nm/186.087500 THz 3.125/6.25/12.5GHz spacing";
               }
               enum "1611.00" {
                 description "1611.00 nm/186.090625 THz 3.125GHz spacing";
               }
               enum "1610.98" {
                 description "1610.98 nm/186.093750 THz 3.125/6.25GHz spacing";
               }
               enum "1610.95" {
                 description "1610.95 nm/186.096875 THz 3.125GHz spacing";
               }
               enum "1610.92" {
                 description "1610.92 nm/186.100000 THz 3.125/6.25/12.5/100GHz spacing";
               }
               enum "1610.89" {
                 description "1610.89 nm/186.103125 THz 3.125GHz spacing";
               }
               enum "1610.87" {
                 description "1610.87 nm/186.106250 THz 3.125/6.25GHz spacing";
               }
               enum "1610.84" {
                 description "1610.84 nm/186.109375 THz 3.125GHz spacing";
               }
               enum "1610.81" {
                 description "1610.81 nm/186.112500 THz 3.125/6.25/12.5GHz spacing";
               }
               enum "1610.79" {
                 description "1610.79 nm/186.115625 THz 3.125GHz spacing";
               }
               enum "1610.76" {
                 description "1610.76 nm/186.118750 THz 3.125/6.25GHz spacing";
               }
               enum "1610.73" {
                 description "1610.73 nm/186.121875 THz 3.125GHz spacing";
               }
               enum "1610.70" {
                 description "1610.70 nm/186.125000 THz 3.125/6.25/12.5/75GHz spacing";
               }
               enum "1610.68" {
                 description "1610.68 nm/186.128125 THz 3.125GHz spacing";
               }
               enum "1610.65" {
                 description "1610.65 nm/186.131250 THz 3.125/6.25GHz spacing";
               }
               enum "1610.62" {
                 description "1610.62 nm/186.134375 THz 3.125GHz spacing";
               }
               enum "1610.60" {
                 description "1610.60 nm/186.137500 THz 3.125/6.25/12.5GHz spacing";
               }
               enum "1610.57" {
                 description "1610.57 nm/186.140625 THz 3.125GHz spacing";
               }
               enum "1610.54" {
                 description "1610.54 nm/186.143750 THz 3.125/6.25GHz spacing";
               }
               enum "1610.52" {
                 description "1610.52 nm/186.146875 THz 3.125GHz spacing";
               }
               enum "1610.49" {
                 description "1610.49 nm/186.150000 THz 3.125/6.25/12.5/50GHz spacing";
               }
               enum "1610.46" {
                 description "1610.46 nm/186.153125 THz 3.125GHz spacing";
               }
               enum "1610.43" {
                 description "1610.43 nm/186.156250 THz 3.125/6.25GHz spacing";
               }
               enum "1610.41" {
                 description "1610.41 nm/186.159375 THz 3.125GHz spacing";
               }
               enum "1610.38" {
                 description "1610.38 nm/186.162500 THz 3.125/6.25/12.5GHz spacing";
               }
               enum "1610.35" {
                 description "1610.35 nm/186.165625 THz 3.125GHz spacing";
               }
               enum "1610.33" {
                 description "1610.33 nm/186.168750 THz 3.125/6.25GHz spacing";
               }
               enum "1610.30" {
                 description "1610.30 nm/186.171875 THz 3.125GHz spacing";
               }
               enum "1610.27" {
                 description "1610.27 nm/186.175000 THz 3.125/6.25/12.5GHz spacing";
               }
               enum "1610.25" {
                 description "1610.25 nm/186.178125 THz 3.125GHz spacing";
               }
               enum "1610.22" {
                 description "1610.22 nm/186.181250 THz 3.125/6.25GHz spacing";
               }
               enum "1610.19" {
                 description "1610.19 nm/186.184375 THz 3.125GHz spacing";
               }
               enum "1610.16" {
                 description "1610.16 nm/186.187500 THz 3.125/6.25/12.5GHz spacing";
               }
               enum "1610.14" {
                 description "1610.14 nm/186.190625 THz 3.125GHz spacing";
               }
               enum "1610.11" {
                 description "1610.11 nm/186.193750 THz 3.125/6.25GHz spacing";
               }
               enum "1610.08" {
                 description "1610.08 nm/186.196875 THz 3.125GHz spacing";
               }
               enum "1610.06" {
                 description "1610.06 nm/186.200000 THz 3.125/6.25/12.5/100GHz spacing";
               }
               enum "1610.03" {
                 description "1610.03 nm/186.203125 THz 3.125GHz spacing";
               }
               enum "1610.00" {
                 description "1610.00 nm/186.206250 THz 3.125/6.25GHz spacing";
               }
               enum "1609.98" {
                 description "1609.98 nm/186.209375 THz 3.125GHz spacing";
               }
               enum "1609.95" {
                 description "1609.95 nm/186.212500 THz 3.125/6.25/12.5GHz spacing";
               }
               enum "1609.92" {
                 description "1609.92 nm/186.215625 THz 3.125GHz spacing";
               }
               enum "1609.89" {
                 description "1609.89 nm/186.218750 THz 3.125/6.25GHz spacing";
               }
               enum "1609.87" {
                 description "1609.87 nm/186.221875 THz 3.125GHz spacing";
               }
               enum "1609.84" {
                 description "1609.84 nm/186.225000 THz 3.125/6.25/12.5GHz spacing";
               }
               enum "1609.81" {
                 description "1609.81 nm/186.228125 THz 3.125GHz spacing";
               }
               enum "1609.79" {
                 description "1609.79 nm/186.231250 THz 3.125/6.25GHz spacing";
               }
               enum "1609.76" {
                 description "1609.76 nm/186.234375 THz 3.125GHz spacing";
               }
               enum "1609.73" {
                 description "1609.73 nm/186.237500 THz 3.125/6.25/12.5GHz spacing";
               }
               enum "1609.70" {
                 description "1609.70 nm/186.240625 THz 3.125GHz spacing";
               }
               enum "1609.68" {
                 description "1609.68 nm/186.243750 THz 3.125/6.25GHz spacing";
               }
               enum "1609.65" {
                 description "1609.65 nm/186.246875 THz 3.125GHz spacing";
               }
               enum "1609.62" {
                 description "1609.62 nm/186.250000 THz 3.125/6.25/12.5/50GHz spacing";
               }
               enum "1609.60" {
                 description "1609.60 nm/186.253125 THz 3.125GHz spacing";
               }
               enum "1609.57" {
                 description "1609.57 nm/186.256250 THz 3.125/6.25GHz spacing";
               }
               enum "1609.54" {
                 description "1609.54 nm/186.259375 THz 3.125GHz spacing";
               }
               enum "1609.52" {
                 description "1609.52 nm/186.262500 THz 3.125/6.25/12.5GHz spacing";
               }
               enum "1609.49" {
                 description "1609.49 nm/186.265625 THz 3.125GHz spacing";
               }
               enum "1609.46" {
                 description "1609.46 nm/186.268750 THz 3.125/6.25GHz spacing";
               }
               enum "1609.43" {
                 description "1609.43 nm/186.271875 THz 3.125GHz spacing";
               }
               enum "1609.41" {
                 description "1609.41 nm/186.275000 THz 3.125/6.25/12.5/75GHz spacing";
               }
               enum "1609.38" {
                 description "1609.38 nm/186.278125 THz 3.125GHz spacing";
               }
               enum "1609.35" {
                 description "1609.35 nm/186.281250 THz 3.125/6.25GHz spacing";
               }
               enum "1609.33" {
                 description "1609.33 nm/186.284375 THz 3.125GHz spacing";
               }
               enum "1609.30" {
                 description "1609.30 nm/186.287500 THz 3.125/6.25/12.5GHz spacing";
               }
               enum "1609.27" {
                 description "1609.27 nm/186.290625 THz 3.125GHz spacing";
               }
               enum "1609.25" {
                 description "1609.25 nm/186.293750 THz 3.125/6.25GHz spacing";
               }
               enum "1609.22" {
                 description "1609.22 nm/186.296875 THz 3.125GHz spacing";
               }
               enum "1609.19" {
                 description "1609.19 nm/186.300000 THz 3.125/6.25/12.5/50/75/100GHz spacing";
               }
               enum "1609.16" {
                 description "1609.16 nm/186.303125 THz 3.125GHz spacing";
               }
               enum "1609.14" {
                 description "1609.14 nm/186.306250 THz 3.125/6.25GHz spacing";
               }
               enum "1609.11" {
                 description "1609.11 nm/186.309375 THz 3.125GHz spacing";
               }
               enum "1609.08" {
                 description "1609.08 nm/186.312500 THz 3.125/6.25/12.5GHz spacing";
               }
               enum "1609.06" {
                 description "1609.06 nm/186.315625 THz 3.125GHz spacing";
               }
               enum "1609.03" {
                 description "1609.03 nm/186.318750 THz 3.125/6.25GHz spacing";
               }
               enum "1609.00" {
                 description "1609.00 nm/186.321875 THz 3.125GHz spacing";
               }
               enum "1608.98" {
                 description "1608.98 nm/186.325000 THz 3.125/6.25/12.5GHz spacing";
               }
               enum "1608.95" {
                 description "1608.95 nm/186.328125 THz 3.125GHz spacing";
               }
               enum "1608.92" {
                 description "1608.92 nm/186.331250 THz 3.125/6.25GHz spacing";
               }
               enum "1608.90" {
                 description "1608.90 nm/186.334375 THz 3.125GHz spacing";
               }
               enum "1608.87" {
                 description "1608.87 nm/186.337500 THz 3.125/6.25/12.5GHz spacing";
               }
               enum "1608.84" {
                 description "1608.84 nm/186.340625 THz 3.125GHz spacing";
               }
               enum "1608.81" {
                 description "1608.81 nm/186.343750 THz 3.125/6.25GHz spacing";
               }
               enum "1608.79" {
                 description "1608.79 nm/186.346875 THz 3.125GHz spacing";
               }
               enum "1608.76" {
                 description "1608.76 nm/186.350000 THz 3.125/6.25/12.5/50/75GHz spacing";
               }
               enum "1608.73" {
                 description "1608.73 nm/186.353125 THz 3.125GHz spacing";
               }
               enum "1608.71" {
                 description "1608.71 nm/186.356250 THz 3.125/6.25GHz spacing";
               }
               enum "1608.68" {
                 description "1608.68 nm/186.359375 THz 3.125GHz spacing";
               }
               enum "1608.65" {
                 description "1608.65 nm/186.362500 THz 3.125/6.25/12.5GHz spacing";
               }
               enum "1608.63" {
                 description "1608.63 nm/186.365625 THz 3.125GHz spacing";
               }
               enum "1608.60" {
                 description "1608.60 nm/186.368750 THz 3.125/6.25GHz spacing";
               }
               enum "1608.57" {
                 description "1608.57 nm/186.371875 THz 3.125GHz spacing";
               }
               enum "1608.54" {
                 description "1608.54 nm/186.375000 THz 3.125/6.25/12.5GHz spacing";
               }
               enum "1608.52" {
                 description "1608.52 nm/186.378125 THz 3.125GHz spacing";
               }
               enum "1608.49" {
                 description "1608.49 nm/186.381250 THz 3.125/6.25GHz spacing";
               }
               enum "1608.46" {
                 description "1608.46 nm/186.384375 THz 3.125GHz spacing";
               }
               enum "1608.44" {
                 description "1608.44 nm/186.387500 THz 3.125/6.25/12.5GHz spacing";
               }
               enum "1608.41" {
                 description "1608.41 nm/186.390625 THz 3.125GHz spacing";
               }
               enum "1608.38" {
                 description "1608.38 nm/186.393750 THz 3.125/6.25GHz spacing";
               }
               enum "1608.36" {
                 description "1608.36 nm/186.396875 THz 3.125GHz spacing";
               }
               enum "1608.33" {
                 description "1608.33 nm/186.400000 THz 3.125/6.25/12.5/100GHz spacing";
               }
               enum "1608.30" {
                 description "1608.30 nm/186.403125 THz 3.125GHz spacing";
               }
               enum "1608.27" {
                 description "1608.27 nm/186.406250 THz 3.125/6.25GHz spacing";
               }
               enum "1608.25" {
                 description "1608.25 nm/186.409375 THz 3.125GHz spacing";
               }
               enum "1608.22" {
                 description "1608.22 nm/186.412500 THz 3.125/6.25/12.5GHz spacing";
               }
               enum "1608.19" {
                 description "1608.19 nm/186.415625 THz 3.125GHz spacing";
               }
               enum "1608.17" {
                 description "1608.17 nm/186.418750 THz 3.125/6.25GHz spacing";
               }
               enum "1608.14" {
                 description "1608.14 nm/186.421875 THz 3.125GHz spacing";
               }
               enum "1608.11" {
                 description "1608.11 nm/186.425000 THz 3.125/6.25/12.5/75GHz spacing";
               }
               enum "1608.09" {
                 description "1608.09 nm/186.428125 THz 3.125GHz spacing";
               }
               enum "1608.06" {
                 description "1608.06 nm/186.431250 THz 3.125/6.25GHz spacing";
               }
               enum "1608.03" {
                 description "1608.03 nm/186.434375 THz 3.125GHz spacing";
               }
               enum "1608.01" {
                 description "1608.01 nm/186.437500 THz 3.125/6.25/12.5GHz spacing";
               }
               enum "1607.98" {
                 description "1607.98 nm/186.440625 THz 3.125GHz spacing";
               }
               enum "1607.95" {
                 description "1607.95 nm/186.443750 THz 3.125/6.25GHz spacing";
               }
               enum "1607.92" {
                 description "1607.92 nm/186.446875 THz 3.125GHz spacing";
               }
               enum "1607.90" {
                 description "1607.90 nm/186.450000 THz 3.125/6.25/12.5/50GHz spacing";
               }
               enum "1607.87" {
                 description "1607.87 nm/186.453125 THz 3.125GHz spacing";
               }
               enum "1607.84" {
                 description "1607.84 nm/186.456250 THz 3.125/6.25GHz spacing";
               }
               enum "1607.82" {
                 description "1607.82 nm/186.459375 THz 3.125GHz spacing";
               }
               enum "1607.79" {
                 description "1607.79 nm/186.462500 THz 3.125/6.25/12.5GHz spacing";
               }
               enum "1607.76" {
                 description "1607.76 nm/186.465625 THz 3.125GHz spacing";
               }
               enum "1607.74" {
                 description "1607.74 nm/186.468750 THz 3.125/6.25GHz spacing";
               }
               enum "1607.71" {
                 description "1607.71 nm/186.471875 THz 3.125GHz spacing";
               }
               enum "1607.68" {
                 description "1607.68 nm/186.475000 THz 3.125/6.25/12.5GHz spacing";
               }
               enum "1607.65" {
                 description "1607.65 nm/186.478125 THz 3.125GHz spacing";
               }
               enum "1607.63" {
                 description "1607.63 nm/186.481250 THz 3.125/6.25GHz spacing";
               }
               enum "1607.60" {
                 description "1607.60 nm/186.484375 THz 3.125GHz spacing";
               }
               enum "1607.57" {
                 description "1607.57 nm/186.487500 THz 3.125/6.25/12.5GHz spacing";
               }
               enum "1607.55" {
                 description "1607.55 nm/186.490625 THz 3.125GHz spacing";
               }
               enum "1607.52" {
                 description "1607.52 nm/186.493750 THz 3.125/6.25GHz spacing";
               }
               enum "1607.49" {
                 description "1607.49 nm/186.496875 THz 3.125GHz spacing";
               }
               enum "1607.47" {
                 description "1607.47 nm/186.500000 THz 3.125/6.25/12.5/100GHz spacing";
               }
               enum "1607.44" {
                 description "1607.44 nm/186.503125 THz 3.125GHz spacing";
               }
               enum "1607.41" {
                 description "1607.41 nm/186.506250 THz 3.125/6.25GHz spacing";
               }
               enum "1607.39" {
                 description "1607.39 nm/186.509375 THz 3.125GHz spacing";
               }
               enum "1607.36" {
                 description "1607.36 nm/186.512500 THz 3.125/6.25/12.5GHz spacing";
               }
               enum "1607.33" {
                 description "1607.33 nm/186.515625 THz 3.125GHz spacing";
               }
               enum "1607.30" {
                 description "1607.30 nm/186.518750 THz 3.125/6.25GHz spacing";
               }
               enum "1607.28" {
                 description "1607.28 nm/186.521875 THz 3.125GHz spacing";
               }
               enum "1607.25" {
                 description "1607.25 nm/186.525000 THz 3.125/6.25/12.5GHz spacing";
               }
               enum "1607.22" {
                 description "1607.22 nm/186.528125 THz 3.125GHz spacing";
               }
               enum "1607.20" {
                 description "1607.20 nm/186.531250 THz 3.125/6.25GHz spacing";
               }
               enum "1607.17" {
                 description "1607.17 nm/186.534375 THz 3.125GHz spacing";
               }
               enum "1607.14" {
                 description "1607.14 nm/186.537500 THz 3.125/6.25/12.5GHz spacing";
               }
               enum "1607.12" {
                 description "1607.12 nm/186.540625 THz 3.125GHz spacing";
               }
               enum "1607.09" {
                 description "1607.09 nm/186.543750 THz 3.125/6.25GHz spacing";
               }
               enum "1607.06" {
                 description "1607.06 nm/186.546875 THz 3.125GHz spacing";
               }
               enum "1607.04" {
                 description "1607.04 nm/186.550000 THz 3.125/6.25/12.5/50GHz spacing";
               }
               enum "1607.01" {
                 description "1607.01 nm/186.553125 THz 3.125GHz spacing";
               }
               enum "1606.98" {
                 description "1606.98 nm/186.556250 THz 3.125/6.25GHz spacing";
               }
               enum "1606.95" {
                 description "1606.95 nm/186.559375 THz 3.125GHz spacing";
               }
               enum "1606.93" {
                 description "1606.93 nm/186.562500 THz 3.125/6.25/12.5GHz spacing";
               }
               enum "1606.90" {
                 description "1606.90 nm/186.565625 THz 3.125GHz spacing";
               }
               enum "1606.87" {
                 description "1606.87 nm/186.568750 THz 3.125/6.25GHz spacing";
               }
               enum "1606.85" {
                 description "1606.85 nm/186.571875 THz 3.125GHz spacing";
               }
               enum "1606.82" {
                 description "1606.82 nm/186.575000 THz 3.125/6.25/12.5/75GHz spacing";
               }
               enum "1606.79" {
                 description "1606.79 nm/186.578125 THz 3.125GHz spacing";
               }
               enum "1606.77" {
                 description "1606.77 nm/186.581250 THz 3.125/6.25GHz spacing";
               }
               enum "1606.74" {
                 description "1606.74 nm/186.584375 THz 3.125GHz spacing";
               }
               enum "1606.71" {
                 description "1606.71 nm/186.587500 THz 3.125/6.25/12.5GHz spacing";
               }
               enum "1606.69" {
                 description "1606.69 nm/186.590625 THz 3.125GHz spacing";
               }
               enum "1606.66" {
                 description "1606.66 nm/186.593750 THz 3.125/6.25GHz spacing";
               }
               enum "1606.63" {
                 description "1606.63 nm/186.596875 THz 3.125GHz spacing";
               }
               enum "1606.60" {
                 description "1606.60 nm/186.600000 THz 3.125/6.25/12.5/50/75/100GHz spacing";
               }
               enum "1606.58" {
                 description "1606.58 nm/186.603125 THz 3.125GHz spacing";
               }
               enum "1606.55" {
                 description "1606.55 nm/186.606250 THz 3.125/6.25GHz spacing";
               }
               enum "1606.52" {
                 description "1606.52 nm/186.609375 THz 3.125GHz spacing";
               }
               enum "1606.50" {
                 description "1606.50 nm/186.612500 THz 3.125/6.25/12.5GHz spacing";
               }
               enum "1606.47" {
                 description "1606.47 nm/186.615625 THz 3.125GHz spacing";
               }
               enum "1606.44" {
                 description "1606.44 nm/186.618750 THz 3.125/6.25GHz spacing";
               }
               enum "1606.42" {
                 description "1606.42 nm/186.621875 THz 3.125GHz spacing";
               }
               enum "1606.39" {
                 description "1606.39 nm/186.625000 THz 3.125/6.25/12.5GHz spacing";
               }
               enum "1606.36" {
                 description "1606.36 nm/186.628125 THz 3.125GHz spacing";
               }
               enum "1606.34" {
                 description "1606.34 nm/186.631250 THz 3.125/6.25GHz spacing";
               }
               enum "1606.31" {
                 description "1606.31 nm/186.634375 THz 3.125GHz spacing";
               }
               enum "1606.28" {
                 description "1606.28 nm/186.637500 THz 3.125/6.25/12.5GHz spacing";
               }
               enum "1606.26" {
                 description "1606.26 nm/186.640625 THz 3.125GHz spacing";
               }
               enum "1606.23" {
                 description "1606.23 nm/186.643750 THz 3.125/6.25GHz spacing";
               }
               enum "1606.20" {
                 description "1606.20 nm/186.646875 THz 3.125GHz spacing";
               }
               enum "1606.17" {
                 description "1606.17 nm/186.650000 THz 3.125/6.25/12.5/50/75GHz spacing";
               }
               enum "1606.15" {
                 description "1606.15 nm/186.653125 THz 3.125GHz spacing";
               }
               enum "1606.12" {
                 description "1606.12 nm/186.656250 THz 3.125/6.25GHz spacing";
               }
               enum "1606.09" {
                 description "1606.09 nm/186.659375 THz 3.125GHz spacing";
               }
               enum "1606.07" {
                 description "1606.07 nm/186.662500 THz 3.125/6.25/12.5GHz spacing";
               }
               enum "1606.04" {
                 description "1606.04 nm/186.665625 THz 3.125GHz spacing";
               }
               enum "1606.01" {
                 description "1606.01 nm/186.668750 THz 3.125/6.25GHz spacing";
               }
               enum "1605.99" {
                 description "1605.99 nm/186.671875 THz 3.125GHz spacing";
               }
               enum "1605.96" {
                 description "1605.96 nm/186.675000 THz 3.125/6.25/12.5GHz spacing";
               }
               enum "1605.93" {
                 description "1605.93 nm/186.678125 THz 3.125GHz spacing";
               }
               enum "1605.91" {
                 description "1605.91 nm/186.681250 THz 3.125/6.25GHz spacing";
               }
               enum "1605.88" {
                 description "1605.88 nm/186.684375 THz 3.125GHz spacing";
               }
               enum "1605.85" {
                 description "1605.85 nm/186.687500 THz 3.125/6.25/12.5GHz spacing";
               }
               enum "1605.82" {
                 description "1605.82 nm/186.690625 THz 3.125GHz spacing";
               }
               enum "1605.80" {
                 description "1605.80 nm/186.693750 THz 3.125/6.25GHz spacing";
               }
               enum "1605.77" {
                 description "1605.77 nm/186.696875 THz 3.125GHz spacing";
               }
               enum "1605.74" {
                 description "1605.74 nm/186.700000 THz 3.125/6.25/12.5/100GHz spacing";
               }
               enum "1605.72" {
                 description "1605.72 nm/186.703125 THz 3.125GHz spacing";
               }
               enum "1605.69" {
                 description "1605.69 nm/186.706250 THz 3.125/6.25GHz spacing";
               }
               enum "1605.66" {
                 description "1605.66 nm/186.709375 THz 3.125GHz spacing";
               }
               enum "1605.64" {
                 description "1605.64 nm/186.712500 THz 3.125/6.25/12.5GHz spacing";
               }
               enum "1605.61" {
                 description "1605.61 nm/186.715625 THz 3.125GHz spacing";
               }
               enum "1605.58" {
                 description "1605.58 nm/186.718750 THz 3.125/6.25GHz spacing";
               }
               enum "1605.56" {
                 description "1605.56 nm/186.721875 THz 3.125GHz spacing";
               }
               enum "1605.53" {
                 description "1605.53 nm/186.725000 THz 3.125/6.25/12.5/75GHz spacing";
               }
               enum "1605.50" {
                 description "1605.50 nm/186.728125 THz 3.125GHz spacing";
               }
               enum "1605.48" {
                 description "1605.48 nm/186.731250 THz 3.125/6.25GHz spacing";
               }
               enum "1605.45" {
                 description "1605.45 nm/186.734375 THz 3.125GHz spacing";
               }
               enum "1605.42" {
                 description "1605.42 nm/186.737500 THz 3.125/6.25/12.5GHz spacing";
               }
               enum "1605.39" {
                 description "1605.39 nm/186.740625 THz 3.125GHz spacing";
               }
               enum "1605.37" {
                 description "1605.37 nm/186.743750 THz 3.125/6.25GHz spacing";
               }
               enum "1605.34" {
                 description "1605.34 nm/186.746875 THz 3.125GHz spacing";
               }
               enum "1605.31" {
                 description "1605.31 nm/186.750000 THz 3.125/6.25/12.5/50GHz spacing";
               }
               enum "1605.29" {
                 description "1605.29 nm/186.753125 THz 3.125GHz spacing";
               }
               enum "1605.26" {
                 description "1605.26 nm/186.756250 THz 3.125/6.25GHz spacing";
               }
               enum "1605.23" {
                 description "1605.23 nm/186.759375 THz 3.125GHz spacing";
               }
               enum "1605.21" {
                 description "1605.21 nm/186.762500 THz 3.125/6.25/12.5GHz spacing";
               }
               enum "1605.18" {
                 description "1605.18 nm/186.765625 THz 3.125GHz spacing";
               }
               enum "1605.15" {
                 description "1605.15 nm/186.768750 THz 3.125/6.25GHz spacing";
               }
               enum "1605.13" {
                 description "1605.13 nm/186.771875 THz 3.125GHz spacing";
               }
               enum "1605.10" {
                 description "1605.10 nm/186.775000 THz 3.125/6.25/12.5GHz spacing";
               }
               enum "1605.07" {
                 description "1605.07 nm/186.778125 THz 3.125GHz spacing";
               }
               enum "1605.05" {
                 description "1605.05 nm/186.781250 THz 3.125/6.25GHz spacing";
               }
               enum "1605.02" {
                 description "1605.02 nm/186.784375 THz 3.125GHz spacing";
               }
               enum "1604.99" {
                 description "1604.99 nm/186.787500 THz 3.125/6.25/12.5GHz spacing";
               }
               enum "1604.97" {
                 description "1604.97 nm/186.790625 THz 3.125GHz spacing";
               }
               enum "1604.94" {
                 description "1604.94 nm/186.793750 THz 3.125/6.25GHz spacing";
               }
               enum "1604.91" {
                 description "1604.91 nm/186.796875 THz 3.125GHz spacing";
               }
               enum "1604.88" {
                 description "1604.88 nm/186.800000 THz 3.125/6.25/12.5/100GHz spacing";
               }
               enum "1604.86" {
                 description "1604.86 nm/186.803125 THz 3.125GHz spacing";
               }
               enum "1604.83" {
                 description "1604.83 nm/186.806250 THz 3.125/6.25GHz spacing";
               }
               enum "1604.80" {
                 description "1604.80 nm/186.809375 THz 3.125GHz spacing";
               }
               enum "1604.78" {
                 description "1604.78 nm/186.812500 THz 3.125/6.25/12.5GHz spacing";
               }
               enum "1604.75" {
                 description "1604.75 nm/186.815625 THz 3.125GHz spacing";
               }
               enum "1604.72" {
                 description "1604.72 nm/186.818750 THz 3.125/6.25GHz spacing";
               }
               enum "1604.70" {
                 description "1604.70 nm/186.821875 THz 3.125GHz spacing";
               }
               enum "1604.67" {
                 description "1604.67 nm/186.825000 THz 3.125/6.25/12.5GHz spacing";
               }
               enum "1604.64" {
                 description "1604.64 nm/186.828125 THz 3.125GHz spacing";
               }
               enum "1604.62" {
                 description "1604.62 nm/186.831250 THz 3.125/6.25GHz spacing";
               }
               enum "1604.59" {
                 description "1604.59 nm/186.834375 THz 3.125GHz spacing";
               }
               enum "1604.56" {
                 description "1604.56 nm/186.837500 THz 3.125/6.25/12.5GHz spacing";
               }
               enum "1604.54" {
                 description "1604.54 nm/186.840625 THz 3.125GHz spacing";
               }
               enum "1604.51" {
                 description "1604.51 nm/186.843750 THz 3.125/6.25GHz spacing";
               }
               enum "1604.48" {
                 description "1604.48 nm/186.846875 THz 3.125GHz spacing";
               }
               enum "1604.46" {
                 description "1604.46 nm/186.850000 THz 3.125/6.25/12.5/50GHz spacing";
               }
               enum "1604.43" {
                 description "1604.43 nm/186.853125 THz 3.125GHz spacing";
               }
               enum "1604.40" {
                 description "1604.40 nm/186.856250 THz 3.125/6.25GHz spacing";
               }
               enum "1604.37" {
                 description "1604.37 nm/186.859375 THz 3.125GHz spacing";
               }
               enum "1604.35" {
                 description "1604.35 nm/186.862500 THz 3.125/6.25/12.5GHz spacing";
               }
               enum "1604.32" {
                 description "1604.32 nm/186.865625 THz 3.125GHz spacing";
               }
               enum "1604.29" {
                 description "1604.29 nm/186.868750 THz 3.125/6.25GHz spacing";
               }
               enum "1604.27" {
                 description "1604.27 nm/186.871875 THz 3.125GHz spacing";
               }
               enum "1604.24" {
                 description "1604.24 nm/186.875000 THz 3.125/6.25/12.5/75GHz spacing";
               }
               enum "1604.21" {
                 description "1604.21 nm/186.878125 THz 3.125GHz spacing";
               }
               enum "1604.19" {
                 description "1604.19 nm/186.881250 THz 3.125/6.25GHz spacing";
               }
               enum "1604.16" {
                 description "1604.16 nm/186.884375 THz 3.125GHz spacing";
               }
               enum "1604.13" {
                 description "1604.13 nm/186.887500 THz 3.125/6.25/12.5GHz spacing";
               }
               enum "1604.11" {
                 description "1604.11 nm/186.890625 THz 3.125GHz spacing";
               }
               enum "1604.08" {
                 description "1604.08 nm/186.893750 THz 3.125/6.25GHz spacing";
               }
               enum "1604.05" {
                 description "1604.05 nm/186.896875 THz 3.125GHz spacing";
               }
               enum "1604.03" {
                 description "1604.03 nm/186.900000 THz 3.125/6.25/12.5/50/75/100GHz spacing";
               }
               enum "1604.00" {
                 description "1604.00 nm/186.903125 THz 3.125GHz spacing";
               }
               enum "1603.97" {
                 description "1603.97 nm/186.906250 THz 3.125/6.25GHz spacing";
               }
               enum "1603.95" {
                 description "1603.95 nm/186.909375 THz 3.125GHz spacing";
               }
               enum "1603.92" {
                 description "1603.92 nm/186.912500 THz 3.125/6.25/12.5GHz spacing";
               }
               enum "1603.89" {
                 description "1603.89 nm/186.915625 THz 3.125GHz spacing";
               }
               enum "1603.87" {
                 description "1603.87 nm/186.918750 THz 3.125/6.25GHz spacing";
               }
               enum "1603.84" {
                 description "1603.84 nm/186.921875 THz 3.125GHz spacing";
               }
               enum "1603.81" {
                 description "1603.81 nm/186.925000 THz 3.125/6.25/12.5GHz spacing";
               }
               enum "1603.78" {
                 description "1603.78 nm/186.928125 THz 3.125GHz spacing";
               }
               enum "1603.76" {
                 description "1603.76 nm/186.931250 THz 3.125/6.25GHz spacing";
               }
               enum "1603.73" {
                 description "1603.73 nm/186.934375 THz 3.125GHz spacing";
               }
               enum "1603.70" {
                 description "1603.70 nm/186.937500 THz 3.125/6.25/12.5GHz spacing";
               }
               enum "1603.68" {
                 description "1603.68 nm/186.940625 THz 3.125GHz spacing";
               }
               enum "1603.65" {
                 description "1603.65 nm/186.943750 THz 3.125/6.25GHz spacing";
               }
               enum "1603.62" {
                 description "1603.62 nm/186.946875 THz 3.125GHz spacing";
               }
               enum "1603.60" {
                 description "1603.60 nm/186.950000 THz 3.125/6.25/12.5/50/75GHz spacing";
               }
               enum "1603.57" {
                 description "1603.57 nm/186.953125 THz 3.125GHz spacing";
               }
               enum "1603.54" {
                 description "1603.54 nm/186.956250 THz 3.125/6.25GHz spacing";
               }
               enum "1603.52" {
                 description "1603.52 nm/186.959375 THz 3.125GHz spacing";
               }
               enum "1603.49" {
                 description "1603.49 nm/186.962500 THz 3.125/6.25/12.5GHz spacing";
               }
               enum "1603.46" {
                 description "1603.46 nm/186.965625 THz 3.125GHz spacing";
               }
               enum "1603.44" {
                 description "1603.44 nm/186.968750 THz 3.125/6.25GHz spacing";
               }
               enum "1603.41" {
                 description "1603.41 nm/186.971875 THz 3.125GHz spacing";
               }
               enum "1603.38" {
                 description "1603.38 nm/186.975000 THz 3.125/6.25/12.5GHz spacing";
               }
               enum "1603.36" {
                 description "1603.36 nm/186.978125 THz 3.125GHz spacing";
               }
               enum "1603.33" {
                 description "1603.33 nm/186.981250 THz 3.125/6.25GHz spacing";
               }
               enum "1603.30" {
                 description "1603.30 nm/186.984375 THz 3.125GHz spacing";
               }
               enum "1603.28" {
                 description "1603.28 nm/186.987500 THz 3.125/6.25/12.5GHz spacing";
               }
               enum "1603.25" {
                 description "1603.25 nm/186.990625 THz 3.125GHz spacing";
               }
               enum "1603.22" {
                 description "1603.22 nm/186.993750 THz 3.125/6.25GHz spacing";
               }
               enum "1603.20" {
                 description "1603.20 nm/186.996875 THz 3.125GHz spacing";
               }
               enum "1603.17" {
                 description "1603.17 nm/187.000000 THz 3.125/6.25/12.5/100GHz spacing";
               }
               enum "1603.14" {
                 description "1603.14 nm/187.003125 THz 3.125GHz spacing";
               }
               enum "1603.11" {
                 description "1603.11 nm/187.006250 THz 3.125/6.25GHz spacing";
               }
               enum "1603.09" {
                 description "1603.09 nm/187.009375 THz 3.125GHz spacing";
               }
               enum "1603.06" {
                 description "1603.06 nm/187.012500 THz 3.125/6.25/12.5GHz spacing";
               }
               enum "1603.03" {
                 description "1603.03 nm/187.015625 THz 3.125GHz spacing";
               }
               enum "1603.01" {
                 description "1603.01 nm/187.018750 THz 3.125/6.25GHz spacing";
               }
               enum "1602.98" {
                 description "1602.98 nm/187.021875 THz 3.125GHz spacing";
               }
               enum "1602.95" {
                 description "1602.95 nm/187.025000 THz 3.125/6.25/12.5/75GHz spacing";
               }
               enum "1602.93" {
                 description "1602.93 nm/187.028125 THz 3.125GHz spacing";
               }
               enum "1602.90" {
                 description "1602.90 nm/187.031250 THz 3.125/6.25GHz spacing";
               }
               enum "1602.87" {
                 description "1602.87 nm/187.034375 THz 3.125GHz spacing";
               }
               enum "1602.85" {
                 description "1602.85 nm/187.037500 THz 3.125/6.25/12.5GHz spacing";
               }
               enum "1602.82" {
                 description "1602.82 nm/187.040625 THz 3.125GHz spacing";
               }
               enum "1602.79" {
                 description "1602.79 nm/187.043750 THz 3.125/6.25GHz spacing";
               }
               enum "1602.77" {
                 description "1602.77 nm/187.046875 THz 3.125GHz spacing";
               }
               enum "1602.74" {
                 description "1602.74 nm/187.050000 THz 3.125/6.25/12.5/50GHz spacing";
               }
               enum "1602.71" {
                 description "1602.71 nm/187.053125 THz 3.125GHz spacing";
               }
               enum "1602.69" {
                 description "1602.69 nm/187.056250 THz 3.125/6.25GHz spacing";
               }
               enum "1602.66" {
                 description "1602.66 nm/187.059375 THz 3.125GHz spacing";
               }
               enum "1602.63" {
                 description "1602.63 nm/187.062500 THz 3.125/6.25/12.5GHz spacing";
               }
               enum "1602.61" {
                 description "1602.61 nm/187.065625 THz 3.125GHz spacing";
               }
               enum "1602.58" {
                 description "1602.58 nm/187.068750 THz 3.125/6.25GHz spacing";
               }
               enum "1602.55" {
                 description "1602.55 nm/187.071875 THz 3.125GHz spacing";
               }
               enum "1602.53" {
                 description "1602.53 nm/187.075000 THz 3.125/6.25/12.5GHz spacing";
               }
               enum "1602.50" {
                 description "1602.50 nm/187.078125 THz 3.125GHz spacing";
               }
               enum "1602.47" {
                 description "1602.47 nm/187.081250 THz 3.125/6.25GHz spacing";
               }
               enum "1602.45" {
                 description "1602.45 nm/187.084375 THz 3.125GHz spacing";
               }
               enum "1602.42" {
                 description "1602.42 nm/187.087500 THz 3.125/6.25/12.5GHz spacing";
               }
               enum "1602.39" {
                 description "1602.39 nm/187.090625 THz 3.125GHz spacing";
               }
               enum "1602.36" {
                 description "1602.36 nm/187.093750 THz 3.125/6.25GHz spacing";
               }
               enum "1602.34" {
                 description "1602.34 nm/187.096875 THz 3.125GHz spacing";
               }
               enum "1602.31" {
                 description "1602.31 nm/187.100000 THz 3.125/6.25/12.5/100GHz spacing";
               }
               enum "1602.28" {
                 description "1602.28 nm/187.103125 THz 3.125GHz spacing";
               }
               enum "1602.26" {
                 description "1602.26 nm/187.106250 THz 3.125/6.25GHz spacing";
               }
               enum "1602.23" {
                 description "1602.23 nm/187.109375 THz 3.125GHz spacing";
               }
               enum "1602.20" {
                 description "1602.20 nm/187.112500 THz 3.125/6.25/12.5GHz spacing";
               }
               enum "1602.18" {
                 description "1602.18 nm/187.115625 THz 3.125GHz spacing";
               }
               enum "1602.15" {
                 description "1602.15 nm/187.118750 THz 3.125/6.25GHz spacing";
               }
               enum "1602.12" {
                 description "1602.12 nm/187.121875 THz 3.125GHz spacing";
               }
               enum "1602.10" {
                 description "1602.10 nm/187.125000 THz 3.125/6.25/12.5GHz spacing";
               }
               enum "1602.07" {
                 description "1602.07 nm/187.128125 THz 3.125GHz spacing";
               }
               enum "1602.04" {
                 description "1602.04 nm/187.131250 THz 3.125/6.25GHz spacing";
               }
               enum "1602.02" {
                 description "1602.02 nm/187.134375 THz 3.125GHz spacing";
               }
               enum "1601.99" {
                 description "1601.99 nm/187.137500 THz 3.125/6.25/12.5GHz spacing";
               }
               enum "1601.96" {
                 description "1601.96 nm/187.140625 THz 3.125GHz spacing";
               }
               enum "1601.94" {
                 description "1601.94 nm/187.143750 THz 3.125/6.25GHz spacing";
               }
               enum "1601.91" {
                 description "1601.91 nm/187.146875 THz 3.125GHz spacing";
               }
               enum "1601.88" {
                 description "1601.88 nm/187.150000 THz 3.125/6.25/12.5/50GHz spacing";
               }
               enum "1601.86" {
                 description "1601.86 nm/187.153125 THz 3.125GHz spacing";
               }
               enum "1601.83" {
                 description "1601.83 nm/187.156250 THz 3.125/6.25GHz spacing";
               }
               enum "1601.80" {
                 description "1601.80 nm/187.159375 THz 3.125GHz spacing";
               }
               enum "1601.78" {
                 description "1601.78 nm/187.162500 THz 3.125/6.25/12.5GHz spacing";
               }
               enum "1601.75" {
                 description "1601.75 nm/187.165625 THz 3.125GHz spacing";
               }
               enum "1601.72" {
                 description "1601.72 nm/187.168750 THz 3.125/6.25GHz spacing";
               }
               enum "1601.70" {
                 description "1601.70 nm/187.171875 THz 3.125GHz spacing";
               }
               enum "1601.67" {
                 description "1601.67 nm/187.175000 THz 3.125/6.25/12.5/75GHz spacing";
               }
               enum "1601.64" {
                 description "1601.64 nm/187.178125 THz 3.125GHz spacing";
               }
               enum "1601.62" {
                 description "1601.62 nm/187.181250 THz 3.125/6.25GHz spacing";
               }
               enum "1601.59" {
                 description "1601.59 nm/187.184375 THz 3.125GHz spacing";
               }
               enum "1601.56" {
                 description "1601.56 nm/187.187500 THz 3.125/6.25/12.5GHz spacing";
               }
               enum "1601.54" {
                 description "1601.54 nm/187.190625 THz 3.125GHz spacing";
               }
               enum "1601.51" {
                 description "1601.51 nm/187.193750 THz 3.125/6.25GHz spacing";
               }
               enum "1601.48" {
                 description "1601.48 nm/187.196875 THz 3.125GHz spacing";
               }
               enum "1601.46" {
                 description "1601.46 nm/187.200000 THz 3.125/6.25/12.5/50/75/100GHz spacing";
               }
               enum "1601.43" {
                 description "1601.43 nm/187.203125 THz 3.125GHz spacing";
               }
               enum "1601.40" {
                 description "1601.40 nm/187.206250 THz 3.125/6.25GHz spacing";
               }
               enum "1601.38" {
                 description "1601.38 nm/187.209375 THz 3.125GHz spacing";
               }
               enum "1601.35" {
                 description "1601.35 nm/187.212500 THz 3.125/6.25/12.5GHz spacing";
               }
               enum "1601.32" {
                 description "1601.32 nm/187.215625 THz 3.125GHz spacing";
               }
               enum "1601.30" {
                 description "1601.30 nm/187.218750 THz 3.125/6.25GHz spacing";
               }
               enum "1601.27" {
                 description "1601.27 nm/187.221875 THz 3.125GHz spacing";
               }
               enum "1601.24" {
                 description "1601.24 nm/187.225000 THz 3.125/6.25/12.5GHz spacing";
               }
               enum "1601.21" {
                 description "1601.21 nm/187.228125 THz 3.125GHz spacing";
               }
               enum "1601.19" {
                 description "1601.19 nm/187.231250 THz 3.125/6.25GHz spacing";
               }
               enum "1601.16" {
                 description "1601.16 nm/187.234375 THz 3.125GHz spacing";
               }
               enum "1601.13" {
                 description "1601.13 nm/187.237500 THz 3.125/6.25/12.5GHz spacing";
               }
               enum "1601.11" {
                 description "1601.11 nm/187.240625 THz 3.125GHz spacing";
               }
               enum "1601.08" {
                 description "1601.08 nm/187.243750 THz 3.125/6.25GHz spacing";
               }
               enum "1601.05" {
                 description "1601.05 nm/187.246875 THz 3.125GHz spacing";
               }
               enum "1601.03" {
                 description "1601.03 nm/187.250000 THz 3.125/6.25/12.5/50/75GHz spacing";
               }
               enum "1601.00" {
                 description "1601.00 nm/187.253125 THz 3.125GHz spacing";
               }
               enum "1600.97" {
                 description "1600.97 nm/187.256250 THz 3.125/6.25GHz spacing";
               }
               enum "1600.95" {
                 description "1600.95 nm/187.259375 THz 3.125GHz spacing";
               }
               enum "1600.92" {
                 description "1600.92 nm/187.262500 THz 3.125/6.25/12.5GHz spacing";
               }
               enum "1600.89" {
                 description "1600.89 nm/187.265625 THz 3.125GHz spacing";
               }
               enum "1600.87" {
                 description "1600.87 nm/187.268750 THz 3.125/6.25GHz spacing";
               }
               enum "1600.84" {
                 description "1600.84 nm/187.271875 THz 3.125GHz spacing";
               }
               enum "1600.81" {
                 description "1600.81 nm/187.275000 THz 3.125/6.25/12.5GHz spacing";
               }
               enum "1600.79" {
                 description "1600.79 nm/187.278125 THz 3.125GHz spacing";
               }
               enum "1600.76" {
                 description "1600.76 nm/187.281250 THz 3.125/6.25GHz spacing";
               }
               enum "1600.73" {
                 description "1600.73 nm/187.284375 THz 3.125GHz spacing";
               }
               enum "1600.71" {
                 description "1600.71 nm/187.287500 THz 3.125/6.25/12.5GHz spacing";
               }
               enum "1600.68" {
                 description "1600.68 nm/187.290625 THz 3.125GHz spacing";
               }
               enum "1600.65" {
                 description "1600.65 nm/187.293750 THz 3.125/6.25GHz spacing";
               }
               enum "1600.63" {
                 description "1600.63 nm/187.296875 THz 3.125GHz spacing";
               }
               enum "1600.60" {
                 description "1600.60 nm/187.300000 THz 3.125/6.25/12.5/100GHz spacing";
               }
               enum "1600.57" {
                 description "1600.57 nm/187.303125 THz 3.125GHz spacing";
               }
               enum "1600.55" {
                 description "1600.55 nm/187.306250 THz 3.125/6.25GHz spacing";
               }
               enum "1600.52" {
                 description "1600.52 nm/187.309375 THz 3.125GHz spacing";
               }
               enum "1600.49" {
                 description "1600.49 nm/187.312500 THz 3.125/6.25/12.5GHz spacing";
               }
               enum "1600.47" {
                 description "1600.47 nm/187.315625 THz 3.125GHz spacing";
               }
               enum "1600.44" {
                 description "1600.44 nm/187.318750 THz 3.125/6.25GHz spacing";
               }
               enum "1600.41" {
                 description "1600.41 nm/187.321875 THz 3.125GHz spacing";
               }
               enum "1600.39" {
                 description "1600.39 nm/187.325000 THz 3.125/6.25/12.5/75GHz spacing";
               }
               enum "1600.36" {
                 description "1600.36 nm/187.328125 THz 3.125GHz spacing";
               }
               enum "1600.33" {
                 description "1600.33 nm/187.331250 THz 3.125/6.25GHz spacing";
               }
               enum "1600.31" {
                 description "1600.31 nm/187.334375 THz 3.125GHz spacing";
               }
               enum "1600.28" {
                 description "1600.28 nm/187.337500 THz 3.125/6.25/12.5GHz spacing";
               }
               enum "1600.25" {
                 description "1600.25 nm/187.340625 THz 3.125GHz spacing";
               }
               enum "1600.23" {
                 description "1600.23 nm/187.343750 THz 3.125/6.25GHz spacing";
               }
               enum "1600.20" {
                 description "1600.20 nm/187.346875 THz 3.125GHz spacing";
               }
               enum "1600.17" {
                 description "1600.17 nm/187.350000 THz 3.125/6.25/12.5/50GHz spacing";
               }
               enum "1600.15" {
                 description "1600.15 nm/187.353125 THz 3.125GHz spacing";
               }
               enum "1600.12" {
                 description "1600.12 nm/187.356250 THz 3.125/6.25GHz spacing";
               }
               enum "1600.09" {
                 description "1600.09 nm/187.359375 THz 3.125GHz spacing";
               }
               enum "1600.07" {
                 description "1600.07 nm/187.362500 THz 3.125/6.25/12.5GHz spacing";
               }
               enum "1600.04" {
                 description "1600.04 nm/187.365625 THz 3.125GHz spacing";
               }
               enum "1600.01" {
                 description "1600.01 nm/187.368750 THz 3.125/6.25GHz spacing";
               }
               enum "1599.99" {
                 description "1599.99 nm/187.371875 THz 3.125GHz spacing";
               }
               enum "1599.96" {
                 description "1599.96 nm/187.375000 THz 3.125/6.25/12.5GHz spacing";
               }
               enum "1599.93" {
                 description "1599.93 nm/187.378125 THz 3.125GHz spacing";
               }
               enum "1599.91" {
                 description "1599.91 nm/187.381250 THz 3.125/6.25GHz spacing";
               }
               enum "1599.88" {
                 description "1599.88 nm/187.384375 THz 3.125GHz spacing";
               }
               enum "1599.85" {
                 description "1599.85 nm/187.387500 THz 3.125/6.25/12.5GHz spacing";
               }
               enum "1599.83" {
                 description "1599.83 nm/187.390625 THz 3.125GHz spacing";
               }
               enum "1599.80" {
                 description "1599.80 nm/187.393750 THz 3.125/6.25GHz spacing";
               }
               enum "1599.77" {
                 description "1599.77 nm/187.396875 THz 3.125GHz spacing";
               }
               enum "1599.75" {
                 description "1599.75 nm/187.400000 THz 3.125/6.25/12.5/100GHz spacing";
               }
               enum "1599.72" {
                 description "1599.72 nm/187.403125 THz 3.125GHz spacing";
               }
               enum "1599.69" {
                 description "1599.69 nm/187.406250 THz 3.125/6.25GHz spacing";
               }
               enum "1599.67" {
                 description "1599.67 nm/187.409375 THz 3.125GHz spacing";
               }
               enum "1599.64" {
                 description "1599.64 nm/187.412500 THz 3.125/6.25/12.5GHz spacing";
               }
               enum "1599.61" {
                 description "1599.61 nm/187.415625 THz 3.125GHz spacing";
               }
               enum "1599.59" {
                 description "1599.59 nm/187.418750 THz 3.125/6.25GHz spacing";
               }
               enum "1599.56" {
                 description "1599.56 nm/187.421875 THz 3.125GHz spacing";
               }
               enum "1599.53" {
                 description "1599.53 nm/187.425000 THz 3.125/6.25/12.5GHz spacing";
               }
               enum "1599.51" {
                 description "1599.51 nm/187.428125 THz 3.125GHz spacing";
               }
               enum "1599.48" {
                 description "1599.48 nm/187.431250 THz 3.125/6.25GHz spacing";
               }
               enum "1599.45" {
                 description "1599.45 nm/187.434375 THz 3.125GHz spacing";
               }
               enum "1599.43" {
                 description "1599.43 nm/187.437500 THz 3.125/6.25/12.5GHz spacing";
               }
               enum "1599.40" {
                 description "1599.40 nm/187.440625 THz 3.125GHz spacing";
               }
               enum "1599.37" {
                 description "1599.37 nm/187.443750 THz 3.125/6.25GHz spacing";
               }
               enum "1599.35" {
                 description "1599.35 nm/187.446875 THz 3.125GHz spacing";
               }
               enum "1599.32" {
                 description "1599.32 nm/187.450000 THz 3.125/6.25/12.5/50GHz spacing";
               }
               enum "1599.29" {
                 description "1599.29 nm/187.453125 THz 3.125GHz spacing";
               }
               enum "1599.27" {
                 description "1599.27 nm/187.456250 THz 3.125/6.25GHz spacing";
               }
               enum "1599.24" {
                 description "1599.24 nm/187.459375 THz 3.125GHz spacing";
               }
               enum "1599.21" {
                 description "1599.21 nm/187.462500 THz 3.125/6.25/12.5GHz spacing";
               }
               enum "1599.19" {
                 description "1599.19 nm/187.465625 THz 3.125GHz spacing";
               }
               enum "1599.16" {
                 description "1599.16 nm/187.468750 THz 3.125/6.25GHz spacing";
               }
               enum "1599.13" {
                 description "1599.13 nm/187.471875 THz 3.125GHz spacing";
               }
               enum "1599.11" {
                 description "1599.11 nm/187.475000 THz 3.125/6.25/12.5/75GHz spacing";
               }
               enum "1599.08" {
                 description "1599.08 nm/187.478125 THz 3.125GHz spacing";
               }
               enum "1599.05" {
                 description "1599.05 nm/187.481250 THz 3.125/6.25GHz spacing";
               }
               enum "1599.03" {
                 description "1599.03 nm/187.484375 THz 3.125GHz spacing";
               }
               enum "1599.00" {
                 description "1599.00 nm/187.487500 THz 3.125/6.25/12.5GHz spacing";
               }
               enum "1598.97" {
                 description "1598.97 nm/187.490625 THz 3.125GHz spacing";
               }
               enum "1598.95" {
                 description "1598.95 nm/187.493750 THz 3.125/6.25GHz spacing";
               }
               enum "1598.92" {
                 description "1598.92 nm/187.496875 THz 3.125GHz spacing";
               }
               enum "1598.89" {
                 description "1598.89 nm/187.500000 THz 3.125/6.25/12.5/50/75/100GHz spacing";
               }
               enum "1598.87" {
                 description "1598.87 nm/187.503125 THz 3.125GHz spacing";
               }
               enum "1598.84" {
                 description "1598.84 nm/187.506250 THz 3.125/6.25GHz spacing";
               }
               enum "1598.81" {
                 description "1598.81 nm/187.509375 THz 3.125GHz spacing";
               }
               enum "1598.79" {
                 description "1598.79 nm/187.512500 THz 3.125/6.25/12.5GHz spacing";
               }
               enum "1598.76" {
                 description "1598.76 nm/187.515625 THz 3.125GHz spacing";
               }
               enum "1598.73" {
                 description "1598.73 nm/187.518750 THz 3.125/6.25GHz spacing";
               }
               enum "1598.71" {
                 description "1598.71 nm/187.521875 THz 3.125GHz spacing";
               }
               enum "1598.68" {
                 description "1598.68 nm/187.525000 THz 3.125/6.25/12.5GHz spacing";
               }
               enum "1598.65" {
                 description "1598.65 nm/187.528125 THz 3.125GHz spacing";
               }
               enum "1598.63" {
                 description "1598.63 nm/187.531250 THz 3.125/6.25GHz spacing";
               }
               enum "1598.60" {
                 description "1598.60 nm/187.534375 THz 3.125GHz spacing";
               }
               enum "1598.57" {
                 description "1598.57 nm/187.537500 THz 3.125/6.25/12.5GHz spacing";
               }
               enum "1598.55" {
                 description "1598.55 nm/187.540625 THz 3.125GHz spacing";
               }
               enum "1598.52" {
                 description "1598.52 nm/187.543750 THz 3.125/6.25GHz spacing";
               }
               enum "1598.49" {
                 description "1598.49 nm/187.546875 THz 3.125GHz spacing";
               }
               enum "1598.47" {
                 description "1598.47 nm/187.550000 THz 3.125/6.25/12.5/50/75GHz spacing";
               }
               enum "1598.44" {
                 description "1598.44 nm/187.553125 THz 3.125GHz spacing";
               }
               enum "1598.41" {
                 description "1598.41 nm/187.556250 THz 3.125/6.25GHz spacing";
               }
               enum "1598.39" {
                 description "1598.39 nm/187.559375 THz 3.125GHz spacing";
               }
               enum "1598.36" {
                 description "1598.36 nm/187.562500 THz 3.125/6.25/12.5GHz spacing";
               }
               enum "1598.33" {
                 description "1598.33 nm/187.565625 THz 3.125GHz spacing";
               }
               enum "1598.31" {
                 description "1598.31 nm/187.568750 THz 3.125/6.25GHz spacing";
               }
               enum "1598.28" {
                 description "1598.28 nm/187.571875 THz 3.125GHz spacing";
               }
               enum "1598.25" {
                 description "1598.25 nm/187.575000 THz 3.125/6.25/12.5GHz spacing";
               }
               enum "1598.23" {
                 description "1598.23 nm/187.578125 THz 3.125GHz spacing";
               }
               enum "1598.20" {
                 description "1598.20 nm/187.581250 THz 3.125/6.25GHz spacing";
               }
               enum "1598.17" {
                 description "1598.17 nm/187.584375 THz 3.125GHz spacing";
               }
               enum "1598.15" {
                 description "1598.15 nm/187.587500 THz 3.125/6.25/12.5GHz spacing";
               }
               enum "1598.12" {
                 description "1598.12 nm/187.590625 THz 3.125GHz spacing";
               }
               enum "1598.09" {
                 description "1598.09 nm/187.593750 THz 3.125/6.25GHz spacing";
               }
               enum "1598.07" {
                 description "1598.07 nm/187.596875 THz 3.125GHz spacing";
               }
               enum "1598.04" {
                 description "1598.04 nm/187.600000 THz 3.125/6.25/12.5/100GHz spacing";
               }
               enum "1598.01" {
                 description "1598.01 nm/187.603125 THz 3.125GHz spacing";
               }
               enum "1597.99" {
                 description "1597.99 nm/187.606250 THz 3.125/6.25GHz spacing";
               }
               enum "1597.96" {
                 description "1597.96 nm/187.609375 THz 3.125GHz spacing";
               }
               enum "1597.93" {
                 description "1597.93 nm/187.612500 THz 3.125/6.25/12.5GHz spacing";
               }
               enum "1597.91" {
                 description "1597.91 nm/187.615625 THz 3.125GHz spacing";
               }
               enum "1597.88" {
                 description "1597.88 nm/187.618750 THz 3.125/6.25GHz spacing";
               }
               enum "1597.85" {
                 description "1597.85 nm/187.621875 THz 3.125GHz spacing";
               }
               enum "1597.83" {
                 description "1597.83 nm/187.625000 THz 3.125/6.25/12.5/75GHz spacing";
               }
               enum "1597.80" {
                 description "1597.80 nm/187.628125 THz 3.125GHz spacing";
               }
               enum "1597.77" {
                 description "1597.77 nm/187.631250 THz 3.125/6.25GHz spacing";
               }
               enum "1597.75" {
                 description "1597.75 nm/187.634375 THz 3.125GHz spacing";
               }
               enum "1597.72" {
                 description "1597.72 nm/187.637500 THz 3.125/6.25/12.5GHz spacing";
               }
               enum "1597.69" {
                 description "1597.69 nm/187.640625 THz 3.125GHz spacing";
               }
               enum "1597.67" {
                 description "1597.67 nm/187.643750 THz 3.125/6.25GHz spacing";
               }
               enum "1597.64" {
                 description "1597.64 nm/187.646875 THz 3.125GHz spacing";
               }
               enum "1597.62" {
                 description "1597.62 nm/187.650000 THz 3.125/6.25/12.5/50GHz spacing";
               }
               enum "1597.59" {
                 description "1597.59 nm/187.653125 THz 3.125GHz spacing";
               }
               enum "1597.56" {
                 description "1597.56 nm/187.656250 THz 3.125/6.25GHz spacing";
               }
               enum "1597.54" {
                 description "1597.54 nm/187.659375 THz 3.125GHz spacing";
               }
               enum "1597.51" {
                 description "1597.51 nm/187.662500 THz 3.125/6.25/12.5GHz spacing";
               }
               enum "1597.48" {
                 description "1597.48 nm/187.665625 THz 3.125GHz spacing";
               }
               enum "1597.46" {
                 description "1597.46 nm/187.668750 THz 3.125/6.25GHz spacing";
               }
               enum "1597.43" {
                 description "1597.43 nm/187.671875 THz 3.125GHz spacing";
               }
               enum "1597.40" {
                 description "1597.40 nm/187.675000 THz 3.125/6.25/12.5GHz spacing";
               }
               enum "1597.38" {
                 description "1597.38 nm/187.678125 THz 3.125GHz spacing";
               }
               enum "1597.35" {
                 description "1597.35 nm/187.681250 THz 3.125/6.25GHz spacing";
               }
               enum "1597.32" {
                 description "1597.32 nm/187.684375 THz 3.125GHz spacing";
               }
               enum "1597.30" {
                 description "1597.30 nm/187.687500 THz 3.125/6.25/12.5GHz spacing";
               }
               enum "1597.27" {
                 description "1597.27 nm/187.690625 THz 3.125GHz spacing";
               }
               enum "1597.24" {
                 description "1597.24 nm/187.693750 THz 3.125/6.25GHz spacing";
               }
               enum "1597.22" {
                 description "1597.22 nm/187.696875 THz 3.125GHz spacing";
               }
               enum "1597.19" {
                 description "1597.19 nm/187.700000 THz 3.125/6.25/12.5/100GHz spacing";
               }
               enum "1597.16" {
                 description "1597.16 nm/187.703125 THz 3.125GHz spacing";
               }
               enum "1597.14" {
                 description "1597.14 nm/187.706250 THz 3.125/6.25GHz spacing";
               }
               enum "1597.11" {
                 description "1597.11 nm/187.709375 THz 3.125GHz spacing";
               }
               enum "1597.08" {
                 description "1597.08 nm/187.712500 THz 3.125/6.25/12.5GHz spacing";
               }
               enum "1597.06" {
                 description "1597.06 nm/187.715625 THz 3.125GHz spacing";
               }
               enum "1597.03" {
                 description "1597.03 nm/187.718750 THz 3.125/6.25GHz spacing";
               }
               enum "1597.00" {
                 description "1597.00 nm/187.721875 THz 3.125GHz spacing";
               }
               enum "1596.98" {
                 description "1596.98 nm/187.725000 THz 3.125/6.25/12.5GHz spacing";
               }
               enum "1596.95" {
                 description "1596.95 nm/187.728125 THz 3.125GHz spacing";
               }
               enum "1596.92" {
                 description "1596.92 nm/187.731250 THz 3.125/6.25GHz spacing";
               }
               enum "1596.90" {
                 description "1596.90 nm/187.734375 THz 3.125GHz spacing";
               }
               enum "1596.87" {
                 description "1596.87 nm/187.737500 THz 3.125/6.25/12.5GHz spacing";
               }
               enum "1596.84" {
                 description "1596.84 nm/187.740625 THz 3.125GHz spacing";
               }
               enum "1596.82" {
                 description "1596.82 nm/187.743750 THz 3.125/6.25GHz spacing";
               }
               enum "1596.79" {
                 description "1596.79 nm/187.746875 THz 3.125GHz spacing";
               }
               enum "1596.76" {
                 description "1596.76 nm/187.750000 THz 3.125/6.25/12.5/50GHz spacing";
               }
               enum "1596.74" {
                 description "1596.74 nm/187.753125 THz 3.125GHz spacing";
               }
               enum "1596.71" {
                 description "1596.71 nm/187.756250 THz 3.125/6.25GHz spacing";
               }
               enum "1596.68" {
                 description "1596.68 nm/187.759375 THz 3.125GHz spacing";
               }
               enum "1596.66" {
                 description "1596.66 nm/187.762500 THz 3.125/6.25/12.5GHz spacing";
               }
               enum "1596.63" {
                 description "1596.63 nm/187.765625 THz 3.125GHz spacing";
               }
               enum "1596.60" {
                 description "1596.60 nm/187.768750 THz 3.125/6.25GHz spacing";
               }
               enum "1596.58" {
                 description "1596.58 nm/187.771875 THz 3.125GHz spacing";
               }
               enum "1596.55" {
                 description "1596.55 nm/187.775000 THz 3.125/6.25/12.5/75GHz spacing";
               }
               enum "1596.52" {
                 description "1596.52 nm/187.778125 THz 3.125GHz spacing";
               }
               enum "1596.50" {
                 description "1596.50 nm/187.781250 THz 3.125/6.25GHz spacing";
               }
               enum "1596.47" {
                 description "1596.47 nm/187.784375 THz 3.125GHz spacing";
               }
               enum "1596.45" {
                 description "1596.45 nm/187.787500 THz 3.125/6.25/12.5GHz spacing";
               }
               enum "1596.42" {
                 description "1596.42 nm/187.790625 THz 3.125GHz spacing";
               }
               enum "1596.39" {
                 description "1596.39 nm/187.793750 THz 3.125/6.25GHz spacing";
               }
               enum "1596.37" {
                 description "1596.37 nm/187.796875 THz 3.125GHz spacing";
               }
               enum "1596.34" {
                 description "1596.34 nm/187.800000 THz 3.125/6.25/12.5/50/75/100GHz spacing";
               }
               enum "1596.31" {
                 description "1596.31 nm/187.803125 THz 3.125GHz spacing";
               }
               enum "1596.29" {
                 description "1596.29 nm/187.806250 THz 3.125/6.25GHz spacing";
               }
               enum "1596.26" {
                 description "1596.26 nm/187.809375 THz 3.125GHz spacing";
               }
               enum "1596.23" {
                 description "1596.23 nm/187.812500 THz 3.125/6.25/12.5GHz spacing";
               }
               enum "1596.21" {
                 description "1596.21 nm/187.815625 THz 3.125GHz spacing";
               }
               enum "1596.18" {
                 description "1596.18 nm/187.818750 THz 3.125/6.25GHz spacing";
               }
               enum "1596.15" {
                 description "1596.15 nm/187.821875 THz 3.125GHz spacing";
               }
               enum "1596.13" {
                 description "1596.13 nm/187.825000 THz 3.125/6.25/12.5GHz spacing";
               }
               enum "1596.10" {
                 description "1596.10 nm/187.828125 THz 3.125GHz spacing";
               }
               enum "1596.07" {
                 description "1596.07 nm/187.831250 THz 3.125/6.25GHz spacing";
               }
               enum "1596.05" {
                 description "1596.05 nm/187.834375 THz 3.125GHz spacing";
               }
               enum "1596.02" {
                 description "1596.02 nm/187.837500 THz 3.125/6.25/12.5GHz spacing";
               }
               enum "1595.99" {
                 description "1595.99 nm/187.840625 THz 3.125GHz spacing";
               }
               enum "1595.97" {
                 description "1595.97 nm/187.843750 THz 3.125/6.25GHz spacing";
               }
               enum "1595.94" {
                 description "1595.94 nm/187.846875 THz 3.125GHz spacing";
               }
               enum "1595.91" {
                 description "1595.91 nm/187.850000 THz 3.125/6.25/12.5/50/75GHz spacing";
               }
               enum "1595.89" {
                 description "1595.89 nm/187.853125 THz 3.125GHz spacing";
               }
               enum "1595.86" {
                 description "1595.86 nm/187.856250 THz 3.125/6.25GHz spacing";
               }
               enum "1595.83" {
                 description "1595.83 nm/187.859375 THz 3.125GHz spacing";
               }
               enum "1595.81" {
                 description "1595.81 nm/187.862500 THz 3.125/6.25/12.5GHz spacing";
               }
               enum "1595.78" {
                 description "1595.78 nm/187.865625 THz 3.125GHz spacing";
               }
               enum "1595.75" {
                 description "1595.75 nm/187.868750 THz 3.125/6.25GHz spacing";
               }
               enum "1595.73" {
                 description "1595.73 nm/187.871875 THz 3.125GHz spacing";
               }
               enum "1595.70" {
                 description "1595.70 nm/187.875000 THz 3.125/6.25/12.5GHz spacing";
               }
               enum "1595.68" {
                 description "1595.68 nm/187.878125 THz 3.125GHz spacing";
               }
               enum "1595.65" {
                 description "1595.65 nm/187.881250 THz 3.125/6.25GHz spacing";
               }
               enum "1595.62" {
                 description "1595.62 nm/187.884375 THz 3.125GHz spacing";
               }
               enum "1595.60" {
                 description "1595.60 nm/187.887500 THz 3.125/6.25/12.5GHz spacing";
               }
               enum "1595.57" {
                 description "1595.57 nm/187.890625 THz 3.125GHz spacing";
               }
               enum "1595.54" {
                 description "1595.54 nm/187.893750 THz 3.125/6.25GHz spacing";
               }
               enum "1595.52" {
                 description "1595.52 nm/187.896875 THz 3.125GHz spacing";
               }
               enum "1595.49" {
                 description "1595.49 nm/187.900000 THz 3.125/6.25/12.5/100GHz spacing";
               }
               enum "1595.46" {
                 description "1595.46 nm/187.903125 THz 3.125GHz spacing";
               }
               enum "1595.44" {
                 description "1595.44 nm/187.906250 THz 3.125/6.25GHz spacing";
               }
               enum "1595.41" {
                 description "1595.41 nm/187.909375 THz 3.125GHz spacing";
               }
               enum "1595.38" {
                 description "1595.38 nm/187.912500 THz 3.125/6.25/12.5GHz spacing";
               }
               enum "1595.36" {
                 description "1595.36 nm/187.915625 THz 3.125GHz spacing";
               }
               enum "1595.33" {
                 description "1595.33 nm/187.918750 THz 3.125/6.25GHz spacing";
               }
               enum "1595.30" {
                 description "1595.30 nm/187.921875 THz 3.125GHz spacing";
               }
               enum "1595.28" {
                 description "1595.28 nm/187.925000 THz 3.125/6.25/12.5/75GHz spacing";
               }
               enum "1595.25" {
                 description "1595.25 nm/187.928125 THz 3.125GHz spacing";
               }
               enum "1595.22" {
                 description "1595.22 nm/187.931250 THz 3.125/6.25GHz spacing";
               }
               enum "1595.20" {
                 description "1595.20 nm/187.934375 THz 3.125GHz spacing";
               }
               enum "1595.17" {
                 description "1595.17 nm/187.937500 THz 3.125/6.25/12.5GHz spacing";
               }
               enum "1595.14" {
                 description "1595.14 nm/187.940625 THz 3.125GHz spacing";
               }
               enum "1595.12" {
                 description "1595.12 nm/187.943750 THz 3.125/6.25GHz spacing";
               }
               enum "1595.09" {
                 description "1595.09 nm/187.946875 THz 3.125GHz spacing";
               }
               enum "1595.06" {
                 description "1595.06 nm/187.950000 THz 3.125/6.25/12.5/50GHz spacing";
               }
               enum "1595.04" {
                 description "1595.04 nm/187.953125 THz 3.125GHz spacing";
               }
               enum "1595.01" {
                 description "1595.01 nm/187.956250 THz 3.125/6.25GHz spacing";
               }
               enum "1594.99" {
                 description "1594.99 nm/187.959375 THz 3.125GHz spacing";
               }
               enum "1594.96" {
                 description "1594.96 nm/187.962500 THz 3.125/6.25/12.5GHz spacing";
               }
               enum "1594.93" {
                 description "1594.93 nm/187.965625 THz 3.125GHz spacing";
               }
               enum "1594.91" {
                 description "1594.91 nm/187.968750 THz 3.125/6.25GHz spacing";
               }
               enum "1594.88" {
                 description "1594.88 nm/187.971875 THz 3.125GHz spacing";
               }
               enum "1594.85" {
                 description "1594.85 nm/187.975000 THz 3.125/6.25/12.5GHz spacing";
               }
               enum "1594.83" {
                 description "1594.83 nm/187.978125 THz 3.125GHz spacing";
               }
               enum "1594.80" {
                 description "1594.80 nm/187.981250 THz 3.125/6.25GHz spacing";
               }
               enum "1594.77" {
                 description "1594.77 nm/187.984375 THz 3.125GHz spacing";
               }
               enum "1594.75" {
                 description "1594.75 nm/187.987500 THz 3.125/6.25/12.5GHz spacing";
               }
               enum "1594.72" {
                 description "1594.72 nm/187.990625 THz 3.125GHz spacing";
               }
               enum "1594.69" {
                 description "1594.69 nm/187.993750 THz 3.125/6.25GHz spacing";
               }
               enum "1594.67" {
                 description "1594.67 nm/187.996875 THz 3.125GHz spacing";
               }
               enum "1594.64" {
                 description "1594.64 nm/188.000000 THz 3.125/6.25/12.5/100GHz spacing";
               }
               enum "1594.61" {
                 description "1594.61 nm/188.003125 THz 3.125GHz spacing";
               }
               enum "1594.59" {
                 description "1594.59 nm/188.006250 THz 3.125/6.25GHz spacing";
               }
               enum "1594.56" {
                 description "1594.56 nm/188.009375 THz 3.125GHz spacing";
               }
               enum "1594.53" {
                 description "1594.53 nm/188.012500 THz 3.125/6.25/12.5GHz spacing";
               }
               enum "1594.51" {
                 description "1594.51 nm/188.015625 THz 3.125GHz spacing";
               }
               enum "1594.48" {
                 description "1594.48 nm/188.018750 THz 3.125/6.25GHz spacing";
               }
               enum "1594.46" {
                 description "1594.46 nm/188.021875 THz 3.125GHz spacing";
               }
               enum "1594.43" {
                 description "1594.43 nm/188.025000 THz 3.125/6.25/12.5GHz spacing";
               }
               enum "1594.40" {
                 description "1594.40 nm/188.028125 THz 3.125GHz spacing";
               }
               enum "1594.38" {
                 description "1594.38 nm/188.031250 THz 3.125/6.25GHz spacing";
               }
               enum "1594.35" {
                 description "1594.35 nm/188.034375 THz 3.125GHz spacing";
               }
               enum "1594.32" {
                 description "1594.32 nm/188.037500 THz 3.125/6.25/12.5GHz spacing";
               }
               enum "1594.30" {
                 description "1594.30 nm/188.040625 THz 3.125GHz spacing";
               }
               enum "1594.27" {
                 description "1594.27 nm/188.043750 THz 3.125/6.25GHz spacing";
               }
               enum "1594.24" {
                 description "1594.24 nm/188.046875 THz 3.125GHz spacing";
               }
               enum "1594.22" {
                 description "1594.22 nm/188.050000 THz 3.125/6.25/12.5/50GHz spacing";
               }
               enum "1594.19" {
                 description "1594.19 nm/188.053125 THz 3.125GHz spacing";
               }
               enum "1594.16" {
                 description "1594.16 nm/188.056250 THz 3.125/6.25GHz spacing";
               }
               enum "1594.14" {
                 description "1594.14 nm/188.059375 THz 3.125GHz spacing";
               }
               enum "1594.11" {
                 description "1594.11 nm/188.062500 THz 3.125/6.25/12.5GHz spacing";
               }
               enum "1594.08" {
                 description "1594.08 nm/188.065625 THz 3.125GHz spacing";
               }
               enum "1594.06" {
                 description "1594.06 nm/188.068750 THz 3.125/6.25GHz spacing";
               }
               enum "1594.03" {
                 description "1594.03 nm/188.071875 THz 3.125GHz spacing";
               }
               enum "1594.00" {
                 description "1594.00 nm/188.075000 THz 3.125/6.25/12.5/75GHz spacing";
               }
               enum "1593.98" {
                 description "1593.98 nm/188.078125 THz 3.125GHz spacing";
               }
               enum "1593.95" {
                 description "1593.95 nm/188.081250 THz 3.125/6.25GHz spacing";
               }
               enum "1593.93" {
                 description "1593.93 nm/188.084375 THz 3.125GHz spacing";
               }
               enum "1593.90" {
                 description "1593.90 nm/188.087500 THz 3.125/6.25/12.5GHz spacing";
               }
               enum "1593.87" {
                 description "1593.87 nm/188.090625 THz 3.125GHz spacing";
               }
               enum "1593.85" {
                 description "1593.85 nm/188.093750 THz 3.125/6.25GHz spacing";
               }
               enum "1593.82" {
                 description "1593.82 nm/188.096875 THz 3.125GHz spacing";
               }
               enum "1593.79" {
                 description "1593.79 nm/188.100000 THz 3.125/6.25/12.5/50/75/100GHz spacing";
               }
               enum "1593.77" {
                 description "1593.77 nm/188.103125 THz 3.125GHz spacing";
               }
               enum "1593.74" {
                 description "1593.74 nm/188.106250 THz 3.125/6.25GHz spacing";
               }
               enum "1593.71" {
                 description "1593.71 nm/188.109375 THz 3.125GHz spacing";
               }
               enum "1593.69" {
                 description "1593.69 nm/188.112500 THz 3.125/6.25/12.5GHz spacing";
               }
               enum "1593.66" {
                 description "1593.66 nm/188.115625 THz 3.125GHz spacing";
               }
               enum "1593.63" {
                 description "1593.63 nm/188.118750 THz 3.125/6.25GHz spacing";
               }
               enum "1593.61" {
                 description "1593.61 nm/188.121875 THz 3.125GHz spacing";
               }
               enum "1593.58" {
                 description "1593.58 nm/188.125000 THz 3.125/6.25/12.5GHz spacing";
               }
               enum "1593.55" {
                 description "1593.55 nm/188.128125 THz 3.125GHz spacing";
               }
               enum "1593.53" {
                 description "1593.53 nm/188.131250 THz 3.125/6.25GHz spacing";
               }
               enum "1593.50" {
                 description "1593.50 nm/188.134375 THz 3.125GHz spacing";
               }
               enum "1593.48" {
                 description "1593.48 nm/188.137500 THz 3.125/6.25/12.5GHz spacing";
               }
               enum "1593.45" {
                 description "1593.45 nm/188.140625 THz 3.125GHz spacing";
               }
               enum "1593.42" {
                 description "1593.42 nm/188.143750 THz 3.125/6.25GHz spacing";
               }
               enum "1593.40" {
                 description "1593.40 nm/188.146875 THz 3.125GHz spacing";
               }
               enum "1593.37" {
                 description "1593.37 nm/188.150000 THz 3.125/6.25/12.5/50/75GHz spacing";
               }
               enum "1593.34" {
                 description "1593.34 nm/188.153125 THz 3.125GHz spacing";
               }
               enum "1593.32" {
                 description "1593.32 nm/188.156250 THz 3.125/6.25GHz spacing";
               }
               enum "1593.29" {
                 description "1593.29 nm/188.159375 THz 3.125GHz spacing";
               }
               enum "1593.26" {
                 description "1593.26 nm/188.162500 THz 3.125/6.25/12.5GHz spacing";
               }
               enum "1593.24" {
                 description "1593.24 nm/188.165625 THz 3.125GHz spacing";
               }
               enum "1593.21" {
                 description "1593.21 nm/188.168750 THz 3.125/6.25GHz spacing";
               }
               enum "1593.18" {
                 description "1593.18 nm/188.171875 THz 3.125GHz spacing";
               }
               enum "1593.16" {
                 description "1593.16 nm/188.175000 THz 3.125/6.25/12.5GHz spacing";
               }
               enum "1593.13" {
                 description "1593.13 nm/188.178125 THz 3.125GHz spacing";
               }
               enum "1593.10" {
                 description "1593.10 nm/188.181250 THz 3.125/6.25GHz spacing";
               }
               enum "1593.08" {
                 description "1593.08 nm/188.184375 THz 3.125GHz spacing";
               }
               enum "1593.05" {
                 description "1593.05 nm/188.187500 THz 3.125/6.25/12.5GHz spacing";
               }
               enum "1593.03" {
                 description "1593.03 nm/188.190625 THz 3.125GHz spacing";
               }
               enum "1593.00" {
                 description "1593.00 nm/188.193750 THz 3.125/6.25GHz spacing";
               }
               enum "1592.97" {
                 description "1592.97 nm/188.196875 THz 3.125GHz spacing";
               }
               enum "1592.95" {
                 description "1592.95 nm/188.200000 THz 3.125/6.25/12.5/100GHz spacing";
               }
               enum "1592.92" {
                 description "1592.92 nm/188.203125 THz 3.125GHz spacing";
               }
               enum "1592.89" {
                 description "1592.89 nm/188.206250 THz 3.125/6.25GHz spacing";
               }
               enum "1592.87" {
                 description "1592.87 nm/188.209375 THz 3.125GHz spacing";
               }
               enum "1592.84" {
                 description "1592.84 nm/188.212500 THz 3.125/6.25/12.5GHz spacing";
               }
               enum "1592.81" {
                 description "1592.81 nm/188.215625 THz 3.125GHz spacing";
               }
               enum "1592.79" {
                 description "1592.79 nm/188.218750 THz 3.125/6.25GHz spacing";
               }
               enum "1592.76" {
                 description "1592.76 nm/188.221875 THz 3.125GHz spacing";
               }
               enum "1592.73" {
                 description "1592.73 nm/188.225000 THz 3.125/6.25/12.5/75GHz spacing";
               }
               enum "1592.71" {
                 description "1592.71 nm/188.228125 THz 3.125GHz spacing";
               }
               enum "1592.68" {
                 description "1592.68 nm/188.231250 THz 3.125/6.25GHz spacing";
               }
               enum "1592.66" {
                 description "1592.66 nm/188.234375 THz 3.125GHz spacing";
               }
               enum "1592.63" {
                 description "1592.63 nm/188.237500 THz 3.125/6.25/12.5GHz spacing";
               }
               enum "1592.60" {
                 description "1592.60 nm/188.240625 THz 3.125GHz spacing";
               }
               enum "1592.58" {
                 description "1592.58 nm/188.243750 THz 3.125/6.25GHz spacing";
               }
               enum "1592.55" {
                 description "1592.55 nm/188.246875 THz 3.125GHz spacing";
               }
               enum "1592.52" {
                 description "1592.52 nm/188.250000 THz 3.125/6.25/12.5/50GHz spacing";
               }
               enum "1592.50" {
                 description "1592.50 nm/188.253125 THz 3.125GHz spacing";
               }
               enum "1592.47" {
                 description "1592.47 nm/188.256250 THz 3.125/6.25GHz spacing";
               }
               enum "1592.44" {
                 description "1592.44 nm/188.259375 THz 3.125GHz spacing";
               }
               enum "1592.42" {
                 description "1592.42 nm/188.262500 THz 3.125/6.25/12.5GHz spacing";
               }
               enum "1592.39" {
                 description "1592.39 nm/188.265625 THz 3.125GHz spacing";
               }
               enum "1592.36" {
                 description "1592.36 nm/188.268750 THz 3.125/6.25GHz spacing";
               }
               enum "1592.34" {
                 description "1592.34 nm/188.271875 THz 3.125GHz spacing";
               }
               enum "1592.31" {
                 description "1592.31 nm/188.275000 THz 3.125/6.25/12.5GHz spacing";
               }
               enum "1592.29" {
                 description "1592.29 nm/188.278125 THz 3.125GHz spacing";
               }
               enum "1592.26" {
                 description "1592.26 nm/188.281250 THz 3.125/6.25GHz spacing";
               }
               enum "1592.23" {
                 description "1592.23 nm/188.284375 THz 3.125GHz spacing";
               }
               enum "1592.21" {
                 description "1592.21 nm/188.287500 THz 3.125/6.25/12.5GHz spacing";
               }
               enum "1592.18" {
                 description "1592.18 nm/188.290625 THz 3.125GHz spacing";
               }
               enum "1592.15" {
                 description "1592.15 nm/188.293750 THz 3.125/6.25GHz spacing";
               }
               enum "1592.13" {
                 description "1592.13 nm/188.296875 THz 3.125GHz spacing";
               }
               enum "1592.10" {
                 description "1592.10 nm/188.300000 THz 3.125/6.25/12.5/100GHz spacing";
               }
               enum "1592.07" {
                 description "1592.07 nm/188.303125 THz 3.125GHz spacing";
               }
               enum "1592.05" {
                 description "1592.05 nm/188.306250 THz 3.125/6.25GHz spacing";
               }
               enum "1592.02" {
                 description "1592.02 nm/188.309375 THz 3.125GHz spacing";
               }
               enum "1591.99" {
                 description "1591.99 nm/188.312500 THz 3.125/6.25/12.5GHz spacing";
               }
               enum "1591.97" {
                 description "1591.97 nm/188.315625 THz 3.125GHz spacing";
               }
               enum "1591.94" {
                 description "1591.94 nm/188.318750 THz 3.125/6.25GHz spacing";
               }
               enum "1591.92" {
                 description "1591.92 nm/188.321875 THz 3.125GHz spacing";
               }
               enum "1591.89" {
                 description "1591.89 nm/188.325000 THz 3.125/6.25/12.5GHz spacing";
               }
               enum "1591.86" {
                 description "1591.86 nm/188.328125 THz 3.125GHz spacing";
               }
               enum "1591.84" {
                 description "1591.84 nm/188.331250 THz 3.125/6.25GHz spacing";
               }
               enum "1591.81" {
                 description "1591.81 nm/188.334375 THz 3.125GHz spacing";
               }
               enum "1591.78" {
                 description "1591.78 nm/188.337500 THz 3.125/6.25/12.5GHz spacing";
               }
               enum "1591.76" {
                 description "1591.76 nm/188.340625 THz 3.125GHz spacing";
               }
               enum "1591.73" {
                 description "1591.73 nm/188.343750 THz 3.125/6.25GHz spacing";
               }
               enum "1591.70" {
                 description "1591.70 nm/188.346875 THz 3.125GHz spacing";
               }
               enum "1591.68" {
                 description "1591.68 nm/188.350000 THz 3.125/6.25/12.5/50GHz spacing";
               }
               enum "1591.65" {
                 description "1591.65 nm/188.353125 THz 3.125GHz spacing";
               }
               enum "1591.62" {
                 description "1591.62 nm/188.356250 THz 3.125/6.25GHz spacing";
               }
               enum "1591.60" {
                 description "1591.60 nm/188.359375 THz 3.125GHz spacing";
               }
               enum "1591.57" {
                 description "1591.57 nm/188.362500 THz 3.125/6.25/12.5GHz spacing";
               }
               enum "1591.55" {
                 description "1591.55 nm/188.365625 THz 3.125GHz spacing";
               }
               enum "1591.52" {
                 description "1591.52 nm/188.368750 THz 3.125/6.25GHz spacing";
               }
               enum "1591.49" {
                 description "1591.49 nm/188.371875 THz 3.125GHz spacing";
               }
               enum "1591.47" {
                 description "1591.47 nm/188.375000 THz 3.125/6.25/12.5/75GHz spacing";
               }
               enum "1591.44" {
                 description "1591.44 nm/188.378125 THz 3.125GHz spacing";
               }
               enum "1591.41" {
                 description "1591.41 nm/188.381250 THz 3.125/6.25GHz spacing";
               }
               enum "1591.39" {
                 description "1591.39 nm/188.384375 THz 3.125GHz spacing";
               }
               enum "1591.36" {
                 description "1591.36 nm/188.387500 THz 3.125/6.25/12.5GHz spacing";
               }
               enum "1591.33" {
                 description "1591.33 nm/188.390625 THz 3.125GHz spacing";
               }
               enum "1591.31" {
                 description "1591.31 nm/188.393750 THz 3.125/6.25GHz spacing";
               }
               enum "1591.28" {
                 description "1591.28 nm/188.396875 THz 3.125GHz spacing";
               }
               enum "1591.26" {
                 description "1591.26 nm/188.400000 THz 3.125/6.25/12.5/50/75/100GHz spacing";
               }
               enum "1591.23" {
                 description "1591.23 nm/188.403125 THz 3.125GHz spacing";
               }
               enum "1591.20" {
                 description "1591.20 nm/188.406250 THz 3.125/6.25GHz spacing";
               }
               enum "1591.18" {
                 description "1591.18 nm/188.409375 THz 3.125GHz spacing";
               }
               enum "1591.15" {
                 description "1591.15 nm/188.412500 THz 3.125/6.25/12.5GHz spacing";
               }
               enum "1591.12" {
                 description "1591.12 nm/188.415625 THz 3.125GHz spacing";
               }
               enum "1591.10" {
                 description "1591.10 nm/188.418750 THz 3.125/6.25GHz spacing";
               }
               enum "1591.07" {
                 description "1591.07 nm/188.421875 THz 3.125GHz spacing";
               }
               enum "1591.04" {
                 description "1591.04 nm/188.425000 THz 3.125/6.25/12.5GHz spacing";
               }
               enum "1591.02" {
                 description "1591.02 nm/188.428125 THz 3.125GHz spacing";
               }
               enum "1590.99" {
                 description "1590.99 nm/188.431250 THz 3.125/6.25GHz spacing";
               }
               enum "1590.96" {
                 description "1590.96 nm/188.434375 THz 3.125GHz spacing";
               }
               enum "1590.94" {
                 description "1590.94 nm/188.437500 THz 3.125/6.25/12.5GHz spacing";
               }
               enum "1590.91" {
                 description "1590.91 nm/188.440625 THz 3.125GHz spacing";
               }
               enum "1590.89" {
                 description "1590.89 nm/188.443750 THz 3.125/6.25GHz spacing";
               }
               enum "1590.86" {
                 description "1590.86 nm/188.446875 THz 3.125GHz spacing";
               }
               enum "1590.83" {
                 description "1590.83 nm/188.450000 THz 3.125/6.25/12.5/50/75GHz spacing";
               }
               enum "1590.81" {
                 description "1590.81 nm/188.453125 THz 3.125GHz spacing";
               }
               enum "1590.78" {
                 description "1590.78 nm/188.456250 THz 3.125/6.25GHz spacing";
               }
               enum "1590.75" {
                 description "1590.75 nm/188.459375 THz 3.125GHz spacing";
               }
               enum "1590.73" {
                 description "1590.73 nm/188.462500 THz 3.125/6.25/12.5GHz spacing";
               }
               enum "1590.70" {
                 description "1590.70 nm/188.465625 THz 3.125GHz spacing";
               }
               enum "1590.67" {
                 description "1590.67 nm/188.468750 THz 3.125/6.25GHz spacing";
               }
               enum "1590.65" {
                 description "1590.65 nm/188.471875 THz 3.125GHz spacing";
               }
               enum "1590.62" {
                 description "1590.62 nm/188.475000 THz 3.125/6.25/12.5GHz spacing";
               }
               enum "1590.60" {
                 description "1590.60 nm/188.478125 THz 3.125GHz spacing";
               }
               enum "1590.57" {
                 description "1590.57 nm/188.481250 THz 3.125/6.25GHz spacing";
               }
               enum "1590.54" {
                 description "1590.54 nm/188.484375 THz 3.125GHz spacing";
               }
               enum "1590.52" {
                 description "1590.52 nm/188.487500 THz 3.125/6.25/12.5GHz spacing";
               }
               enum "1590.49" {
                 description "1590.49 nm/188.490625 THz 3.125GHz spacing";
               }
               enum "1590.46" {
                 description "1590.46 nm/188.493750 THz 3.125/6.25GHz spacing";
               }
               enum "1590.44" {
                 description "1590.44 nm/188.496875 THz 3.125GHz spacing";
               }
               enum "1590.41" {
                 description "1590.41 nm/188.500000 THz 3.125/6.25/12.5/100GHz spacing";
               }
               enum "1590.38" {
                 description "1590.38 nm/188.503125 THz 3.125GHz spacing";
               }
               enum "1590.36" {
                 description "1590.36 nm/188.506250 THz 3.125/6.25GHz spacing";
               }
               enum "1590.33" {
                 description "1590.33 nm/188.509375 THz 3.125GHz spacing";
               }
               enum "1590.31" {
                 description "1590.31 nm/188.512500 THz 3.125/6.25/12.5GHz spacing";
               }
               enum "1590.28" {
                 description "1590.28 nm/188.515625 THz 3.125GHz spacing";
               }
               enum "1590.25" {
                 description "1590.25 nm/188.518750 THz 3.125/6.25GHz spacing";
               }
               enum "1590.23" {
                 description "1590.23 nm/188.521875 THz 3.125GHz spacing";
               }
               enum "1590.20" {
                 description "1590.20 nm/188.525000 THz 3.125/6.25/12.5/75GHz spacing";
               }
               enum "1590.17" {
                 description "1590.17 nm/188.528125 THz 3.125GHz spacing";
               }
               enum "1590.15" {
                 description "1590.15 nm/188.531250 THz 3.125/6.25GHz spacing";
               }
               enum "1590.12" {
                 description "1590.12 nm/188.534375 THz 3.125GHz spacing";
               }
               enum "1590.09" {
                 description "1590.09 nm/188.537500 THz 3.125/6.25/12.5GHz spacing";
               }
               enum "1590.07" {
                 description "1590.07 nm/188.540625 THz 3.125GHz spacing";
               }
               enum "1590.04" {
                 description "1590.04 nm/188.543750 THz 3.125/6.25GHz spacing";
               }
               enum "1590.02" {
                 description "1590.02 nm/188.546875 THz 3.125GHz spacing";
               }
               enum "1589.99" {
                 description "1589.99 nm/188.550000 THz 3.125/6.25/12.5/50GHz spacing";
               }
               enum "1589.96" {
                 description "1589.96 nm/188.553125 THz 3.125GHz spacing";
               }
               enum "1589.94" {
                 description "1589.94 nm/188.556250 THz 3.125/6.25GHz spacing";
               }
               enum "1589.91" {
                 description "1589.91 nm/188.559375 THz 3.125GHz spacing";
               }
               enum "1589.88" {
                 description "1589.88 nm/188.562500 THz 3.125/6.25/12.5GHz spacing";
               }
               enum "1589.86" {
                 description "1589.86 nm/188.565625 THz 3.125GHz spacing";
               }
               enum "1589.83" {
                 description "1589.83 nm/188.568750 THz 3.125/6.25GHz spacing";
               }
               enum "1589.80" {
                 description "1589.80 nm/188.571875 THz 3.125GHz spacing";
               }
               enum "1589.78" {
                 description "1589.78 nm/188.575000 THz 3.125/6.25/12.5GHz spacing";
               }
               enum "1589.75" {
                 description "1589.75 nm/188.578125 THz 3.125GHz spacing";
               }
               enum "1589.73" {
                 description "1589.73 nm/188.581250 THz 3.125/6.25GHz spacing";
               }
               enum "1589.70" {
                 description "1589.70 nm/188.584375 THz 3.125GHz spacing";
               }
               enum "1589.67" {
                 description "1589.67 nm/188.587500 THz 3.125/6.25/12.5GHz spacing";
               }
               enum "1589.65" {
                 description "1589.65 nm/188.590625 THz 3.125GHz spacing";
               }
               enum "1589.62" {
                 description "1589.62 nm/188.593750 THz 3.125/6.25GHz spacing";
               }
               enum "1589.59" {
                 description "1589.59 nm/188.596875 THz 3.125GHz spacing";
               }
               enum "1589.57" {
                 description "1589.57 nm/188.600000 THz 3.125/6.25/12.5/100GHz spacing";
               }
               enum "1589.54" {
                 description "1589.54 nm/188.603125 THz 3.125GHz spacing";
               }
               enum "1589.51" {
                 description "1589.51 nm/188.606250 THz 3.125/6.25GHz spacing";
               }
               enum "1589.49" {
                 description "1589.49 nm/188.609375 THz 3.125GHz spacing";
               }
               enum "1589.46" {
                 description "1589.46 nm/188.612500 THz 3.125/6.25/12.5GHz spacing";
               }
               enum "1589.44" {
                 description "1589.44 nm/188.615625 THz 3.125GHz spacing";
               }
               enum "1589.41" {
                 description "1589.41 nm/188.618750 THz 3.125/6.25GHz spacing";
               }
               enum "1589.38" {
                 description "1589.38 nm/188.621875 THz 3.125GHz spacing";
               }
               enum "1589.36" {
                 description "1589.36 nm/188.625000 THz 3.125/6.25/12.5GHz spacing";
               }
               enum "1589.33" {
                 description "1589.33 nm/188.628125 THz 3.125GHz spacing";
               }
               enum "1589.30" {
                 description "1589.30 nm/188.631250 THz 3.125/6.25GHz spacing";
               }
               enum "1589.28" {
                 description "1589.28 nm/188.634375 THz 3.125GHz spacing";
               }
               enum "1589.25" {
                 description "1589.25 nm/188.637500 THz 3.125/6.25/12.5GHz spacing";
               }
               enum "1589.23" {
                 description "1589.23 nm/188.640625 THz 3.125GHz spacing";
               }
               enum "1589.20" {
                 description "1589.20 nm/188.643750 THz 3.125/6.25GHz spacing";
               }
               enum "1589.17" {
                 description "1589.17 nm/188.646875 THz 3.125GHz spacing";
               }
               enum "1589.15" {
                 description "1589.15 nm/188.650000 THz 3.125/6.25/12.5/50GHz spacing";
               }
               enum "1589.12" {
                 description "1589.12 nm/188.653125 THz 3.125GHz spacing";
               }
               enum "1589.09" {
                 description "1589.09 nm/188.656250 THz 3.125/6.25GHz spacing";
               }
               enum "1589.07" {
                 description "1589.07 nm/188.659375 THz 3.125GHz spacing";
               }
               enum "1589.04" {
                 description "1589.04 nm/188.662500 THz 3.125/6.25/12.5GHz spacing";
               }
               enum "1589.01" {
                 description "1589.01 nm/188.665625 THz 3.125GHz spacing";
               }
               enum "1588.99" {
                 description "1588.99 nm/188.668750 THz 3.125/6.25GHz spacing";
               }
               enum "1588.96" {
                 description "1588.96 nm/188.671875 THz 3.125GHz spacing";
               }
               enum "1588.94" {
                 description "1588.94 nm/188.675000 THz 3.125/6.25/12.5/75GHz spacing";
               }
               enum "1588.91" {
                 description "1588.91 nm/188.678125 THz 3.125GHz spacing";
               }
               enum "1588.88" {
                 description "1588.88 nm/188.681250 THz 3.125/6.25GHz spacing";
               }
               enum "1588.86" {
                 description "1588.86 nm/188.684375 THz 3.125GHz spacing";
               }
               enum "1588.83" {
                 description "1588.83 nm/188.687500 THz 3.125/6.25/12.5GHz spacing";
               }
               enum "1588.80" {
                 description "1588.80 nm/188.690625 THz 3.125GHz spacing";
               }
               enum "1588.78" {
                 description "1588.78 nm/188.693750 THz 3.125/6.25GHz spacing";
               }
               enum "1588.75" {
                 description "1588.75 nm/188.696875 THz 3.125GHz spacing";
               }
               enum "1588.73" {
                 description "1588.73 nm/188.700000 THz 3.125/6.25/12.5/50/75/100GHz spacing";
               }
               enum "1588.70" {
                 description "1588.70 nm/188.703125 THz 3.125GHz spacing";
               }
               enum "1588.67" {
                 description "1588.67 nm/188.706250 THz 3.125/6.25GHz spacing";
               }
               enum "1588.65" {
                 description "1588.65 nm/188.709375 THz 3.125GHz spacing";
               }
               enum "1588.62" {
                 description "1588.62 nm/188.712500 THz 3.125/6.25/12.5GHz spacing";
               }
               enum "1588.59" {
                 description "1588.59 nm/188.715625 THz 3.125GHz spacing";
               }
               enum "1588.57" {
                 description "1588.57 nm/188.718750 THz 3.125/6.25GHz spacing";
               }
               enum "1588.54" {
                 description "1588.54 nm/188.721875 THz 3.125GHz spacing";
               }
               enum "1588.51" {
                 description "1588.51 nm/188.725000 THz 3.125/6.25/12.5GHz spacing";
               }
               enum "1588.49" {
                 description "1588.49 nm/188.728125 THz 3.125GHz spacing";
               }
               enum "1588.46" {
                 description "1588.46 nm/188.731250 THz 3.125/6.25GHz spacing";
               }
               enum "1588.44" {
                 description "1588.44 nm/188.734375 THz 3.125GHz spacing";
               }
               enum "1588.41" {
                 description "1588.41 nm/188.737500 THz 3.125/6.25/12.5GHz spacing";
               }
               enum "1588.38" {
                 description "1588.38 nm/188.740625 THz 3.125GHz spacing";
               }
               enum "1588.36" {
                 description "1588.36 nm/188.743750 THz 3.125/6.25GHz spacing";
               }
               enum "1588.33" {
                 description "1588.33 nm/188.746875 THz 3.125GHz spacing";
               }
               enum "1588.30" {
                 description "1588.30 nm/188.750000 THz 3.125/6.25/12.5/50/75GHz spacing";
               }
               enum "1588.28" {
                 description "1588.28 nm/188.753125 THz 3.125GHz spacing";
               }
               enum "1588.25" {
                 description "1588.25 nm/188.756250 THz 3.125/6.25GHz spacing";
               }
               enum "1588.23" {
                 description "1588.23 nm/188.759375 THz 3.125GHz spacing";
               }
               enum "1588.20" {
                 description "1588.20 nm/188.762500 THz 3.125/6.25/12.5GHz spacing";
               }
               enum "1588.17" {
                 description "1588.17 nm/188.765625 THz 3.125GHz spacing";
               }
               enum "1588.15" {
                 description "1588.15 nm/188.768750 THz 3.125/6.25GHz spacing";
               }
               enum "1588.12" {
                 description "1588.12 nm/188.771875 THz 3.125GHz spacing";
               }
               enum "1588.09" {
                 description "1588.09 nm/188.775000 THz 3.125/6.25/12.5GHz spacing";
               }
               enum "1588.07" {
                 description "1588.07 nm/188.778125 THz 3.125GHz spacing";
               }
               enum "1588.04" {
                 description "1588.04 nm/188.781250 THz 3.125/6.25GHz spacing";
               }
               enum "1588.02" {
                 description "1588.02 nm/188.784375 THz 3.125GHz spacing";
               }
               enum "1587.99" {
                 description "1587.99 nm/188.787500 THz 3.125/6.25/12.5GHz spacing";
               }
               enum "1587.96" {
                 description "1587.96 nm/188.790625 THz 3.125GHz spacing";
               }
               enum "1587.94" {
                 description "1587.94 nm/188.793750 THz 3.125/6.25GHz spacing";
               }
               enum "1587.91" {
                 description "1587.91 nm/188.796875 THz 3.125GHz spacing";
               }
               enum "1587.88" {
                 description "1587.88 nm/188.800000 THz 3.125/6.25/12.5/100GHz spacing";
               }
               enum "1587.86" {
                 description "1587.86 nm/188.803125 THz 3.125GHz spacing";
               }
               enum "1587.83" {
                 description "1587.83 nm/188.806250 THz 3.125/6.25GHz spacing";
               }
               enum "1587.80" {
                 description "1587.80 nm/188.809375 THz 3.125GHz spacing";
               }
               enum "1587.78" {
                 description "1587.78 nm/188.812500 THz 3.125/6.25/12.5GHz spacing";
               }
               enum "1587.75" {
                 description "1587.75 nm/188.815625 THz 3.125GHz spacing";
               }
               enum "1587.73" {
                 description "1587.73 nm/188.818750 THz 3.125/6.25GHz spacing";
               }
               enum "1587.70" {
                 description "1587.70 nm/188.821875 THz 3.125GHz spacing";
               }
               enum "1587.67" {
                 description "1587.67 nm/188.825000 THz 3.125/6.25/12.5/75GHz spacing";
               }
               enum "1587.65" {
                 description "1587.65 nm/188.828125 THz 3.125GHz spacing";
               }
               enum "1587.62" {
                 description "1587.62 nm/188.831250 THz 3.125/6.25GHz spacing";
               }
               enum "1587.59" {
                 description "1587.59 nm/188.834375 THz 3.125GHz spacing";
               }
               enum "1587.57" {
                 description "1587.57 nm/188.837500 THz 3.125/6.25/12.5GHz spacing";
               }
               enum "1587.54" {
                 description "1587.54 nm/188.840625 THz 3.125GHz spacing";
               }
               enum "1587.52" {
                 description "1587.52 nm/188.843750 THz 3.125/6.25GHz spacing";
               }
               enum "1587.49" {
                 description "1587.49 nm/188.846875 THz 3.125GHz spacing";
               }
               enum "1587.46" {
                 description "1587.46 nm/188.850000 THz 3.125/6.25/12.5/50GHz spacing";
               }
               enum "1587.44" {
                 description "1587.44 nm/188.853125 THz 3.125GHz spacing";
               }
               enum "1587.41" {
                 description "1587.41 nm/188.856250 THz 3.125/6.25GHz spacing";
               }
               enum "1587.38" {
                 description "1587.38 nm/188.859375 THz 3.125GHz spacing";
               }
               enum "1587.36" {
                 description "1587.36 nm/188.862500 THz 3.125/6.25/12.5GHz spacing";
               }
               enum "1587.33" {
                 description "1587.33 nm/188.865625 THz 3.125GHz spacing";
               }
               enum "1587.31" {
                 description "1587.31 nm/188.868750 THz 3.125/6.25GHz spacing";
               }
               enum "1587.28" {
                 description "1587.28 nm/188.871875 THz 3.125GHz spacing";
               }
               enum "1587.25" {
                 description "1587.25 nm/188.875000 THz 3.125/6.25/12.5GHz spacing";
               }
               enum "1587.23" {
                 description "1587.23 nm/188.878125 THz 3.125GHz spacing";
               }
               enum "1587.20" {
                 description "1587.20 nm/188.881250 THz 3.125/6.25GHz spacing";
               }
               enum "1587.17" {
                 description "1587.17 nm/188.884375 THz 3.125GHz spacing";
               }
               enum "1587.15" {
                 description "1587.15 nm/188.887500 THz 3.125/6.25/12.5GHz spacing";
               }
               enum "1587.12" {
                 description "1587.12 nm/188.890625 THz 3.125GHz spacing";
               }
               enum "1587.10" {
                 description "1587.10 nm/188.893750 THz 3.125/6.25GHz spacing";
               }
               enum "1587.07" {
                 description "1587.07 nm/188.896875 THz 3.125GHz spacing";
               }
               enum "1587.04" {
                 description "1587.04 nm/188.900000 THz 3.125/6.25/12.5/100GHz spacing";
               }
               enum "1587.02" {
                 description "1587.02 nm/188.903125 THz 3.125GHz spacing";
               }
               enum "1586.99" {
                 description "1586.99 nm/188.906250 THz 3.125/6.25GHz spacing";
               }
               enum "1586.96" {
                 description "1586.96 nm/188.909375 THz 3.125GHz spacing";
               }
               enum "1586.94" {
                 description "1586.94 nm/188.912500 THz 3.125/6.25/12.5GHz spacing";
               }
               enum "1586.91" {
                 description "1586.91 nm/188.915625 THz 3.125GHz spacing";
               }
               enum "1586.89" {
                 description "1586.89 nm/188.918750 THz 3.125/6.25GHz spacing";
               }
               enum "1586.86" {
                 description "1586.86 nm/188.921875 THz 3.125GHz spacing";
               }
               enum "1586.83" {
                 description "1586.83 nm/188.925000 THz 3.125/6.25/12.5GHz spacing";
               }
               enum "1586.81" {
                 description "1586.81 nm/188.928125 THz 3.125GHz spacing";
               }
               enum "1586.78" {
                 description "1586.78 nm/188.931250 THz 3.125/6.25GHz spacing";
               }
               enum "1586.75" {
                 description "1586.75 nm/188.934375 THz 3.125GHz spacing";
               }
               enum "1586.73" {
                 description "1586.73 nm/188.937500 THz 3.125/6.25/12.5GHz spacing";
               }
               enum "1586.70" {
                 description "1586.70 nm/188.940625 THz 3.125GHz spacing";
               }
               enum "1586.68" {
                 description "1586.68 nm/188.943750 THz 3.125/6.25GHz spacing";
               }
               enum "1586.65" {
                 description "1586.65 nm/188.946875 THz 3.125GHz spacing";
               }
               enum "1586.62" {
                 description "1586.62 nm/188.950000 THz 3.125/6.25/12.5/50GHz spacing";
               }
               enum "1586.60" {
                 description "1586.60 nm/188.953125 THz 3.125GHz spacing";
               }
               enum "1586.57" {
                 description "1586.57 nm/188.956250 THz 3.125/6.25GHz spacing";
               }
               enum "1586.54" {
                 description "1586.54 nm/188.959375 THz 3.125GHz spacing";
               }
               enum "1586.52" {
                 description "1586.52 nm/188.962500 THz 3.125/6.25/12.5GHz spacing";
               }
               enum "1586.49" {
                 description "1586.49 nm/188.965625 THz 3.125GHz spacing";
               }
               enum "1586.47" {
                 description "1586.47 nm/188.968750 THz 3.125/6.25GHz spacing";
               }
               enum "1586.44" {
                 description "1586.44 nm/188.971875 THz 3.125GHz spacing";
               }
               enum "1586.41" {
                 description "1586.41 nm/188.975000 THz 3.125/6.25/12.5/75GHz spacing";
               }
               enum "1586.39" {
                 description "1586.39 nm/188.978125 THz 3.125GHz spacing";
               }
               enum "1586.36" {
                 description "1586.36 nm/188.981250 THz 3.125/6.25GHz spacing";
               }
               enum "1586.33" {
                 description "1586.33 nm/188.984375 THz 3.125GHz spacing";
               }
               enum "1586.31" {
                 description "1586.31 nm/188.987500 THz 3.125/6.25/12.5GHz spacing";
               }
               enum "1586.28" {
                 description "1586.28 nm/188.990625 THz 3.125GHz spacing";
               }
               enum "1586.26" {
                 description "1586.26 nm/188.993750 THz 3.125/6.25GHz spacing";
               }
               enum "1586.23" {
                 description "1586.23 nm/188.996875 THz 3.125GHz spacing";
               }
               enum "1586.20" {
                 description "1586.20 nm/189.000000 THz 3.125/6.25/12.5/50/75/100GHz spacing";
               }
               enum "1586.18" {
                 description "1586.18 nm/189.003125 THz 3.125GHz spacing";
               }
               enum "1586.15" {
                 description "1586.15 nm/189.006250 THz 3.125/6.25GHz spacing";
               }
               enum "1586.12" {
                 description "1586.12 nm/189.009375 THz 3.125GHz spacing";
               }
               enum "1586.10" {
                 description "1586.10 nm/189.012500 THz 3.125/6.25/12.5GHz spacing";
               }
               enum "1586.07" {
                 description "1586.07 nm/189.015625 THz 3.125GHz spacing";
               }
               enum "1586.05" {
                 description "1586.05 nm/189.018750 THz 3.125/6.25GHz spacing";
               }
               enum "1586.02" {
                 description "1586.02 nm/189.021875 THz 3.125GHz spacing";
               }
               enum "1585.99" {
                 description "1585.99 nm/189.025000 THz 3.125/6.25/12.5GHz spacing";
               }
               enum "1585.97" {
                 description "1585.97 nm/189.028125 THz 3.125GHz spacing";
               }
               enum "1585.94" {
                 description "1585.94 nm/189.031250 THz 3.125/6.25GHz spacing";
               }
               enum "1585.92" {
                 description "1585.92 nm/189.034375 THz 3.125GHz spacing";
               }
               enum "1585.89" {
                 description "1585.89 nm/189.037500 THz 3.125/6.25/12.5GHz spacing";
               }
               enum "1585.86" {
                 description "1585.86 nm/189.040625 THz 3.125GHz spacing";
               }
               enum "1585.84" {
                 description "1585.84 nm/189.043750 THz 3.125/6.25GHz spacing";
               }
               enum "1585.81" {
                 description "1585.81 nm/189.046875 THz 3.125GHz spacing";
               }
               enum "1585.78" {
                 description "1585.78 nm/189.050000 THz 3.125/6.25/12.5/50/75GHz spacing";
               }
               enum "1585.76" {
                 description "1585.76 nm/189.053125 THz 3.125GHz spacing";
               }
               enum "1585.73" {
                 description "1585.73 nm/189.056250 THz 3.125/6.25GHz spacing";
               }
               enum "1585.71" {
                 description "1585.71 nm/189.059375 THz 3.125GHz spacing";
               }
               enum "1585.68" {
                 description "1585.68 nm/189.062500 THz 3.125/6.25/12.5GHz spacing";
               }
               enum "1585.65" {
                 description "1585.65 nm/189.065625 THz 3.125GHz spacing";
               }
               enum "1585.63" {
                 description "1585.63 nm/189.068750 THz 3.125/6.25GHz spacing";
               }
               enum "1585.60" {
                 description "1585.60 nm/189.071875 THz 3.125GHz spacing";
               }
               enum "1585.57" {
                 description "1585.57 nm/189.075000 THz 3.125/6.25/12.5GHz spacing";
               }
               enum "1585.55" {
                 description "1585.55 nm/189.078125 THz 3.125GHz spacing";
               }
               enum "1585.52" {
                 description "1585.52 nm/189.081250 THz 3.125/6.25GHz spacing";
               }
               enum "1585.50" {
                 description "1585.50 nm/189.084375 THz 3.125GHz spacing";
               }
               enum "1585.47" {
                 description "1585.47 nm/189.087500 THz 3.125/6.25/12.5GHz spacing";
               }
               enum "1585.44" {
                 description "1585.44 nm/189.090625 THz 3.125GHz spacing";
               }
               enum "1585.42" {
                 description "1585.42 nm/189.093750 THz 3.125/6.25GHz spacing";
               }
               enum "1585.39" {
                 description "1585.39 nm/189.096875 THz 3.125GHz spacing";
               }
               enum "1585.36" {
                 description "1585.36 nm/189.100000 THz 3.125/6.25/12.5/100GHz spacing";
               }
               enum "1585.34" {
                 description "1585.34 nm/189.103125 THz 3.125GHz spacing";
               }
               enum "1585.31" {
                 description "1585.31 nm/189.106250 THz 3.125/6.25GHz spacing";
               }
               enum "1585.29" {
                 description "1585.29 nm/189.109375 THz 3.125GHz spacing";
               }
               enum "1585.26" {
                 description "1585.26 nm/189.112500 THz 3.125/6.25/12.5GHz spacing";
               }
               enum "1585.23" {
                 description "1585.23 nm/189.115625 THz 3.125GHz spacing";
               }
               enum "1585.21" {
                 description "1585.21 nm/189.118750 THz 3.125/6.25GHz spacing";
               }
               enum "1585.18" {
                 description "1585.18 nm/189.121875 THz 3.125GHz spacing";
               }
               enum "1585.16" {
                 description "1585.16 nm/189.125000 THz 3.125/6.25/12.5/75GHz spacing";
               }
               enum "1585.13" {
                 description "1585.13 nm/189.128125 THz 3.125GHz spacing";
               }
               enum "1585.10" {
                 description "1585.10 nm/189.131250 THz 3.125/6.25GHz spacing";
               }
               enum "1585.08" {
                 description "1585.08 nm/189.134375 THz 3.125GHz spacing";
               }
               enum "1585.05" {
                 description "1585.05 nm/189.137500 THz 3.125/6.25/12.5GHz spacing";
               }
               enum "1585.02" {
                 description "1585.02 nm/189.140625 THz 3.125GHz spacing";
               }
               enum "1585.00" {
                 description "1585.00 nm/189.143750 THz 3.125/6.25GHz spacing";
               }
               enum "1584.97" {
                 description "1584.97 nm/189.146875 THz 3.125GHz spacing";
               }
               enum "1584.95" {
                 description "1584.95 nm/189.150000 THz 3.125/6.25/12.5/50GHz spacing";
               }
               enum "1584.92" {
                 description "1584.92 nm/189.153125 THz 3.125GHz spacing";
               }
               enum "1584.89" {
                 description "1584.89 nm/189.156250 THz 3.125/6.25GHz spacing";
               }
               enum "1584.87" {
                 description "1584.87 nm/189.159375 THz 3.125GHz spacing";
               }
               enum "1584.84" {
                 description "1584.84 nm/189.162500 THz 3.125/6.25/12.5GHz spacing";
               }
               enum "1584.81" {
                 description "1584.81 nm/189.165625 THz 3.125GHz spacing";
               }
               enum "1584.79" {
                 description "1584.79 nm/189.168750 THz 3.125/6.25GHz spacing";
               }
               enum "1584.76" {
                 description "1584.76 nm/189.171875 THz 3.125GHz spacing";
               }
               enum "1584.74" {
                 description "1584.74 nm/189.175000 THz 3.125/6.25/12.5GHz spacing";
               }
               enum "1584.71" {
                 description "1584.71 nm/189.178125 THz 3.125GHz spacing";
               }
               enum "1584.68" {
                 description "1584.68 nm/189.181250 THz 3.125/6.25GHz spacing";
               }
               enum "1584.66" {
                 description "1584.66 nm/189.184375 THz 3.125GHz spacing";
               }
               enum "1584.63" {
                 description "1584.63 nm/189.187500 THz 3.125/6.25/12.5GHz spacing";
               }
               enum "1584.61" {
                 description "1584.61 nm/189.190625 THz 3.125GHz spacing";
               }
               enum "1584.58" {
                 description "1584.58 nm/189.193750 THz 3.125/6.25GHz spacing";
               }
               enum "1584.55" {
                 description "1584.55 nm/189.196875 THz 3.125GHz spacing";
               }
               enum "1584.53" {
                 description "1584.53 nm/189.200000 THz 3.125/6.25/12.5/100GHz spacing";
               }
               enum "1584.50" {
                 description "1584.50 nm/189.203125 THz 3.125GHz spacing";
               }
               enum "1584.47" {
                 description "1584.47 nm/189.206250 THz 3.125/6.25GHz spacing";
               }
               enum "1584.45" {
                 description "1584.45 nm/189.209375 THz 3.125GHz spacing";
               }
               enum "1584.42" {
                 description "1584.42 nm/189.212500 THz 3.125/6.25/12.5GHz spacing";
               }
               enum "1584.40" {
                 description "1584.40 nm/189.215625 THz 3.125GHz spacing";
               }
               enum "1584.37" {
                 description "1584.37 nm/189.218750 THz 3.125/6.25GHz spacing";
               }
               enum "1584.34" {
                 description "1584.34 nm/189.221875 THz 3.125GHz spacing";
               }
               enum "1584.32" {
                 description "1584.32 nm/189.225000 THz 3.125/6.25/12.5GHz spacing";
               }
               enum "1584.29" {
                 description "1584.29 nm/189.228125 THz 3.125GHz spacing";
               }
               enum "1584.27" {
                 description "1584.27 nm/189.231250 THz 3.125/6.25GHz spacing";
               }
               enum "1584.24" {
                 description "1584.24 nm/189.234375 THz 3.125GHz spacing";
               }
               enum "1584.21" {
                 description "1584.21 nm/189.237500 THz 3.125/6.25/12.5GHz spacing";
               }
               enum "1584.19" {
                 description "1584.19 nm/189.240625 THz 3.125GHz spacing";
               }
               enum "1584.16" {
                 description "1584.16 nm/189.243750 THz 3.125/6.25GHz spacing";
               }
               enum "1584.13" {
                 description "1584.13 nm/189.246875 THz 3.125GHz spacing";
               }
               enum "1584.11" {
                 description "1584.11 nm/189.250000 THz 3.125/6.25/12.5/50GHz spacing";
               }
               enum "1584.08" {
                 description "1584.08 nm/189.253125 THz 3.125GHz spacing";
               }
               enum "1584.06" {
                 description "1584.06 nm/189.256250 THz 3.125/6.25GHz spacing";
               }
               enum "1584.03" {
                 description "1584.03 nm/189.259375 THz 3.125GHz spacing";
               }
               enum "1584.00" {
                 description "1584.00 nm/189.262500 THz 3.125/6.25/12.5GHz spacing";
               }
               enum "1583.98" {
                 description "1583.98 nm/189.265625 THz 3.125GHz spacing";
               }
               enum "1583.95" {
                 description "1583.95 nm/189.268750 THz 3.125/6.25GHz spacing";
               }
               enum "1583.93" {
                 description "1583.93 nm/189.271875 THz 3.125GHz spacing";
               }
               enum "1583.90" {
                 description "1583.90 nm/189.275000 THz 3.125/6.25/12.5/75GHz spacing";
               }
               enum "1583.87" {
                 description "1583.87 nm/189.278125 THz 3.125GHz spacing";
               }
               enum "1583.85" {
                 description "1583.85 nm/189.281250 THz 3.125/6.25GHz spacing";
               }
               enum "1583.82" {
                 description "1583.82 nm/189.284375 THz 3.125GHz spacing";
               }
               enum "1583.79" {
                 description "1583.79 nm/189.287500 THz 3.125/6.25/12.5GHz spacing";
               }
               enum "1583.77" {
                 description "1583.77 nm/189.290625 THz 3.125GHz spacing";
               }
               enum "1583.74" {
                 description "1583.74 nm/189.293750 THz 3.125/6.25GHz spacing";
               }
               enum "1583.72" {
                 description "1583.72 nm/189.296875 THz 3.125GHz spacing";
               }
               enum "1583.69" {
                 description "1583.69 nm/189.300000 THz 3.125/6.25/12.5/50/75/100GHz spacing";
               }
               enum "1583.66" {
                 description "1583.66 nm/189.303125 THz 3.125GHz spacing";
               }
               enum "1583.64" {
                 description "1583.64 nm/189.306250 THz 3.125/6.25GHz spacing";
               }
               enum "1583.61" {
                 description "1583.61 nm/189.309375 THz 3.125GHz spacing";
               }
               enum "1583.59" {
                 description "1583.59 nm/189.312500 THz 3.125/6.25/12.5GHz spacing";
               }
               enum "1583.56" {
                 description "1583.56 nm/189.315625 THz 3.125GHz spacing";
               }
               enum "1583.53" {
                 description "1583.53 nm/189.318750 THz 3.125/6.25GHz spacing";
               }
               enum "1583.51" {
                 description "1583.51 nm/189.321875 THz 3.125GHz spacing";
               }
               enum "1583.48" {
                 description "1583.48 nm/189.325000 THz 3.125/6.25/12.5GHz spacing";
               }
               enum "1583.45" {
                 description "1583.45 nm/189.328125 THz 3.125GHz spacing";
               }
               enum "1583.43" {
                 description "1583.43 nm/189.331250 THz 3.125/6.25GHz spacing";
               }
               enum "1583.40" {
                 description "1583.40 nm/189.334375 THz 3.125GHz spacing";
               }
               enum "1583.38" {
                 description "1583.38 nm/189.337500 THz 3.125/6.25/12.5GHz spacing";
               }
               enum "1583.35" {
                 description "1583.35 nm/189.340625 THz 3.125GHz spacing";
               }
               enum "1583.32" {
                 description "1583.32 nm/189.343750 THz 3.125/6.25GHz spacing";
               }
               enum "1583.30" {
                 description "1583.30 nm/189.346875 THz 3.125GHz spacing";
               }
               enum "1583.27" {
                 description "1583.27 nm/189.350000 THz 3.125/6.25/12.5/50/75GHz spacing";
               }
               enum "1583.25" {
                 description "1583.25 nm/189.353125 THz 3.125GHz spacing";
               }
               enum "1583.22" {
                 description "1583.22 nm/189.356250 THz 3.125/6.25GHz spacing";
               }
               enum "1583.19" {
                 description "1583.19 nm/189.359375 THz 3.125GHz spacing";
               }
               enum "1583.17" {
                 description "1583.17 nm/189.362500 THz 3.125/6.25/12.5GHz spacing";
               }
               enum "1583.14" {
                 description "1583.14 nm/189.365625 THz 3.125GHz spacing";
               }
               enum "1583.11" {
                 description "1583.11 nm/189.368750 THz 3.125/6.25GHz spacing";
               }
               enum "1583.09" {
                 description "1583.09 nm/189.371875 THz 3.125GHz spacing";
               }
               enum "1583.06" {
                 description "1583.06 nm/189.375000 THz 3.125/6.25/12.5GHz spacing";
               }
               enum "1583.04" {
                 description "1583.04 nm/189.378125 THz 3.125GHz spacing";
               }
               enum "1583.01" {
                 description "1583.01 nm/189.381250 THz 3.125/6.25GHz spacing";
               }
               enum "1582.98" {
                 description "1582.98 nm/189.384375 THz 3.125GHz spacing";
               }
               enum "1582.96" {
                 description "1582.96 nm/189.387500 THz 3.125/6.25/12.5GHz spacing";
               }
               enum "1582.93" {
                 description "1582.93 nm/189.390625 THz 3.125GHz spacing";
               }
               enum "1582.91" {
                 description "1582.91 nm/189.393750 THz 3.125/6.25GHz spacing";
               }
               enum "1582.88" {
                 description "1582.88 nm/189.396875 THz 3.125GHz spacing";
               }
               enum "1582.85" {
                 description "1582.85 nm/189.400000 THz 3.125/6.25/12.5/100GHz spacing";
               }
               enum "1582.83" {
                 description "1582.83 nm/189.403125 THz 3.125GHz spacing";
               }
               enum "1582.80" {
                 description "1582.80 nm/189.406250 THz 3.125/6.25GHz spacing";
               }
               enum "1582.78" {
                 description "1582.78 nm/189.409375 THz 3.125GHz spacing";
               }
               enum "1582.75" {
                 description "1582.75 nm/189.412500 THz 3.125/6.25/12.5GHz spacing";
               }
               enum "1582.72" {
                 description "1582.72 nm/189.415625 THz 3.125GHz spacing";
               }
               enum "1582.70" {
                 description "1582.70 nm/189.418750 THz 3.125/6.25GHz spacing";
               }
               enum "1582.67" {
                 description "1582.67 nm/189.421875 THz 3.125GHz spacing";
               }
               enum "1582.64" {
                 description "1582.64 nm/189.425000 THz 3.125/6.25/12.5/75GHz spacing";
               }
               enum "1582.62" {
                 description "1582.62 nm/189.428125 THz 3.125GHz spacing";
               }
               enum "1582.59" {
                 description "1582.59 nm/189.431250 THz 3.125/6.25GHz spacing";
               }
               enum "1582.57" {
                 description "1582.57 nm/189.434375 THz 3.125GHz spacing";
               }
               enum "1582.54" {
                 description "1582.54 nm/189.437500 THz 3.125/6.25/12.5GHz spacing";
               }
               enum "1582.51" {
                 description "1582.51 nm/189.440625 THz 3.125GHz spacing";
               }
               enum "1582.49" {
                 description "1582.49 nm/189.443750 THz 3.125/6.25GHz spacing";
               }
               enum "1582.46" {
                 description "1582.46 nm/189.446875 THz 3.125GHz spacing";
               }
               enum "1582.44" {
                 description "1582.44 nm/189.450000 THz 3.125/6.25/12.5/50GHz spacing";
               }
               enum "1582.41" {
                 description "1582.41 nm/189.453125 THz 3.125GHz spacing";
               }
               enum "1582.38" {
                 description "1582.38 nm/189.456250 THz 3.125/6.25GHz spacing";
               }
               enum "1582.36" {
                 description "1582.36 nm/189.459375 THz 3.125GHz spacing";
               }
               enum "1582.33" {
                 description "1582.33 nm/189.462500 THz 3.125/6.25/12.5GHz spacing";
               }
               enum "1582.31" {
                 description "1582.31 nm/189.465625 THz 3.125GHz spacing";
               }
               enum "1582.28" {
                 description "1582.28 nm/189.468750 THz 3.125/6.25GHz spacing";
               }
               enum "1582.25" {
                 description "1582.25 nm/189.471875 THz 3.125GHz spacing";
               }
               enum "1582.23" {
                 description "1582.23 nm/189.475000 THz 3.125/6.25/12.5GHz spacing";
               }
               enum "1582.20" {
                 description "1582.20 nm/189.478125 THz 3.125GHz spacing";
               }
               enum "1582.17" {
                 description "1582.17 nm/189.481250 THz 3.125/6.25GHz spacing";
               }
               enum "1582.15" {
                 description "1582.15 nm/189.484375 THz 3.125GHz spacing";
               }
               enum "1582.12" {
                 description "1582.12 nm/189.487500 THz 3.125/6.25/12.5GHz spacing";
               }
               enum "1582.10" {
                 description "1582.10 nm/189.490625 THz 3.125GHz spacing";
               }
               enum "1582.07" {
                 description "1582.07 nm/189.493750 THz 3.125/6.25GHz spacing";
               }
               enum "1582.04" {
                 description "1582.04 nm/189.496875 THz 3.125GHz spacing";
               }
               enum "1582.02" {
                 description "1582.02 nm/189.500000 THz 3.125/6.25/12.5/100GHz spacing";
               }
               enum "1581.99" {
                 description "1581.99 nm/189.503125 THz 3.125GHz spacing";
               }
               enum "1581.97" {
                 description "1581.97 nm/189.506250 THz 3.125/6.25GHz spacing";
               }
               enum "1581.94" {
                 description "1581.94 nm/189.509375 THz 3.125GHz spacing";
               }
               enum "1581.91" {
                 description "1581.91 nm/189.512500 THz 3.125/6.25/12.5GHz spacing";
               }
               enum "1581.89" {
                 description "1581.89 nm/189.515625 THz 3.125GHz spacing";
               }
               enum "1581.86" {
                 description "1581.86 nm/189.518750 THz 3.125/6.25GHz spacing";
               }
               enum "1581.84" {
                 description "1581.84 nm/189.521875 THz 3.125GHz spacing";
               }
               enum "1581.81" {
                 description "1581.81 nm/189.525000 THz 3.125/6.25/12.5GHz spacing";
               }
               enum "1581.78" {
                 description "1581.78 nm/189.528125 THz 3.125GHz spacing";
               }
               enum "1581.76" {
                 description "1581.76 nm/189.531250 THz 3.125/6.25GHz spacing";
               }
               enum "1581.73" {
                 description "1581.73 nm/189.534375 THz 3.125GHz spacing";
               }
               enum "1581.71" {
                 description "1581.71 nm/189.537500 THz 3.125/6.25/12.5GHz spacing";
               }
               enum "1581.68" {
                 description "1581.68 nm/189.540625 THz 3.125GHz spacing";
               }
               enum "1581.65" {
                 description "1581.65 nm/189.543750 THz 3.125/6.25GHz spacing";
               }
               enum "1581.63" {
                 description "1581.63 nm/189.546875 THz 3.125GHz spacing";
               }
               enum "1581.60" {
                 description "1581.60 nm/189.550000 THz 3.125/6.25/12.5/50GHz spacing";
               }
               enum "1581.57" {
                 description "1581.57 nm/189.553125 THz 3.125GHz spacing";
               }
               enum "1581.55" {
                 description "1581.55 nm/189.556250 THz 3.125/6.25GHz spacing";
               }
               enum "1581.52" {
                 description "1581.52 nm/189.559375 THz 3.125GHz spacing";
               }
               enum "1581.50" {
                 description "1581.50 nm/189.562500 THz 3.125/6.25/12.5GHz spacing";
               }
               enum "1581.47" {
                 description "1581.47 nm/189.565625 THz 3.125GHz spacing";
               }
               enum "1581.44" {
                 description "1581.44 nm/189.568750 THz 3.125/6.25GHz spacing";
               }
               enum "1581.42" {
                 description "1581.42 nm/189.571875 THz 3.125GHz spacing";
               }
               enum "1581.39" {
                 description "1581.39 nm/189.575000 THz 3.125/6.25/12.5/75GHz spacing";
               }
               enum "1581.37" {
                 description "1581.37 nm/189.578125 THz 3.125GHz spacing";
               }
               enum "1581.34" {
                 description "1581.34 nm/189.581250 THz 3.125/6.25GHz spacing";
               }
               enum "1581.31" {
                 description "1581.31 nm/189.584375 THz 3.125GHz spacing";
               }
               enum "1581.29" {
                 description "1581.29 nm/189.587500 THz 3.125/6.25/12.5GHz spacing";
               }
               enum "1581.26" {
                 description "1581.26 nm/189.590625 THz 3.125GHz spacing";
               }
               enum "1581.24" {
                 description "1581.24 nm/189.593750 THz 3.125/6.25GHz spacing";
               }
               enum "1581.21" {
                 description "1581.21 nm/189.596875 THz 3.125GHz spacing";
               }
               enum "1581.18" {
                 description "1581.18 nm/189.600000 THz 3.125/6.25/12.5/50/75/100GHz spacing";
               }
               enum "1581.16" {
                 description "1581.16 nm/189.603125 THz 3.125GHz spacing";
               }
               enum "1581.13" {
                 description "1581.13 nm/189.606250 THz 3.125/6.25GHz spacing";
               }
               enum "1581.11" {
                 description "1581.11 nm/189.609375 THz 3.125GHz spacing";
               }
               enum "1581.08" {
                 description "1581.08 nm/189.612500 THz 3.125/6.25/12.5GHz spacing";
               }
               enum "1581.05" {
                 description "1581.05 nm/189.615625 THz 3.125GHz spacing";
               }
               enum "1581.03" {
                 description "1581.03 nm/189.618750 THz 3.125/6.25GHz spacing";
               }
               enum "1581.00" {
                 description "1581.00 nm/189.621875 THz 3.125GHz spacing";
               }
               enum "1580.98" {
                 description "1580.98 nm/189.625000 THz 3.125/6.25/12.5GHz spacing";
               }
               enum "1580.95" {
                 description "1580.95 nm/189.628125 THz 3.125GHz spacing";
               }
               enum "1580.92" {
                 description "1580.92 nm/189.631250 THz 3.125/6.25GHz spacing";
               }
               enum "1580.90" {
                 description "1580.90 nm/189.634375 THz 3.125GHz spacing";
               }
               enum "1580.87" {
                 description "1580.87 nm/189.637500 THz 3.125/6.25/12.5GHz spacing";
               }
               enum "1580.85" {
                 description "1580.85 nm/189.640625 THz 3.125GHz spacing";
               }
               enum "1580.82" {
                 description "1580.82 nm/189.643750 THz 3.125/6.25GHz spacing";
               }
               enum "1580.79" {
                 description "1580.79 nm/189.646875 THz 3.125GHz spacing";
               }
               enum "1580.77" {
                 description "1580.77 nm/189.650000 THz 3.125/6.25/12.5/50/75GHz spacing";
               }
               enum "1580.74" {
                 description "1580.74 nm/189.653125 THz 3.125GHz spacing";
               }
               enum "1580.71" {
                 description "1580.71 nm/189.656250 THz 3.125/6.25GHz spacing";
               }
               enum "1580.69" {
                 description "1580.69 nm/189.659375 THz 3.125GHz spacing";
               }
               enum "1580.66" {
                 description "1580.66 nm/189.662500 THz 3.125/6.25/12.5GHz spacing";
               }
               enum "1580.64" {
                 description "1580.64 nm/189.665625 THz 3.125GHz spacing";
               }
               enum "1580.61" {
                 description "1580.61 nm/189.668750 THz 3.125/6.25GHz spacing";
               }
               enum "1580.58" {
                 description "1580.58 nm/189.671875 THz 3.125GHz spacing";
               }
               enum "1580.56" {
                 description "1580.56 nm/189.675000 THz 3.125/6.25/12.5GHz spacing";
               }
               enum "1580.53" {
                 description "1580.53 nm/189.678125 THz 3.125GHz spacing";
               }
               enum "1580.51" {
                 description "1580.51 nm/189.681250 THz 3.125/6.25GHz spacing";
               }
               enum "1580.48" {
                 description "1580.48 nm/189.684375 THz 3.125GHz spacing";
               }
               enum "1580.45" {
                 description "1580.45 nm/189.687500 THz 3.125/6.25/12.5GHz spacing";
               }
               enum "1580.43" {
                 description "1580.43 nm/189.690625 THz 3.125GHz spacing";
               }
               enum "1580.40" {
                 description "1580.40 nm/189.693750 THz 3.125/6.25GHz spacing";
               }
               enum "1580.38" {
                 description "1580.38 nm/189.696875 THz 3.125GHz spacing";
               }
               enum "1580.35" {
                 description "1580.35 nm/189.700000 THz 3.125/6.25/12.5/100GHz spacing";
               }
               enum "1580.32" {
                 description "1580.32 nm/189.703125 THz 3.125GHz spacing";
               }
               enum "1580.30" {
                 description "1580.30 nm/189.706250 THz 3.125/6.25GHz spacing";
               }
               enum "1580.27" {
                 description "1580.27 nm/189.709375 THz 3.125GHz spacing";
               }
               enum "1580.25" {
                 description "1580.25 nm/189.712500 THz 3.125/6.25/12.5GHz spacing";
               }
               enum "1580.22" {
                 description "1580.22 nm/189.715625 THz 3.125GHz spacing";
               }
               enum "1580.19" {
                 description "1580.19 nm/189.718750 THz 3.125/6.25GHz spacing";
               }
               enum "1580.17" {
                 description "1580.17 nm/189.721875 THz 3.125GHz spacing";
               }
               enum "1580.14" {
                 description "1580.14 nm/189.725000 THz 3.125/6.25/12.5/75GHz spacing";
               }
               enum "1580.12" {
                 description "1580.12 nm/189.728125 THz 3.125GHz spacing";
               }
               enum "1580.09" {
                 description "1580.09 nm/189.731250 THz 3.125/6.25GHz spacing";
               }
               enum "1580.06" {
                 description "1580.06 nm/189.734375 THz 3.125GHz spacing";
               }
               enum "1580.04" {
                 description "1580.04 nm/189.737500 THz 3.125/6.25/12.5GHz spacing";
               }
               enum "1580.01" {
                 description "1580.01 nm/189.740625 THz 3.125GHz spacing";
               }
               enum "1579.99" {
                 description "1579.99 nm/189.743750 THz 3.125/6.25GHz spacing";
               }
               enum "1579.96" {
                 description "1579.96 nm/189.746875 THz 3.125GHz spacing";
               }
               enum "1579.93" {
                 description "1579.93 nm/189.750000 THz 3.125/6.25/12.5/50GHz spacing";
               }
               enum "1579.91" {
                 description "1579.91 nm/189.753125 THz 3.125GHz spacing";
               }
               enum "1579.88" {
                 description "1579.88 nm/189.756250 THz 3.125/6.25GHz spacing";
               }
               enum "1579.86" {
                 description "1579.86 nm/189.759375 THz 3.125GHz spacing";
               }
               enum "1579.83" {
                 description "1579.83 nm/189.762500 THz 3.125/6.25/12.5GHz spacing";
               }
               enum "1579.80" {
                 description "1579.80 nm/189.765625 THz 3.125GHz spacing";
               }
               enum "1579.78" {
                 description "1579.78 nm/189.768750 THz 3.125/6.25GHz spacing";
               }
               enum "1579.75" {
                 description "1579.75 nm/189.771875 THz 3.125GHz spacing";
               }
               enum "1579.73" {
                 description "1579.73 nm/189.775000 THz 3.125/6.25/12.5GHz spacing";
               }
               enum "1579.70" {
                 description "1579.70 nm/189.778125 THz 3.125GHz spacing";
               }
               enum "1579.67" {
                 description "1579.67 nm/189.781250 THz 3.125/6.25GHz spacing";
               }
               enum "1579.65" {
                 description "1579.65 nm/189.784375 THz 3.125GHz spacing";
               }
               enum "1579.62" {
                 description "1579.62 nm/189.787500 THz 3.125/6.25/12.5GHz spacing";
               }
               enum "1579.60" {
                 description "1579.60 nm/189.790625 THz 3.125GHz spacing";
               }
               enum "1579.57" {
                 description "1579.57 nm/189.793750 THz 3.125/6.25GHz spacing";
               }
               enum "1579.54" {
                 description "1579.54 nm/189.796875 THz 3.125GHz spacing";
               }
               enum "1579.52" {
                 description "1579.52 nm/189.800000 THz 3.125/6.25/12.5/100GHz spacing";
               }
               enum "1579.49" {
                 description "1579.49 nm/189.803125 THz 3.125GHz spacing";
               }
               enum "1579.47" {
                 description "1579.47 nm/189.806250 THz 3.125/6.25GHz spacing";
               }
               enum "1579.44" {
                 description "1579.44 nm/189.809375 THz 3.125GHz spacing";
               }
               enum "1579.41" {
                 description "1579.41 nm/189.812500 THz 3.125/6.25/12.5GHz spacing";
               }
               enum "1579.39" {
                 description "1579.39 nm/189.815625 THz 3.125GHz spacing";
               }
               enum "1579.36" {
                 description "1579.36 nm/189.818750 THz 3.125/6.25GHz spacing";
               }
               enum "1579.34" {
                 description "1579.34 nm/189.821875 THz 3.125GHz spacing";
               }
               enum "1579.31" {
                 description "1579.31 nm/189.825000 THz 3.125/6.25/12.5GHz spacing";
               }
               enum "1579.28" {
                 description "1579.28 nm/189.828125 THz 3.125GHz spacing";
               }
               enum "1579.26" {
                 description "1579.26 nm/189.831250 THz 3.125/6.25GHz spacing";
               }
               enum "1579.23" {
                 description "1579.23 nm/189.834375 THz 3.125GHz spacing";
               }
               enum "1579.21" {
                 description "1579.21 nm/189.837500 THz 3.125/6.25/12.5GHz spacing";
               }
               enum "1579.18" {
                 description "1579.18 nm/189.840625 THz 3.125GHz spacing";
               }
               enum "1579.15" {
                 description "1579.15 nm/189.843750 THz 3.125/6.25GHz spacing";
               }
               enum "1579.13" {
                 description "1579.13 nm/189.846875 THz 3.125GHz spacing";
               }
               enum "1579.10" {
                 description "1579.10 nm/189.850000 THz 3.125/6.25/12.5/50GHz spacing";
               }
               enum "1579.08" {
                 description "1579.08 nm/189.853125 THz 3.125GHz spacing";
               }
               enum "1579.05" {
                 description "1579.05 nm/189.856250 THz 3.125/6.25GHz spacing";
               }
               enum "1579.02" {
                 description "1579.02 nm/189.859375 THz 3.125GHz spacing";
               }
               enum "1579.00" {
                 description "1579.00 nm/189.862500 THz 3.125/6.25/12.5GHz spacing";
               }
               enum "1578.97" {
                 description "1578.97 nm/189.865625 THz 3.125GHz spacing";
               }
               enum "1578.95" {
                 description "1578.95 nm/189.868750 THz 3.125/6.25GHz spacing";
               }
               enum "1578.92" {
                 description "1578.92 nm/189.871875 THz 3.125GHz spacing";
               }
               enum "1578.89" {
                 description "1578.89 nm/189.875000 THz 3.125/6.25/12.5/75GHz spacing";
               }
               enum "1578.87" {
                 description "1578.87 nm/189.878125 THz 3.125GHz spacing";
               }
               enum "1578.84" {
                 description "1578.84 nm/189.881250 THz 3.125/6.25GHz spacing";
               }
               enum "1578.82" {
                 description "1578.82 nm/189.884375 THz 3.125GHz spacing";
               }
               enum "1578.79" {
                 description "1578.79 nm/189.887500 THz 3.125/6.25/12.5GHz spacing";
               }
               enum "1578.76" {
                 description "1578.76 nm/189.890625 THz 3.125GHz spacing";
               }
               enum "1578.74" {
                 description "1578.74 nm/189.893750 THz 3.125/6.25GHz spacing";
               }
               enum "1578.71" {
                 description "1578.71 nm/189.896875 THz 3.125GHz spacing";
               }
               enum "1578.69" {
                 description "1578.69 nm/189.900000 THz 3.125/6.25/12.5/50/75/100GHz spacing";
               }
               enum "1578.66" {
                 description "1578.66 nm/189.903125 THz 3.125GHz spacing";
               }
               enum "1578.63" {
                 description "1578.63 nm/189.906250 THz 3.125/6.25GHz spacing";
               }
               enum "1578.61" {
                 description "1578.61 nm/189.909375 THz 3.125GHz spacing";
               }
               enum "1578.58" {
                 description "1578.58 nm/189.912500 THz 3.125/6.25/12.5GHz spacing";
               }
               enum "1578.56" {
                 description "1578.56 nm/189.915625 THz 3.125GHz spacing";
               }
               enum "1578.53" {
                 description "1578.53 nm/189.918750 THz 3.125/6.25GHz spacing";
               }
               enum "1578.50" {
                 description "1578.50 nm/189.921875 THz 3.125GHz spacing";
               }
               enum "1578.48" {
                 description "1578.48 nm/189.925000 THz 3.125/6.25/12.5GHz spacing";
               }
               enum "1578.45" {
                 description "1578.45 nm/189.928125 THz 3.125GHz spacing";
               }
               enum "1578.43" {
                 description "1578.43 nm/189.931250 THz 3.125/6.25GHz spacing";
               }
               enum "1578.40" {
                 description "1578.40 nm/189.934375 THz 3.125GHz spacing";
               }
               enum "1578.37" {
                 description "1578.37 nm/189.937500 THz 3.125/6.25/12.5GHz spacing";
               }
               enum "1578.35" {
                 description "1578.35 nm/189.940625 THz 3.125GHz spacing";
               }
               enum "1578.32" {
                 description "1578.32 nm/189.943750 THz 3.125/6.25GHz spacing";
               }
               enum "1578.30" {
                 description "1578.30 nm/189.946875 THz 3.125GHz spacing";
               }
               enum "1578.27" {
                 description "1578.27 nm/189.950000 THz 3.125/6.25/12.5/50/75GHz spacing";
               }
               enum "1578.24" {
                 description "1578.24 nm/189.953125 THz 3.125GHz spacing";
               }
               enum "1578.22" {
                 description "1578.22 nm/189.956250 THz 3.125/6.25GHz spacing";
               }
               enum "1578.19" {
                 description "1578.19 nm/189.959375 THz 3.125GHz spacing";
               }
               enum "1578.17" {
                 description "1578.17 nm/189.962500 THz 3.125/6.25/12.5GHz spacing";
               }
               enum "1578.14" {
                 description "1578.14 nm/189.965625 THz 3.125GHz spacing";
               }
               enum "1578.11" {
                 description "1578.11 nm/189.968750 THz 3.125/6.25GHz spacing";
               }
               enum "1578.09" {
                 description "1578.09 nm/189.971875 THz 3.125GHz spacing";
               }
               enum "1578.06" {
                 description "1578.06 nm/189.975000 THz 3.125/6.25/12.5GHz spacing";
               }
               enum "1578.04" {
                 description "1578.04 nm/189.978125 THz 3.125GHz spacing";
               }
               enum "1578.01" {
                 description "1578.01 nm/189.981250 THz 3.125/6.25GHz spacing";
               }
               enum "1577.98" {
                 description "1577.98 nm/189.984375 THz 3.125GHz spacing";
               }
               enum "1577.96" {
                 description "1577.96 nm/189.987500 THz 3.125/6.25/12.5GHz spacing";
               }
               enum "1577.93" {
                 description "1577.93 nm/189.990625 THz 3.125GHz spacing";
               }
               enum "1577.91" {
                 description "1577.91 nm/189.993750 THz 3.125/6.25GHz spacing";
               }
               enum "1577.88" {
                 description "1577.88 nm/189.996875 THz 3.125GHz spacing";
               }
               enum "1577.86" {
                 description "1577.86 nm/190.000000 THz 3.125/6.25/12.5/100GHz spacing";
               }
               enum "1577.83" {
                 description "1577.83 nm/190.003125 THz 3.125GHz spacing";
               }
               enum "1577.80" {
                 description "1577.80 nm/190.006250 THz 3.125/6.25GHz spacing";
               }
               enum "1577.78" {
                 description "1577.78 nm/190.009375 THz 3.125GHz spacing";
               }
               enum "1577.75" {
                 description "1577.75 nm/190.012500 THz 3.125/6.25/12.5GHz spacing";
               }
               enum "1577.73" {
                 description "1577.73 nm/190.015625 THz 3.125GHz spacing";
               }
               enum "1577.70" {
                 description "1577.70 nm/190.018750 THz 3.125/6.25GHz spacing";
               }
               enum "1577.67" {
                 description "1577.67 nm/190.021875 THz 3.125GHz spacing";
               }
               enum "1577.65" {
                 description "1577.65 nm/190.025000 THz 3.125/6.25/12.5/75GHz spacing";
               }
               enum "1577.62" {
                 description "1577.62 nm/190.028125 THz 3.125GHz spacing";
               }
               enum "1577.60" {
                 description "1577.60 nm/190.031250 THz 3.125/6.25GHz spacing";
               }
               enum "1577.57" {
                 description "1577.57 nm/190.034375 THz 3.125GHz spacing";
               }
               enum "1577.54" {
                 description "1577.54 nm/190.037500 THz 3.125/6.25/12.5GHz spacing";
               }
               enum "1577.52" {
                 description "1577.52 nm/190.040625 THz 3.125GHz spacing";
               }
               enum "1577.49" {
                 description "1577.49 nm/190.043750 THz 3.125/6.25GHz spacing";
               }
               enum "1577.47" {
                 description "1577.47 nm/190.046875 THz 3.125GHz spacing";
               }
               enum "1577.44" {
                 description "1577.44 nm/190.050000 THz 3.125/6.25/12.5/50GHz spacing";
               }
               enum "1577.41" {
                 description "1577.41 nm/190.053125 THz 3.125GHz spacing";
               }
               enum "1577.39" {
                 description "1577.39 nm/190.056250 THz 3.125/6.25GHz spacing";
               }
               enum "1577.36" {
                 description "1577.36 nm/190.059375 THz 3.125GHz spacing";
               }
               enum "1577.34" {
                 description "1577.34 nm/190.062500 THz 3.125/6.25/12.5GHz spacing";
               }
               enum "1577.31" {
                 description "1577.31 nm/190.065625 THz 3.125GHz spacing";
               }
               enum "1577.28" {
                 description "1577.28 nm/190.068750 THz 3.125/6.25GHz spacing";
               }
               enum "1577.26" {
                 description "1577.26 nm/190.071875 THz 3.125GHz spacing";
               }
               enum "1577.23" {
                 description "1577.23 nm/190.075000 THz 3.125/6.25/12.5GHz spacing";
               }
               enum "1577.21" {
                 description "1577.21 nm/190.078125 THz 3.125GHz spacing";
               }
               enum "1577.18" {
                 description "1577.18 nm/190.081250 THz 3.125/6.25GHz spacing";
               }
               enum "1577.15" {
                 description "1577.15 nm/190.084375 THz 3.125GHz spacing";
               }
               enum "1577.13" {
                 description "1577.13 nm/190.087500 THz 3.125/6.25/12.5GHz spacing";
               }
               enum "1577.10" {
                 description "1577.10 nm/190.090625 THz 3.125GHz spacing";
               }
               enum "1577.08" {
                 description "1577.08 nm/190.093750 THz 3.125/6.25GHz spacing";
               }
               enum "1577.05" {
                 description "1577.05 nm/190.096875 THz 3.125GHz spacing";
               }
               enum "1577.03" {
                 description "1577.03 nm/190.100000 THz 3.125/6.25/12.5/100GHz spacing";
               }
               enum "1577.00" {
                 description "1577.00 nm/190.103125 THz 3.125GHz spacing";
               }
               enum "1576.97" {
                 description "1576.97 nm/190.106250 THz 3.125/6.25GHz spacing";
               }
               enum "1576.95" {
                 description "1576.95 nm/190.109375 THz 3.125GHz spacing";
               }
               enum "1576.92" {
                 description "1576.92 nm/190.112500 THz 3.125/6.25/12.5GHz spacing";
               }
               enum "1576.90" {
                 description "1576.90 nm/190.115625 THz 3.125GHz spacing";
               }
               enum "1576.87" {
                 description "1576.87 nm/190.118750 THz 3.125/6.25GHz spacing";
               }
               enum "1576.84" {
                 description "1576.84 nm/190.121875 THz 3.125GHz spacing";
               }
               enum "1576.82" {
                 description "1576.82 nm/190.125000 THz 3.125/6.25/12.5GHz spacing";
               }
               enum "1576.79" {
                 description "1576.79 nm/190.128125 THz 3.125GHz spacing";
               }
               enum "1576.77" {
                 description "1576.77 nm/190.131250 THz 3.125/6.25GHz spacing";
               }
               enum "1576.74" {
                 description "1576.74 nm/190.134375 THz 3.125GHz spacing";
               }
               enum "1576.71" {
                 description "1576.71 nm/190.137500 THz 3.125/6.25/12.5GHz spacing";
               }
               enum "1576.69" {
                 description "1576.69 nm/190.140625 THz 3.125GHz spacing";
               }
               enum "1576.66" {
                 description "1576.66 nm/190.143750 THz 3.125/6.25GHz spacing";
               }
               enum "1576.64" {
                 description "1576.64 nm/190.146875 THz 3.125GHz spacing";
               }
               enum "1576.61" {
                 description "1576.61 nm/190.150000 THz 3.125/6.25/12.5/50GHz spacing";
               }
               enum "1576.58" {
                 description "1576.58 nm/190.153125 THz 3.125GHz spacing";
               }
               enum "1576.56" {
                 description "1576.56 nm/190.156250 THz 3.125/6.25GHz spacing";
               }
               enum "1576.53" {
                 description "1576.53 nm/190.159375 THz 3.125GHz spacing";
               }
               enum "1576.51" {
                 description "1576.51 nm/190.162500 THz 3.125/6.25/12.5GHz spacing";
               }
               enum "1576.48" {
                 description "1576.48 nm/190.165625 THz 3.125GHz spacing";
               }
               enum "1576.45" {
                 description "1576.45 nm/190.168750 THz 3.125/6.25GHz spacing";
               }
               enum "1576.43" {
                 description "1576.43 nm/190.171875 THz 3.125GHz spacing";
               }
               enum "1576.40" {
                 description "1576.40 nm/190.175000 THz 3.125/6.25/12.5/75GHz spacing";
               }
               enum "1576.38" {
                 description "1576.38 nm/190.178125 THz 3.125GHz spacing";
               }
               enum "1576.35" {
                 description "1576.35 nm/190.181250 THz 3.125/6.25GHz spacing";
               }
               enum "1576.33" {
                 description "1576.33 nm/190.184375 THz 3.125GHz spacing";
               }
               enum "1576.30" {
                 description "1576.30 nm/190.187500 THz 3.125/6.25/12.5GHz spacing";
               }
               enum "1576.27" {
                 description "1576.27 nm/190.190625 THz 3.125GHz spacing";
               }
               enum "1576.25" {
                 description "1576.25 nm/190.193750 THz 3.125/6.25GHz spacing";
               }
               enum "1576.22" {
                 description "1576.22 nm/190.196875 THz 3.125GHz spacing";
               }
               enum "1576.20" {
                 description "1576.20 nm/190.200000 THz 3.125/6.25/12.5/50/75/100GHz spacing";
               }
               enum "1576.17" {
                 description "1576.17 nm/190.203125 THz 3.125GHz spacing";
               }
               enum "1576.14" {
                 description "1576.14 nm/190.206250 THz 3.125/6.25GHz spacing";
               }
               enum "1576.12" {
                 description "1576.12 nm/190.209375 THz 3.125GHz spacing";
               }
               enum "1576.09" {
                 description "1576.09 nm/190.212500 THz 3.125/6.25/12.5GHz spacing";
               }
               enum "1576.07" {
                 description "1576.07 nm/190.215625 THz 3.125GHz spacing";
               }
               enum "1576.04" {
                 description "1576.04 nm/190.218750 THz 3.125/6.25GHz spacing";
               }
               enum "1576.01" {
                 description "1576.01 nm/190.221875 THz 3.125GHz spacing";
               }
               enum "1575.99" {
                 description "1575.99 nm/190.225000 THz 3.125/6.25/12.5GHz spacing";
               }
               enum "1575.96" {
                 description "1575.96 nm/190.228125 THz 3.125GHz spacing";
               }
               enum "1575.94" {
                 description "1575.94 nm/190.231250 THz 3.125/6.25GHz spacing";
               }
               enum "1575.91" {
                 description "1575.91 nm/190.234375 THz 3.125GHz spacing";
               }
               enum "1575.89" {
                 description "1575.89 nm/190.237500 THz 3.125/6.25/12.5GHz spacing";
               }
               enum "1575.86" {
                 description "1575.86 nm/190.240625 THz 3.125GHz spacing";
               }
               enum "1575.83" {
                 description "1575.83 nm/190.243750 THz 3.125/6.25GHz spacing";
               }
               enum "1575.81" {
                 description "1575.81 nm/190.246875 THz 3.125GHz spacing";
               }
               enum "1575.78" {
                 description "1575.78 nm/190.250000 THz 3.125/6.25/12.5/50/75GHz spacing";
               }
               enum "1575.76" {
                 description "1575.76 nm/190.253125 THz 3.125GHz spacing";
               }
               enum "1575.73" {
                 description "1575.73 nm/190.256250 THz 3.125/6.25GHz spacing";
               }
               enum "1575.70" {
                 description "1575.70 nm/190.259375 THz 3.125GHz spacing";
               }
               enum "1575.68" {
                 description "1575.68 nm/190.262500 THz 3.125/6.25/12.5GHz spacing";
               }
               enum "1575.65" {
                 description "1575.65 nm/190.265625 THz 3.125GHz spacing";
               }
               enum "1575.63" {
                 description "1575.63 nm/190.268750 THz 3.125/6.25GHz spacing";
               }
               enum "1575.60" {
                 description "1575.60 nm/190.271875 THz 3.125GHz spacing";
               }
               enum "1575.57" {
                 description "1575.57 nm/190.275000 THz 3.125/6.25/12.5GHz spacing";
               }
               enum "1575.55" {
                 description "1575.55 nm/190.278125 THz 3.125GHz spacing";
               }
               enum "1575.52" {
                 description "1575.52 nm/190.281250 THz 3.125/6.25GHz spacing";
               }
               enum "1575.50" {
                 description "1575.50 nm/190.284375 THz 3.125GHz spacing";
               }
               enum "1575.47" {
                 description "1575.47 nm/190.287500 THz 3.125/6.25/12.5GHz spacing";
               }
               enum "1575.45" {
                 description "1575.45 nm/190.290625 THz 3.125GHz spacing";
               }
               enum "1575.42" {
                 description "1575.42 nm/190.293750 THz 3.125/6.25GHz spacing";
               }
               enum "1575.39" {
                 description "1575.39 nm/190.296875 THz 3.125GHz spacing";
               }
               enum "1575.37" {
                 description "1575.37 nm/190.300000 THz 3.125/6.25/12.5/100GHz spacing";
               }
               enum "1575.34" {
                 description "1575.34 nm/190.303125 THz 3.125GHz spacing";
               }
               enum "1575.32" {
                 description "1575.32 nm/190.306250 THz 3.125/6.25GHz spacing";
               }
               enum "1575.29" {
                 description "1575.29 nm/190.309375 THz 3.125GHz spacing";
               }
               enum "1575.26" {
                 description "1575.26 nm/190.312500 THz 3.125/6.25/12.5GHz spacing";
               }
               enum "1575.24" {
                 description "1575.24 nm/190.315625 THz 3.125GHz spacing";
               }
               enum "1575.21" {
                 description "1575.21 nm/190.318750 THz 3.125/6.25GHz spacing";
               }
               enum "1575.19" {
                 description "1575.19 nm/190.321875 THz 3.125GHz spacing";
               }
               enum "1575.16" {
                 description "1575.16 nm/190.325000 THz 3.125/6.25/12.5/75GHz spacing";
               }
               enum "1575.13" {
                 description "1575.13 nm/190.328125 THz 3.125GHz spacing";
               }
               enum "1575.11" {
                 description "1575.11 nm/190.331250 THz 3.125/6.25GHz spacing";
               }
               enum "1575.08" {
                 description "1575.08 nm/190.334375 THz 3.125GHz spacing";
               }
               enum "1575.06" {
                 description "1575.06 nm/190.337500 THz 3.125/6.25/12.5GHz spacing";
               }
               enum "1575.03" {
                 description "1575.03 nm/190.340625 THz 3.125GHz spacing";
               }
               enum "1575.01" {
                 description "1575.01 nm/190.343750 THz 3.125/6.25GHz spacing";
               }
               enum "1574.98" {
                 description "1574.98 nm/190.346875 THz 3.125GHz spacing";
               }
               enum "1574.95" {
                 description "1574.95 nm/190.350000 THz 3.125/6.25/12.5/50GHz spacing";
               }
               enum "1574.93" {
                 description "1574.93 nm/190.353125 THz 3.125GHz spacing";
               }
               enum "1574.90" {
                 description "1574.90 nm/190.356250 THz 3.125/6.25GHz spacing";
               }
               enum "1574.88" {
                 description "1574.88 nm/190.359375 THz 3.125GHz spacing";
               }
               enum "1574.85" {
                 description "1574.85 nm/190.362500 THz 3.125/6.25/12.5GHz spacing";
               }
               enum "1574.82" {
                 description "1574.82 nm/190.365625 THz 3.125GHz spacing";
               }
               enum "1574.80" {
                 description "1574.80 nm/190.368750 THz 3.125/6.25GHz spacing";
               }
               enum "1574.77" {
                 description "1574.77 nm/190.371875 THz 3.125GHz spacing";
               }
               enum "1574.75" {
                 description "1574.75 nm/190.375000 THz 3.125/6.25/12.5GHz spacing";
               }
               enum "1574.72" {
                 description "1574.72 nm/190.378125 THz 3.125GHz spacing";
               }
               enum "1574.70" {
                 description "1574.70 nm/190.381250 THz 3.125/6.25GHz spacing";
               }
               enum "1574.67" {
                 description "1574.67 nm/190.384375 THz 3.125GHz spacing";
               }
               enum "1574.64" {
                 description "1574.64 nm/190.387500 THz 3.125/6.25/12.5GHz spacing";
               }
               enum "1574.62" {
                 description "1574.62 nm/190.390625 THz 3.125GHz spacing";
               }
               enum "1574.59" {
                 description "1574.59 nm/190.393750 THz 3.125/6.25GHz spacing";
               }
               enum "1574.57" {
                 description "1574.57 nm/190.396875 THz 3.125GHz spacing";
               }
               enum "1574.54" {
                 description "1574.54 nm/190.400000 THz 3.125/6.25/12.5/100GHz spacing";
               }
               enum "1574.51" {
                 description "1574.51 nm/190.403125 THz 3.125GHz spacing";
               }
               enum "1574.49" {
                 description "1574.49 nm/190.406250 THz 3.125/6.25GHz spacing";
               }
               enum "1574.46" {
                 description "1574.46 nm/190.409375 THz 3.125GHz spacing";
               }
               enum "1574.44" {
                 description "1574.44 nm/190.412500 THz 3.125/6.25/12.5GHz spacing";
               }
               enum "1574.41" {
                 description "1574.41 nm/190.415625 THz 3.125GHz spacing";
               }
               enum "1574.39" {
                 description "1574.39 nm/190.418750 THz 3.125/6.25GHz spacing";
               }
               enum "1574.36" {
                 description "1574.36 nm/190.421875 THz 3.125GHz spacing";
               }
               enum "1574.33" {
                 description "1574.33 nm/190.425000 THz 3.125/6.25/12.5GHz spacing";
               }
               enum "1574.31" {
                 description "1574.31 nm/190.428125 THz 3.125GHz spacing";
               }
               enum "1574.28" {
                 description "1574.28 nm/190.431250 THz 3.125/6.25GHz spacing";
               }
               enum "1574.26" {
                 description "1574.26 nm/190.434375 THz 3.125GHz spacing";
               }
               enum "1574.23" {
                 description "1574.23 nm/190.437500 THz 3.125/6.25/12.5GHz spacing";
               }
               enum "1574.20" {
                 description "1574.20 nm/190.440625 THz 3.125GHz spacing";
               }
               enum "1574.18" {
                 description "1574.18 nm/190.443750 THz 3.125/6.25GHz spacing";
               }
               enum "1574.15" {
                 description "1574.15 nm/190.446875 THz 3.125GHz spacing";
               }
               enum "1574.13" {
                 description "1574.13 nm/190.450000 THz 3.125/6.25/12.5/50GHz spacing";
               }
               enum "1574.10" {
                 description "1574.10 nm/190.453125 THz 3.125GHz spacing";
               }
               enum "1574.08" {
                 description "1574.08 nm/190.456250 THz 3.125/6.25GHz spacing";
               }
               enum "1574.05" {
                 description "1574.05 nm/190.459375 THz 3.125GHz spacing";
               }
               enum "1574.02" {
                 description "1574.02 nm/190.462500 THz 3.125/6.25/12.5GHz spacing";
               }
               enum "1574.00" {
                 description "1574.00 nm/190.465625 THz 3.125GHz spacing";
               }
               enum "1573.97" {
                 description "1573.97 nm/190.468750 THz 3.125/6.25GHz spacing";
               }
               enum "1573.95" {
                 description "1573.95 nm/190.471875 THz 3.125GHz spacing";
               }
               enum "1573.92" {
                 description "1573.92 nm/190.475000 THz 3.125/6.25/12.5/75GHz spacing";
               }
               enum "1573.89" {
                 description "1573.89 nm/190.478125 THz 3.125GHz spacing";
               }
               enum "1573.87" {
                 description "1573.87 nm/190.481250 THz 3.125/6.25GHz spacing";
               }
               enum "1573.84" {
                 description "1573.84 nm/190.484375 THz 3.125GHz spacing";
               }
               enum "1573.82" {
                 description "1573.82 nm/190.487500 THz 3.125/6.25/12.5GHz spacing";
               }
               enum "1573.79" {
                 description "1573.79 nm/190.490625 THz 3.125GHz spacing";
               }
               enum "1573.77" {
                 description "1573.77 nm/190.493750 THz 3.125/6.25GHz spacing";
               }
               enum "1573.74" {
                 description "1573.74 nm/190.496875 THz 3.125GHz spacing";
               }
               enum "1573.71" {
                 description "1573.71 nm/190.500000 THz 3.125/6.25/12.5/50/75/100GHz spacing";
               }
               enum "1573.69" {
                 description "1573.69 nm/190.503125 THz 3.125GHz spacing";
               }
               enum "1573.66" {
                 description "1573.66 nm/190.506250 THz 3.125/6.25GHz spacing";
               }
               enum "1573.64" {
                 description "1573.64 nm/190.509375 THz 3.125GHz spacing";
               }
               enum "1573.61" {
                 description "1573.61 nm/190.512500 THz 3.125/6.25/12.5GHz spacing";
               }
               enum "1573.58" {
                 description "1573.58 nm/190.515625 THz 3.125GHz spacing";
               }
               enum "1573.56" {
                 description "1573.56 nm/190.518750 THz 3.125/6.25GHz spacing";
               }
               enum "1573.53" {
                 description "1573.53 nm/190.521875 THz 3.125GHz spacing";
               }
               enum "1573.51" {
                 description "1573.51 nm/190.525000 THz 3.125/6.25/12.5GHz spacing";
               }
               enum "1573.48" {
                 description "1573.48 nm/190.528125 THz 3.125GHz spacing";
               }
               enum "1573.46" {
                 description "1573.46 nm/190.531250 THz 3.125/6.25GHz spacing";
               }
               enum "1573.43" {
                 description "1573.43 nm/190.534375 THz 3.125GHz spacing";
               }
               enum "1573.40" {
                 description "1573.40 nm/190.537500 THz 3.125/6.25/12.5GHz spacing";
               }
               enum "1573.38" {
                 description "1573.38 nm/190.540625 THz 3.125GHz spacing";
               }
               enum "1573.35" {
                 description "1573.35 nm/190.543750 THz 3.125/6.25GHz spacing";
               }
               enum "1573.33" {
                 description "1573.33 nm/190.546875 THz 3.125GHz spacing";
               }
               enum "1573.30" {
                 description "1573.30 nm/190.550000 THz 3.125/6.25/12.5/50/75GHz spacing";
               }
               enum "1573.27" {
                 description "1573.27 nm/190.553125 THz 3.125GHz spacing";
               }
               enum "1573.25" {
                 description "1573.25 nm/190.556250 THz 3.125/6.25GHz spacing";
               }
               enum "1573.22" {
                 description "1573.22 nm/190.559375 THz 3.125GHz spacing";
               }
               enum "1573.20" {
                 description "1573.20 nm/190.562500 THz 3.125/6.25/12.5GHz spacing";
               }
               enum "1573.17" {
                 description "1573.17 nm/190.565625 THz 3.125GHz spacing";
               }
               enum "1573.15" {
                 description "1573.15 nm/190.568750 THz 3.125/6.25GHz spacing";
               }
               enum "1573.12" {
                 description "1573.12 nm/190.571875 THz 3.125GHz spacing";
               }
               enum "1573.09" {
                 description "1573.09 nm/190.575000 THz 3.125/6.25/12.5GHz spacing";
               }
               enum "1573.07" {
                 description "1573.07 nm/190.578125 THz 3.125GHz spacing";
               }
               enum "1573.04" {
                 description "1573.04 nm/190.581250 THz 3.125/6.25GHz spacing";
               }
               enum "1573.02" {
                 description "1573.02 nm/190.584375 THz 3.125GHz spacing";
               }
               enum "1572.99" {
                 description "1572.99 nm/190.587500 THz 3.125/6.25/12.5GHz spacing";
               }
               enum "1572.97" {
                 description "1572.97 nm/190.590625 THz 3.125GHz spacing";
               }
               enum "1572.94" {
                 description "1572.94 nm/190.593750 THz 3.125/6.25GHz spacing";
               }
               enum "1572.91" {
                 description "1572.91 nm/190.596875 THz 3.125GHz spacing";
               }
               enum "1572.89" {
                 description "1572.89 nm/190.600000 THz 3.125/6.25/12.5/100GHz spacing";
               }
               enum "1572.86" {
                 description "1572.86 nm/190.603125 THz 3.125GHz spacing";
               }
               enum "1572.84" {
                 description "1572.84 nm/190.606250 THz 3.125/6.25GHz spacing";
               }
               enum "1572.81" {
                 description "1572.81 nm/190.609375 THz 3.125GHz spacing";
               }
               enum "1572.78" {
                 description "1572.78 nm/190.612500 THz 3.125/6.25/12.5GHz spacing";
               }
               enum "1572.76" {
                 description "1572.76 nm/190.615625 THz 3.125GHz spacing";
               }
               enum "1572.73" {
                 description "1572.73 nm/190.618750 THz 3.125/6.25GHz spacing";
               }
               enum "1572.71" {
                 description "1572.71 nm/190.621875 THz 3.125GHz spacing";
               }
               enum "1572.68" {
                 description "1572.68 nm/190.625000 THz 3.125/6.25/12.5/75GHz spacing";
               }
               enum "1572.66" {
                 description "1572.66 nm/190.628125 THz 3.125GHz spacing";
               }
               enum "1572.63" {
                 description "1572.63 nm/190.631250 THz 3.125/6.25GHz spacing";
               }
               enum "1572.60" {
                 description "1572.60 nm/190.634375 THz 3.125GHz spacing";
               }
               enum "1572.58" {
                 description "1572.58 nm/190.637500 THz 3.125/6.25/12.5GHz spacing";
               }
               enum "1572.55" {
                 description "1572.55 nm/190.640625 THz 3.125GHz spacing";
               }
               enum "1572.53" {
                 description "1572.53 nm/190.643750 THz 3.125/6.25GHz spacing";
               }
               enum "1572.50" {
                 description "1572.50 nm/190.646875 THz 3.125GHz spacing";
               }
               enum "1572.48" {
                 description "1572.48 nm/190.650000 THz 3.125/6.25/12.5/50GHz spacing";
               }
               enum "1572.45" {
                 description "1572.45 nm/190.653125 THz 3.125GHz spacing";
               }
               enum "1572.42" {
                 description "1572.42 nm/190.656250 THz 3.125/6.25GHz spacing";
               }
               enum "1572.40" {
                 description "1572.40 nm/190.659375 THz 3.125GHz spacing";
               }
               enum "1572.37" {
                 description "1572.37 nm/190.662500 THz 3.125/6.25/12.5GHz spacing";
               }
               enum "1572.35" {
                 description "1572.35 nm/190.665625 THz 3.125GHz spacing";
               }
               enum "1572.32" {
                 description "1572.32 nm/190.668750 THz 3.125/6.25GHz spacing";
               }
               enum "1572.30" {
                 description "1572.30 nm/190.671875 THz 3.125GHz spacing";
               }
               enum "1572.27" {
                 description "1572.27 nm/190.675000 THz 3.125/6.25/12.5GHz spacing";
               }
               enum "1572.24" {
                 description "1572.24 nm/190.678125 THz 3.125GHz spacing";
               }
               enum "1572.22" {
                 description "1572.22 nm/190.681250 THz 3.125/6.25GHz spacing";
               }
               enum "1572.19" {
                 description "1572.19 nm/190.684375 THz 3.125GHz spacing";
               }
               enum "1572.17" {
                 description "1572.17 nm/190.687500 THz 3.125/6.25/12.5GHz spacing";
               }
               enum "1572.14" {
                 description "1572.14 nm/190.690625 THz 3.125GHz spacing";
               }
               enum "1572.11" {
                 description "1572.11 nm/190.693750 THz 3.125/6.25GHz spacing";
               }
               enum "1572.09" {
                 description "1572.09 nm/190.696875 THz 3.125GHz spacing";
               }
               enum "1572.06" {
                 description "1572.06 nm/190.700000 THz 3.125/6.25/12.5/100GHz spacing";
               }
               enum "1572.04" {
                 description "1572.04 nm/190.703125 THz 3.125GHz spacing";
               }
               enum "1572.01" {
                 description "1572.01 nm/190.706250 THz 3.125/6.25GHz spacing";
               }
               enum "1571.99" {
                 description "1571.99 nm/190.709375 THz 3.125GHz spacing";
               }
               enum "1571.96" {
                 description "1571.96 nm/190.712500 THz 3.125/6.25/12.5GHz spacing";
               }
               enum "1571.93" {
                 description "1571.93 nm/190.715625 THz 3.125GHz spacing";
               }
               enum "1571.91" {
                 description "1571.91 nm/190.718750 THz 3.125/6.25GHz spacing";
               }
               enum "1571.88" {
                 description "1571.88 nm/190.721875 THz 3.125GHz spacing";
               }
               enum "1571.86" {
                 description "1571.86 nm/190.725000 THz 3.125/6.25/12.5GHz spacing";
               }
               enum "1571.83" {
                 description "1571.83 nm/190.728125 THz 3.125GHz spacing";
               }
               enum "1571.81" {
                 description "1571.81 nm/190.731250 THz 3.125/6.25GHz spacing";
               }
               enum "1571.78" {
                 description "1571.78 nm/190.734375 THz 3.125GHz spacing";
               }
               enum "1571.75" {
                 description "1571.75 nm/190.737500 THz 3.125/6.25/12.5GHz spacing";
               }
               enum "1571.73" {
                 description "1571.73 nm/190.740625 THz 3.125GHz spacing";
               }
               enum "1571.70" {
                 description "1571.70 nm/190.743750 THz 3.125/6.25GHz spacing";
               }
               enum "1571.68" {
                 description "1571.68 nm/190.746875 THz 3.125GHz spacing";
               }
               enum "1571.65" {
                 description "1571.65 nm/190.750000 THz 3.125/6.25/12.5/50GHz spacing";
               }
               enum "1571.63" {
                 description "1571.63 nm/190.753125 THz 3.125GHz spacing";
               }
               enum "1571.60" {
                 description "1571.60 nm/190.756250 THz 3.125/6.25GHz spacing";
               }
               enum "1571.57" {
                 description "1571.57 nm/190.759375 THz 3.125GHz spacing";
               }
               enum "1571.55" {
                 description "1571.55 nm/190.762500 THz 3.125/6.25/12.5GHz spacing";
               }
               enum "1571.52" {
                 description "1571.52 nm/190.765625 THz 3.125GHz spacing";
               }
               enum "1571.50" {
                 description "1571.50 nm/190.768750 THz 3.125/6.25GHz spacing";
               }
               enum "1571.47" {
                 description "1571.47 nm/190.771875 THz 3.125GHz spacing";
               }
               enum "1571.45" {
                 description "1571.45 nm/190.775000 THz 3.125/6.25/12.5/75GHz spacing";
               }
               enum "1571.42" {
                 description "1571.42 nm/190.778125 THz 3.125GHz spacing";
               }
               enum "1571.39" {
                 description "1571.39 nm/190.781250 THz 3.125/6.25GHz spacing";
               }
               enum "1571.37" {
                 description "1571.37 nm/190.784375 THz 3.125GHz spacing";
               }
               enum "1571.34" {
                 description "1571.34 nm/190.787500 THz 3.125/6.25/12.5GHz spacing";
               }
               enum "1571.32" {
                 description "1571.32 nm/190.790625 THz 3.125GHz spacing";
               }
               enum "1571.29" {
                 description "1571.29 nm/190.793750 THz 3.125/6.25GHz spacing";
               }
               enum "1571.27" {
                 description "1571.27 nm/190.796875 THz 3.125GHz spacing";
               }
               enum "1571.24" {
                 description "1571.24 nm/190.800000 THz 3.125/6.25/12.5/50/75/100GHz spacing";
               }
               enum "1571.21" {
                 description "1571.21 nm/190.803125 THz 3.125GHz spacing";
               }
               enum "1571.19" {
                 description "1571.19 nm/190.806250 THz 3.125/6.25GHz spacing";
               }
               enum "1571.16" {
                 description "1571.16 nm/190.809375 THz 3.125GHz spacing";
               }
               enum "1571.14" {
                 description "1571.14 nm/190.812500 THz 3.125/6.25/12.5GHz spacing";
               }
               enum "1571.11" {
                 description "1571.11 nm/190.815625 THz 3.125GHz spacing";
               }
               enum "1571.08" {
                 description "1571.08 nm/190.818750 THz 3.125/6.25GHz spacing";
               }
               enum "1571.06" {
                 description "1571.06 nm/190.821875 THz 3.125GHz spacing";
               }
               enum "1571.03" {
                 description "1571.03 nm/190.825000 THz 3.125/6.25/12.5GHz spacing";
               }
               enum "1571.01" {
                 description "1571.01 nm/190.828125 THz 3.125GHz spacing";
               }
               enum "1570.98" {
                 description "1570.98 nm/190.831250 THz 3.125/6.25GHz spacing";
               }
               enum "1570.96" {
                 description "1570.96 nm/190.834375 THz 3.125GHz spacing";
               }
               enum "1570.93" {
                 description "1570.93 nm/190.837500 THz 3.125/6.25/12.5GHz spacing";
               }
               enum "1570.90" {
                 description "1570.90 nm/190.840625 THz 3.125GHz spacing";
               }
               enum "1570.88" {
                 description "1570.88 nm/190.843750 THz 3.125/6.25GHz spacing";
               }
               enum "1570.85" {
                 description "1570.85 nm/190.846875 THz 3.125GHz spacing";
               }
               enum "1570.83" {
                 description "1570.83 nm/190.850000 THz 3.125/6.25/12.5/50/75GHz spacing";
               }
               enum "1570.80" {
                 description "1570.80 nm/190.853125 THz 3.125GHz spacing";
               }
               enum "1570.78" {
                 description "1570.78 nm/190.856250 THz 3.125/6.25GHz spacing";
               }
               enum "1570.75" {
                 description "1570.75 nm/190.859375 THz 3.125GHz spacing";
               }
               enum "1570.72" {
                 description "1570.72 nm/190.862500 THz 3.125/6.25/12.5GHz spacing";
               }
               enum "1570.70" {
                 description "1570.70 nm/190.865625 THz 3.125GHz spacing";
               }
               enum "1570.67" {
                 description "1570.67 nm/190.868750 THz 3.125/6.25GHz spacing";
               }
               enum "1570.65" {
                 description "1570.65 nm/190.871875 THz 3.125GHz spacing";
               }
               enum "1570.62" {
                 description "1570.62 nm/190.875000 THz 3.125/6.25/12.5GHz spacing";
               }
               enum "1570.60" {
                 description "1570.60 nm/190.878125 THz 3.125GHz spacing";
               }
               enum "1570.57" {
                 description "1570.57 nm/190.881250 THz 3.125/6.25GHz spacing";
               }
               enum "1570.54" {
                 description "1570.54 nm/190.884375 THz 3.125GHz spacing";
               }
               enum "1570.52" {
                 description "1570.52 nm/190.887500 THz 3.125/6.25/12.5GHz spacing";
               }
               enum "1570.49" {
                 description "1570.49 nm/190.890625 THz 3.125GHz spacing";
               }
               enum "1570.47" {
                 description "1570.47 nm/190.893750 THz 3.125/6.25GHz spacing";
               }
               enum "1570.44" {
                 description "1570.44 nm/190.896875 THz 3.125GHz spacing";
               }
               enum "1570.42" {
                 description "1570.42 nm/190.900000 THz 3.125/6.25/12.5/100GHz spacing";
               }
               enum "1570.39" {
                 description "1570.39 nm/190.903125 THz 3.125GHz spacing";
               }
               enum "1570.36" {
                 description "1570.36 nm/190.906250 THz 3.125/6.25GHz spacing";
               }
               enum "1570.34" {
                 description "1570.34 nm/190.909375 THz 3.125GHz spacing";
               }
               enum "1570.31" {
                 description "1570.31 nm/190.912500 THz 3.125/6.25/12.5GHz spacing";
               }
               enum "1570.29" {
                 description "1570.29 nm/190.915625 THz 3.125GHz spacing";
               }
               enum "1570.26" {
                 description "1570.26 nm/190.918750 THz 3.125/6.25GHz spacing";
               }
               enum "1570.24" {
                 description "1570.24 nm/190.921875 THz 3.125GHz spacing";
               }
               enum "1570.21" {
                 description "1570.21 nm/190.925000 THz 3.125/6.25/12.5/75GHz spacing";
               }
               enum "1570.18" {
                 description "1570.18 nm/190.928125 THz 3.125GHz spacing";
               }
               enum "1570.16" {
                 description "1570.16 nm/190.931250 THz 3.125/6.25GHz spacing";
               }
               enum "1570.13" {
                 description "1570.13 nm/190.934375 THz 3.125GHz spacing";
               }
               enum "1570.11" {
                 description "1570.11 nm/190.937500 THz 3.125/6.25/12.5GHz spacing";
               }
               enum "1570.08" {
                 description "1570.08 nm/190.940625 THz 3.125GHz spacing";
               }
               enum "1570.06" {
                 description "1570.06 nm/190.943750 THz 3.125/6.25GHz spacing";
               }
               enum "1570.03" {
                 description "1570.03 nm/190.946875 THz 3.125GHz spacing";
               }
               enum "1570.01" {
                 description "1570.01 nm/190.950000 THz 3.125/6.25/12.5/50GHz spacing";
               }
               enum "1569.98" {
                 description "1569.98 nm/190.953125 THz 3.125GHz spacing";
               }
               enum "1569.95" {
                 description "1569.95 nm/190.956250 THz 3.125/6.25GHz spacing";
               }
               enum "1569.93" {
                 description "1569.93 nm/190.959375 THz 3.125GHz spacing";
               }
               enum "1569.90" {
                 description "1569.90 nm/190.962500 THz 3.125/6.25/12.5GHz spacing";
               }
               enum "1569.88" {
                 description "1569.88 nm/190.965625 THz 3.125GHz spacing";
               }
               enum "1569.85" {
                 description "1569.85 nm/190.968750 THz 3.125/6.25GHz spacing";
               }
               enum "1569.83" {
                 description "1569.83 nm/190.971875 THz 3.125GHz spacing";
               }
               enum "1569.80" {
                 description "1569.80 nm/190.975000 THz 3.125/6.25/12.5GHz spacing";
               }
               enum "1569.77" {
                 description "1569.77 nm/190.978125 THz 3.125GHz spacing";
               }
               enum "1569.75" {
                 description "1569.75 nm/190.981250 THz 3.125/6.25GHz spacing";
               }
               enum "1569.72" {
                 description "1569.72 nm/190.984375 THz 3.125GHz spacing";
               }
               enum "1569.70" {
                 description "1569.70 nm/190.987500 THz 3.125/6.25/12.5GHz spacing";
               }
               enum "1569.67" {
                 description "1569.67 nm/190.990625 THz 3.125GHz spacing";
               }
               enum "1569.65" {
                 description "1569.65 nm/190.993750 THz 3.125/6.25GHz spacing";
               }
               enum "1569.62" {
                 description "1569.62 nm/190.996875 THz 3.125GHz spacing";
               }
               enum "1569.59" {
                 description "1569.59 nm/191.000000 THz 3.125/6.25/12.5/100GHz spacing";
               }
               enum "1568.77" {
                 description "1568.77 nm/191.1003 THz 50/100Ghz spacing";
               }
               enum "1568.36" {
                 description "1568.36 nm/191.150000 THz 3.125/6.25/12.5/50/75GHz spacing";
               }
               enum "1568.34" {
                 description "1568.34 nm/191.153125 THz 3.125GHz spacing";
               }
               enum "1568.31" {
                 description "1568.31 nm/191.156250 THz 3.125/6.25GHz spacing";
               }
               enum "1568.29" {
                 description "1568.29 nm/191.159375 THz 3.125GHz spacing";
               }
               enum "1568.26" {
                 description "1568.26 nm/191.162500 THz 3.125/6.25/12.5GHz spacing";
               }
               enum "1568.23" {
                 description "1568.23 nm/191.165625 THz 3.125GHz spacing";
               }
               enum "1568.21" {
                 description "1568.21 nm/191.168750 THz 3.125/6.25GHz spacing";
               }
               enum "1568.18" {
                 description "1568.18 nm/191.171875 THz 3.125GHz spacing";
               }
               enum "1568.16" {
                 description "1568.16 nm/191.175000 THz 3.125/6.25/12.5/75GHz spacing";
               }
               enum "1568.13" {
                 description "1568.13 nm/191.178125 THz 3.125GHz spacing";
               }
               enum "1568.11" {
                 description "1568.11 nm/191.181250 THz 3.125/6.25GHz spacing";
               }
               enum "1568.08" {
                 description "1568.08 nm/191.184375 THz 3.125GHz spacing";
               }
               enum "1568.05" {
                 description "1568.05 nm/191.187500 THz 3.125/6.25/12.5GHz spacing";
               }
               enum "1568.03" {
                 description "1568.03 nm/191.190625 THz 3.125GHz spacing";
               }
               enum "1568.00" {
                 description "1568.00 nm/191.193750 THz 3.125/6.25GHz spacing";
               }
               enum "1567.98" {
                 description "1567.98 nm/191.196875 THz 3.125GHz spacing";
               }
               enum "1567.95" {
                 description "1567.95 nm/191.200000 THz 3.125/6.25/12.5/100GHz spacing";
               }
               enum "1567.93" {
                 description "1567.93 nm/191.203125 THz 3.125GHz spacing";
               }
               enum "1567.90" {
                 description "1567.90 nm/191.206250 THz 3.125/6.25GHz spacing";
               }
               enum "1567.88" {
                 description "1567.88 nm/191.209375 THz 3.125GHz spacing";
               }
               enum "1567.85" {
                 description "1567.85 nm/191.212500 THz 3.125/6.25/12.5GHz spacing";
               }
               enum "1567.82" {
                 description "1567.82 nm/191.215625 THz 3.125GHz spacing";
               }
               enum "1567.80" {
                 description "1567.80 nm/191.218750 THz 3.125/6.25GHz spacing";
               }
               enum "1567.77" {
                 description "1567.77 nm/191.221875 THz 3.125GHz spacing";
               }
               enum "1567.75" {
                 description "1567.75 nm/191.225000 THz 3.125/6.25/12.5/75GHz spacing";
               }
               enum "1567.72" {
                 description "1567.72 nm/191.228125 THz 3.125GHz spacing";
               }
               enum "1567.70" {
                 description "1567.70 nm/191.231250 THz 3.125/6.25GHz spacing";
               }
               enum "1567.67" {
                 description "1567.67 nm/191.234375 THz 3.125GHz spacing";
               }
               enum "1567.64" {
                 description "1567.64 nm/191.237500 THz 3.125/6.25/12.5GHz spacing";
               }
               enum "1567.62" {
                 description "1567.62 nm/191.240625 THz 3.125GHz spacing";
               }
               enum "1567.59" {
                 description "1567.59 nm/191.243750 THz 3.125/6.25GHz spacing";
               }
               enum "1567.57" {
                 description "1567.57 nm/191.246875 THz 3.125GHz spacing";
               }
               enum "1567.54" {
                 description "1567.54 nm/191.250000 THz 3.125/6.25/12.5/50/75GHz spacing";
               }
               enum "1567.52" {
                 description "1567.52 nm/191.253125 THz 3.125GHz spacing";
               }
               enum "1567.49" {
                 description "1567.49 nm/191.256250 THz 3.125/6.25GHz spacing";
               }
               enum "1567.47" {
                 description "1567.47 nm/191.259375 THz 3.125GHz spacing";
               }
               enum "1567.44" {
                 description "1567.44 nm/191.262500 THz 3.125/6.25/12.5GHz spacing";
               }
               enum "1567.41" {
                 description "1567.41 nm/191.265625 THz 3.125GHz spacing";
               }
               enum "1567.39" {
                 description "1567.39 nm/191.268750 THz 3.125/6.25GHz spacing";
               }
               enum "1567.36" {
                 description "1567.36 nm/191.271875 THz 3.125GHz spacing";
               }
               enum "1567.34" {
                 description "1567.34 nm/191.275000 THz 3.125/6.25/12.5GHz spacing";
               }
               enum "1567.31" {
                 description "1567.31 nm/191.278125 THz 3.125GHz spacing";
               }
               enum "1567.29" {
                 description "1567.29 nm/191.281250 THz 3.125/6.25GHz spacing";
               }
               enum "1567.26" {
                 description "1567.26 nm/191.284375 THz 3.125GHz spacing";
               }
               enum "1567.23" {
                 description "1567.23 nm/191.287500 THz 3.125/6.25/12.5GHz spacing";
               }
               enum "1567.21" {
                 description "1567.21 nm/191.290625 THz 3.125GHz spacing";
               }
               enum "1567.18" {
                 description "1567.18 nm/191.293750 THz 3.125/6.25GHz spacing";
               }
               enum "1567.16" {
                 description "1567.16 nm/191.296875 THz 3.125GHz spacing";
               }
               enum "1567.13" {
                 description "1567.13 nm/191.300000 THz 3.125/6.25/12.5/100GHz spacing";
               }
               enum "1567.11" {
                 description "1567.11 nm/191.303125 THz 3.125GHz spacing";
               }
               enum "1567.08" {
                 description "1567.08 nm/191.306250 THz 3.125/6.25GHz spacing";
               }
               enum "1567.06" {
                 description "1567.06 nm/191.309375 THz 3.125GHz spacing";
               }
               enum "1567.03" {
                 description "1567.03 nm/191.312500 THz 3.125/6.25/12.5GHz spacing";
               }
               enum "1567.00" {
                 description "1567.00 nm/191.315625 THz 3.125GHz spacing";
               }
               enum "1566.98" {
                 description "1566.98 nm/191.318750 THz 3.125/6.25GHz spacing";
               }
               enum "1566.95" {
                 description "1566.95 nm/191.321875 THz 3.125GHz spacing";
               }
               enum "1566.93" {
                 description "1566.93 nm/191.325000 THz 3.125/6.25/12.5/75GHz spacing";
               }
               enum "1566.90" {
                 description "1566.90 nm/191.328125 THz 3.125GHz spacing";
               }
               enum "1566.88" {
                 description "1566.88 nm/191.331250 THz 3.125/6.25GHz spacing";
               }
               enum "1566.85" {
                 description "1566.85 nm/191.334375 THz 3.125GHz spacing";
               }
               enum "1566.83" {
                 description "1566.83 nm/191.337500 THz 3.125/6.25/12.5GHz spacing";
               }
               enum "1566.80" {
                 description "1566.80 nm/191.340625 THz 3.125GHz spacing";
               }
               enum "1566.77" {
                 description "1566.77 nm/191.343750 THz 3.125/6.25GHz spacing";
               }
               enum "1566.75" {
                 description "1566.75 nm/191.346875 THz 3.125GHz spacing";
               }
               enum "1566.72" {
                 description "1566.72 nm/191.350000 THz 3.125/6.25/12.5/50GHz spacing";
               }
               enum "1566.70" {
                 description "1566.70 nm/191.353125 THz 3.125GHz spacing";
               }
               enum "1566.67" {
                 description "1566.67 nm/191.356250 THz 3.125/6.25GHz spacing";
               }
               enum "1566.65" {
                 description "1566.65 nm/191.359375 THz 3.125GHz spacing";
               }
               enum "1566.62" {
                 description "1566.62 nm/191.362500 THz 3.125/6.25/12.5GHz spacing";
               }
               enum "1566.60" {
                 description "1566.60 nm/191.365625 THz 3.125GHz spacing";
               }
               enum "1566.57" {
                 description "1566.57 nm/191.368750 THz 3.125/6.25GHz spacing";
               }
               enum "1566.54" {
                 description "1566.54 nm/191.371875 THz 3.125GHz spacing";
               }
               enum "1566.52" {
                 description "1566.52 nm/191.375000 THz 3.125/6.25/12.5GHz spacing";
               }
               enum "1566.49" {
                 description "1566.49 nm/191.378125 THz 3.125GHz spacing";
               }
               enum "1566.47" {
                 description "1566.47 nm/191.381250 THz 3.125/6.25GHz spacing";
               }
               enum "1566.44" {
                 description "1566.44 nm/191.384375 THz 3.125GHz spacing";
               }
               enum "1566.42" {
                 description "1566.42 nm/191.387500 THz 3.125/6.25/12.5GHz spacing";
               }
               enum "1566.39" {
                 description "1566.39 nm/191.390625 THz 3.125GHz spacing";
               }
               enum "1566.36" {
                 description "1566.36 nm/191.393750 THz 3.125/6.25GHz spacing";
               }
               enum "1566.34" {
                 description "1566.34 nm/191.396875 THz 3.125GHz spacing";
               }
               enum "1566.31" {
                 description "1566.31 nm/191.400000 THz 3.125/6.25/12.5/50/75/100GHz spacing";
               }
               enum "1566.29" {
                 description "1566.29 nm/191.403125 THz 3.125GHz spacing";
               }
               enum "1566.26" {
                 description "1566.26 nm/191.406250 THz 3.125/6.25GHz spacing";
               }
               enum "1566.24" {
                 description "1566.24 nm/191.409375 THz 3.125GHz spacing";
               }
               enum "1566.21" {
                 description "1566.21 nm/191.412500 THz 3.125/6.25/12.5GHz spacing";
               }
               enum "1566.19" {
                 description "1566.19 nm/191.415625 THz 3.125GHz spacing";
               }
               enum "1566.16" {
                 description "1566.16 nm/191.418750 THz 3.125/6.25GHz spacing";
               }
               enum "1566.13" {
                 description "1566.13 nm/191.421875 THz 3.125GHz spacing";
               }
               enum "1566.11" {
                 description "1566.11 nm/191.425000 THz 3.125/6.25/12.5GHz spacing";
               }
               enum "1566.08" {
                 description "1566.08 nm/191.428125 THz 3.125GHz spacing";
               }
               enum "1566.06" {
                 description "1566.06 nm/191.431250 THz 3.125/6.25GHz spacing";
               }
               enum "1566.03" {
                 description "1566.03 nm/191.434375 THz 3.125GHz spacing";
               }
               enum "1566.01" {
                 description "1566.01 nm/191.437500 THz 3.125/6.25/12.5GHz spacing";
               }
               enum "1565.98" {
                 description "1565.98 nm/191.440625 THz 3.125GHz spacing";
               }
               enum "1565.96" {
                 description "1565.96 nm/191.443750 THz 3.125/6.25GHz spacing";
               }
               enum "1565.93" {
                 description "1565.93 nm/191.446875 THz 3.125GHz spacing";
               }
               enum "1565.90" {
                 description "1565.90 nm/191.450000 THz 3.125/6.25/12.5/50GHz spacing";
               }
               enum "1565.88" {
                 description "1565.88 nm/191.453125 THz 3.125GHz spacing";
               }
               enum "1565.85" {
                 description "1565.85 nm/191.456250 THz 3.125/6.25GHz spacing";
               }
               enum "1565.83" {
                 description "1565.83 nm/191.459375 THz 3.125GHz spacing";
               }
               enum "1565.80" {
                 description "1565.80 nm/191.462500 THz 3.125/6.25/12.5GHz spacing";
               }
               enum "1565.78" {
                 description "1565.78 nm/191.465625 THz 3.125GHz spacing";
               }
               enum "1565.75" {
                 description "1565.75 nm/191.468750 THz 3.125/6.25GHz spacing";
               }
               enum "1565.73" {
                 description "1565.73 nm/191.471875 THz 3.125GHz spacing";
               }
               enum "1565.70" {
                 description "1565.70 nm/191.475000 THz 3.125/6.25/12.5/75GHz spacing";
               }
               enum "1565.67" {
                 description "1565.67 nm/191.478125 THz 3.125GHz spacing";
               }
               enum "1565.65" {
                 description "1565.65 nm/191.481250 THz 3.125/6.25GHz spacing";
               }
               enum "1565.62" {
                 description "1565.62 nm/191.484375 THz 3.125GHz spacing";
               }
               enum "1565.60" {
                 description "1565.60 nm/191.487500 THz 3.125/6.25/12.5GHz spacing";
               }
               enum "1565.57" {
                 description "1565.57 nm/191.490625 THz 3.125GHz spacing";
               }
               enum "1565.55" {
                 description "1565.55 nm/191.493750 THz 3.125/6.25GHz spacing";
               }
               enum "1565.52" {
                 description "1565.52 nm/191.496875 THz 3.125GHz spacing";
               }
               enum "1565.50" {
                 description "1565.50 nm/191.500000 THz 3.125/6.25/12.5/100GHz spacing";
               }
               enum "1565.47" {
                 description "1565.47 nm/191.503125 THz 3.125GHz spacing";
               }
               enum "1565.44" {
                 description "1565.44 nm/191.506250 THz 3.125/6.25GHz spacing";
               }
               enum "1565.42" {
                 description "1565.42 nm/191.509375 THz 3.125GHz spacing";
               }
               enum "1565.39" {
                 description "1565.39 nm/191.512500 THz 3.125/6.25/12.5GHz spacing";
               }
               enum "1565.37" {
                 description "1565.37 nm/191.515625 THz 3.125GHz spacing";
               }
               enum "1565.34" {
                 description "1565.34 nm/191.518750 THz 3.125/6.25GHz spacing";
               }
               enum "1565.32" {
                 description "1565.32 nm/191.521875 THz 3.125GHz spacing";
               }
               enum "1565.29" {
                 description "1565.29 nm/191.525000 THz 3.125/6.25/12.5GHz spacing";
               }
               enum "1565.27" {
                 description "1565.27 nm/191.528125 THz 3.125GHz spacing";
               }
               enum "1565.24" {
                 description "1565.24 nm/191.531250 THz 3.125/6.25GHz spacing";
               }
               enum "1565.21" {
                 description "1565.21 nm/191.534375 THz 3.125GHz spacing";
               }
               enum "1565.19" {
                 description "1565.19 nm/191.537500 THz 3.125/6.25/12.5GHz spacing";
               }
               enum "1565.16" {
                 description "1565.16 nm/191.540625 THz 3.125GHz spacing";
               }
               enum "1565.14" {
                 description "1565.14 nm/191.543750 THz 3.125/6.25GHz spacing";
               }
               enum "1565.11" {
                 description "1565.11 nm/191.546875 THz 3.125GHz spacing";
               }
               enum "1565.09" {
                 description "1565.09 nm/191.550000 THz 3.125/6.25/12.5/50/75GHz spacing";
               }
               enum "1565.06" {
                 description "1565.06 nm/191.553125 THz 3.125GHz spacing";
               }
               enum "1565.04" {
                 description "1565.04 nm/191.556250 THz 3.125/6.25GHz spacing";
               }
               enum "1565.01" {
                 description "1565.01 nm/191.559375 THz 3.125GHz spacing";
               }
               enum "1564.99" {
                 description "1564.99 nm/191.562500 THz 3.125/6.25/12.5GHz spacing";
               }
               enum "1564.96" {
                 description "1564.96 nm/191.565625 THz 3.125GHz spacing";
               }
               enum "1564.93" {
                 description "1564.93 nm/191.568750 THz 3.125/6.25GHz spacing";
               }
               enum "1564.91" {
                 description "1564.91 nm/191.571875 THz 3.125GHz spacing";
               }
               enum "1564.88" {
                 description "1564.88 nm/191.575000 THz 3.125/6.25/12.5GHz spacing";
               }
               enum "1564.86" {
                 description "1564.86 nm/191.578125 THz 3.125GHz spacing";
               }
               enum "1564.83" {
                 description "1564.83 nm/191.581250 THz 3.125/6.25GHz spacing";
               }
               enum "1564.81" {
                 description "1564.81 nm/191.584375 THz 3.125GHz spacing";
               }
               enum "1564.78" {
                 description "1564.78 nm/191.587500 THz 3.125/6.25/12.5GHz spacing";
               }
               enum "1564.76" {
                 description "1564.76 nm/191.590625 THz 3.125GHz spacing";
               }
               enum "1564.73" {
                 description "1564.73 nm/191.593750 THz 3.125/6.25GHz spacing";
               }
               enum "1564.70" {
                 description "1564.70 nm/191.596875 THz 3.125GHz spacing";
               }
               enum "1564.68" {
                 description "1564.68 nm/191.600000 THz 3.125/6.25/12.5/100GHz spacing";
               }
               enum "1564.65" {
                 description "1564.65 nm/191.603125 THz 3.125GHz spacing";
               }
               enum "1564.63" {
                 description "1564.63 nm/191.606250 THz 3.125/6.25GHz spacing";
               }
               enum "1564.60" {
                 description "1564.60 nm/191.609375 THz 3.125GHz spacing";
               }
               enum "1564.58" {
                 description "1564.58 nm/191.612500 THz 3.125/6.25/12.5GHz spacing";
               }
               enum "1564.55" {
                 description "1564.55 nm/191.615625 THz 3.125GHz spacing";
               }
               enum "1564.53" {
                 description "1564.53 nm/191.618750 THz 3.125/6.25GHz spacing";
               }
               enum "1564.50" {
                 description "1564.50 nm/191.621875 THz 3.125GHz spacing";
               }
               enum "1564.47" {
                 description "1564.47 nm/191.625000 THz 3.125/6.25/12.5/75GHz spacing";
               }
               enum "1564.45" {
                 description "1564.45 nm/191.628125 THz 3.125GHz spacing";
               }
               enum "1564.42" {
                 description "1564.42 nm/191.631250 THz 3.125/6.25GHz spacing";
               }
               enum "1564.40" {
                 description "1564.40 nm/191.634375 THz 3.125GHz spacing";
               }
               enum "1564.37" {
                 description "1564.37 nm/191.637500 THz 3.125/6.25/12.5GHz spacing";
               }
               enum "1564.35" {
                 description "1564.35 nm/191.640625 THz 3.125GHz spacing";
               }
               enum "1564.32" {
                 description "1564.32 nm/191.643750 THz 3.125/6.25GHz spacing";
               }
               enum "1564.30" {
                 description "1564.30 nm/191.646875 THz 3.125GHz spacing";
               }
               enum "1564.27" {
                 description "1564.27 nm/191.650000 THz 3.125/6.25/12.5/50GHz spacing";
               }
               enum "1564.25" {
                 description "1564.25 nm/191.653125 THz 3.125GHz spacing";
               }
               enum "1564.22" {
                 description "1564.22 nm/191.656250 THz 3.125/6.25GHz spacing";
               }
               enum "1564.19" {
                 description "1564.19 nm/191.659375 THz 3.125GHz spacing";
               }
               enum "1564.17" {
                 description "1564.17 nm/191.662500 THz 3.125/6.25/12.5GHz spacing";
               }
               enum "1564.14" {
                 description "1564.14 nm/191.665625 THz 3.125GHz spacing";
               }
               enum "1564.12" {
                 description "1564.12 nm/191.668750 THz 3.125/6.25GHz spacing";
               }
               enum "1564.09" {
                 description "1564.09 nm/191.671875 THz 3.125GHz spacing";
               }
               enum "1564.07" {
                 description "1564.07 nm/191.675000 THz 3.125/6.25/12.5GHz spacing";
               }
               enum "1564.04" {
                 description "1564.04 nm/191.678125 THz 3.125GHz spacing";
               }
               enum "1564.02" {
                 description "1564.02 nm/191.681250 THz 3.125/6.25GHz spacing";
               }
               enum "1563.99" {
                 description "1563.99 nm/191.684375 THz 3.125GHz spacing";
               }
               enum "1563.96" {
                 description "1563.96 nm/191.687500 THz 3.125/6.25/12.5GHz spacing";
               }
               enum "1563.94" {
                 description "1563.94 nm/191.690625 THz 3.125GHz spacing";
               }
               enum "1563.91" {
                 description "1563.91 nm/191.693750 THz 3.125/6.25GHz spacing";
               }
               enum "1563.89" {
                 description "1563.89 nm/191.696875 THz 3.125GHz spacing";
               }
               enum "1563.86" {
                 description "1563.86 nm/191.700000 THz 3.125/6.25/12.5/50/75/100GHz spacing";
               }
               enum "1563.84" {
                 description "1563.84 nm/191.703125 THz 3.125GHz spacing";
               }
               enum "1563.81" {
                 description "1563.81 nm/191.706250 THz 3.125/6.25GHz spacing";
               }
               enum "1563.79" {
                 description "1563.79 nm/191.709375 THz 3.125GHz spacing";
               }
               enum "1563.76" {
                 description "1563.76 nm/191.712500 THz 3.125/6.25/12.5GHz spacing";
               }
               enum "1563.74" {
                 description "1563.74 nm/191.715625 THz 3.125GHz spacing";
               }
               enum "1563.71" {
                 description "1563.71 nm/191.718750 THz 3.125/6.25GHz spacing";
               }
               enum "1563.68" {
                 description "1563.68 nm/191.721875 THz 3.125GHz spacing";
               }
               enum "1563.66" {
                 description "1563.66 nm/191.725000 THz 3.125/6.25/12.5GHz spacing";
               }
               enum "1563.63" {
                 description "1563.63 nm/191.728125 THz 3.125GHz spacing";
               }
               enum "1563.61" {
                 description "1563.61 nm/191.731250 THz 3.125/6.25GHz spacing";
               }
               enum "1563.58" {
                 description "1563.58 nm/191.734375 THz 3.125GHz spacing";
               }
               enum "1563.56" {
                 description "1563.56 nm/191.737500 THz 3.125/6.25/12.5GHz spacing";
               }
               enum "1563.53" {
                 description "1563.53 nm/191.740625 THz 3.125GHz spacing";
               }
               enum "1563.51" {
                 description "1563.51 nm/191.743750 THz 3.125/6.25GHz spacing";
               }
               enum "1563.48" {
                 description "1563.48 nm/191.746875 THz 3.125GHz spacing";
               }
               enum "1563.45" {
                 description "1563.45 nm/191.750000 THz 3.125/6.25/12.5/50GHz spacing";
               }
               enum "1563.43" {
                 description "1563.43 nm/191.753125 THz 3.125GHz spacing";
               }
               enum "1563.40" {
                 description "1563.40 nm/191.756250 THz 3.125/6.25GHz spacing";
               }
               enum "1563.38" {
                 description "1563.38 nm/191.759375 THz 3.125GHz spacing";
               }
               enum "1563.35" {
                 description "1563.35 nm/191.762500 THz 3.125/6.25/12.5GHz spacing";
               }
               enum "1563.33" {
                 description "1563.33 nm/191.765625 THz 3.125GHz spacing";
               }
               enum "1563.30" {
                 description "1563.30 nm/191.768750 THz 3.125/6.25GHz spacing";
               }
               enum "1563.28" {
                 description "1563.28 nm/191.771875 THz 3.125GHz spacing";
               }
               enum "1563.25" {
                 description "1563.25 nm/191.775000 THz 3.125/6.25/12.5/75GHz spacing";
               }
               enum "1563.23" {
                 description "1563.23 nm/191.778125 THz 3.125GHz spacing";
               }
               enum "1563.20" {
                 description "1563.20 nm/191.781250 THz 3.125/6.25GHz spacing";
               }
               enum "1563.17" {
                 description "1563.17 nm/191.784375 THz 3.125GHz spacing";
               }
               enum "1563.15" {
                 description "1563.15 nm/191.787500 THz 3.125/6.25/12.5GHz spacing";
               }
               enum "1563.12" {
                 description "1563.12 nm/191.790625 THz 3.125GHz spacing";
               }
               enum "1563.10" {
                 description "1563.10 nm/191.793750 THz 3.125/6.25GHz spacing";
               }
               enum "1563.07" {
                 description "1563.07 nm/191.796875 THz 3.125GHz spacing";
               }
               enum "1563.05" {
                 description "1563.05 nm/191.800000 THz 3.125/6.25/12.5/100GHz spacing";
               }
               enum "1563.02" {
                 description "1563.02 nm/191.803125 THz 3.125GHz spacing";
               }
               enum "1563.00" {
                 description "1563.00 nm/191.806250 THz 3.125/6.25GHz spacing";
               }
               enum "1562.97" {
                 description "1562.97 nm/191.809375 THz 3.125GHz spacing";
               }
               enum "1562.95" {
                 description "1562.95 nm/191.812500 THz 3.125/6.25/12.5GHz spacing";
               }
               enum "1562.92" {
                 description "1562.92 nm/191.815625 THz 3.125GHz spacing";
               }
               enum "1562.89" {
                 description "1562.89 nm/191.818750 THz 3.125/6.25GHz spacing";
               }
               enum "1562.87" {
                 description "1562.87 nm/191.821875 THz 3.125GHz spacing";
               }
               enum "1562.84" {
                 description "1562.84 nm/191.825000 THz 3.125/6.25/12.5GHz spacing";
               }
               enum "1562.82" {
                 description "1562.82 nm/191.828125 THz 3.125GHz spacing";
               }
               enum "1562.79" {
                 description "1562.79 nm/191.831250 THz 3.125/6.25GHz spacing";
               }
               enum "1562.77" {
                 description "1562.77 nm/191.834375 THz 3.125GHz spacing";
               }
               enum "1562.74" {
                 description "1562.74 nm/191.837500 THz 3.125/6.25/12.5GHz spacing";
               }
               enum "1562.72" {
                 description "1562.72 nm/191.840625 THz 3.125GHz spacing";
               }
               enum "1562.69" {
                 description "1562.69 nm/191.843750 THz 3.125/6.25GHz spacing";
               }
               enum "1562.67" {
                 description "1562.67 nm/191.846875 THz 3.125GHz spacing";
               }
               enum "1562.64" {
                 description "1562.64 nm/191.850000 THz 3.125/6.25/12.5/50/75GHz spacing";
               }
               enum "1562.61" {
                 description "1562.61 nm/191.853125 THz 3.125GHz spacing";
               }
               enum "1562.59" {
                 description "1562.59 nm/191.856250 THz 3.125/6.25GHz spacing";
               }
               enum "1562.56" {
                 description "1562.56 nm/191.859375 THz 3.125GHz spacing";
               }
               enum "1562.54" {
                 description "1562.54 nm/191.862500 THz 3.125/6.25/12.5GHz spacing";
               }
               enum "1562.51" {
                 description "1562.51 nm/191.865625 THz 3.125GHz spacing";
               }
               enum "1562.49" {
                 description "1562.49 nm/191.868750 THz 3.125/6.25GHz spacing";
               }
               enum "1562.46" {
                 description "1562.46 nm/191.871875 THz 3.125GHz spacing";
               }
               enum "1562.44" {
                 description "1562.44 nm/191.875000 THz 3.125/6.25/12.5GHz spacing";
               }
               enum "1562.41" {
                 description "1562.41 nm/191.878125 THz 3.125GHz spacing";
               }
               enum "1562.39" {
                 description "1562.39 nm/191.881250 THz 3.125/6.25GHz spacing";
               }
               enum "1562.36" {
                 description "1562.36 nm/191.884375 THz 3.125GHz spacing";
               }
               enum "1562.33" {
                 description "1562.33 nm/191.887500 THz 3.125/6.25/12.5GHz spacing";
               }
               enum "1562.31" {
                 description "1562.31 nm/191.890625 THz 3.125GHz spacing";
               }
               enum "1562.28" {
                 description "1562.28 nm/191.893750 THz 3.125/6.25GHz spacing";
               }
               enum "1562.26" {
                 description "1562.26 nm/191.896875 THz 3.125GHz spacing";
               }
               enum "1562.23" {
                 description "1562.23 nm/191.900000 THz 3.125/6.25/12.5/100GHz spacing";
               }
               enum "1562.21" {
                 description "1562.21 nm/191.903125 THz 3.125GHz spacing";
               }
               enum "1562.18" {
                 description "1562.18 nm/191.906250 THz 3.125/6.25GHz spacing";
               }
               enum "1562.16" {
                 description "1562.16 nm/191.909375 THz 3.125GHz spacing";
               }
               enum "1562.13" {
                 description "1562.13 nm/191.912500 THz 3.125/6.25/12.5GHz spacing";
               }
               enum "1562.11" {
                 description "1562.11 nm/191.915625 THz 3.125GHz spacing";
               }
               enum "1562.08" {
                 description "1562.08 nm/191.918750 THz 3.125/6.25GHz spacing";
               }
               enum "1562.05" {
                 description "1562.05 nm/191.921875 THz 3.125GHz spacing";
               }
               enum "1562.03" {
                 description "1562.03 nm/191.925000 THz 3.125/6.25/12.5/75GHz spacing";
               }
               enum "1562.00" {
                 description "1562.00 nm/191.928125 THz 3.125GHz spacing";
               }
               enum "1561.98" {
                 description "1561.98 nm/191.931250 THz 3.125/6.25GHz spacing";
               }
               enum "1561.95" {
                 description "1561.95 nm/191.934375 THz 3.125GHz spacing";
               }
               enum "1561.93" {
                 description "1561.93 nm/191.937500 THz 3.125/6.25/12.5GHz spacing";
               }
               enum "1561.90" {
                 description "1561.90 nm/191.940625 THz 3.125GHz spacing";
               }
               enum "1561.88" {
                 description "1561.88 nm/191.943750 THz 3.125/6.25GHz spacing";
               }
               enum "1561.85" {
                 description "1561.85 nm/191.946875 THz 3.125GHz spacing";
               }
               enum "1561.83" {
                 description "1561.83 nm/191.950000 THz 3.125/6.25/12.5/50GHz spacing";
               }
               enum "1561.80" {
                 description "1561.80 nm/191.953125 THz 3.125GHz spacing";
               }
               enum "1561.77" {
                 description "1561.77 nm/191.956250 THz 3.125/6.25GHz spacing";
               }
               enum "1561.75" {
                 description "1561.75 nm/191.959375 THz 3.125GHz spacing";
               }
               enum "1561.72" {
                 description "1561.72 nm/191.962500 THz 3.125/6.25/12.5GHz spacing";
               }
               enum "1561.70" {
                 description "1561.70 nm/191.965625 THz 3.125GHz spacing";
               }
               enum "1561.67" {
                 description "1561.67 nm/191.968750 THz 3.125/6.25GHz spacing";
               }
               enum "1561.65" {
                 description "1561.65 nm/191.971875 THz 3.125GHz spacing";
               }
               enum "1561.62" {
                 description "1561.62 nm/191.975000 THz 3.125/6.25/12.5GHz spacing";
               }
               enum "1561.60" {
                 description "1561.60 nm/191.978125 THz 3.125GHz spacing";
               }
               enum "1561.57" {
                 description "1561.57 nm/191.981250 THz 3.125/6.25GHz spacing";
               }
               enum "1561.55" {
                 description "1561.55 nm/191.984375 THz 3.125GHz spacing";
               }
               enum "1561.52" {
                 description "1561.52 nm/191.987500 THz 3.125/6.25/12.5GHz spacing";
               }
               enum "1561.50" {
                 description "1561.50 nm/191.990625 THz 3.125GHz spacing";
               }
               enum "1561.47" {
                 description "1561.47 nm/191.993750 THz 3.125/6.25GHz spacing";
               }
               enum "1561.44" {
                 description "1561.44 nm/191.996875 THz 3.125GHz spacing";
               }
               enum "1561.42" {
                 description "1561.42 nm/192.000000 THz 3.125/6.25/12.5/50/75/100GHz spacing";
               }
               enum "1561.39" {
                 description "1561.39 nm/192.003125 THz 3.125GHz spacing";
               }
               enum "1561.37" {
                 description "1561.37 nm/192.006250 THz 3.125/6.25GHz spacing";
               }
               enum "1561.34" {
                 description "1561.34 nm/192.009375 THz 3.125GHz spacing";
               }
               enum "1561.32" {
                 description "1561.32 nm/192.012500 THz 3.125/6.25/12.5GHz spacing";
               }
               enum "1561.29" {
                 description "1561.29 nm/192.015625 THz 3.125GHz spacing";
               }
               enum "1561.27" {
                 description "1561.27 nm/192.018750 THz 3.125/6.25GHz spacing";
               }
               enum "1561.24" {
                 description "1561.24 nm/192.021875 THz 3.125GHz spacing";
               }
               enum "1561.22" {
                 description "1561.22 nm/192.025000 THz 3.125/6.25/12.5GHz spacing";
               }
               enum "1561.19" {
                 description "1561.19 nm/192.028125 THz 3.125GHz spacing";
               }
               enum "1561.16" {
                 description "1561.16 nm/192.031250 THz 3.125/6.25GHz spacing";
               }
               enum "1561.14" {
                 description "1561.14 nm/192.034375 THz 3.125GHz spacing";
               }
               enum "1561.11" {
                 description "1561.11 nm/192.037500 THz 3.125/6.25/12.5GHz spacing";
               }
               enum "1561.09" {
                 description "1561.09 nm/192.040625 THz 3.125GHz spacing";
               }
               enum "1561.06" {
                 description "1561.06 nm/192.043750 THz 3.125/6.25GHz spacing";
               }
               enum "1561.04" {
                 description "1561.04 nm/192.046875 THz 3.125GHz spacing";
               }
               enum "1561.01" {
                 description "1561.01 nm/192.050000 THz 3.125/6.25/12.5/50GHz spacing";
               }
               enum "1560.99" {
                 description "1560.99 nm/192.053125 THz 3.125GHz spacing";
               }
               enum "1560.96" {
                 description "1560.96 nm/192.056250 THz 3.125/6.25GHz spacing";
               }
               enum "1560.94" {
                 description "1560.94 nm/192.059375 THz 3.125GHz spacing";
               }
               enum "1560.91" {
                 description "1560.91 nm/192.062500 THz 3.125/6.25/12.5GHz spacing";
               }
               enum "1560.89" {
                 description "1560.89 nm/192.065625 THz 3.125GHz spacing";
               }
               enum "1560.86" {
                 description "1560.86 nm/192.068750 THz 3.125/6.25GHz spacing";
               }
               enum "1560.83" {
                 description "1560.83 nm/192.071875 THz 3.125GHz spacing";
               }
               enum "1560.81" {
                 description "1560.81 nm/192.075000 THz 3.125/6.25/12.5/75GHz spacing";
               }
               enum "1560.78" {
                 description "1560.78 nm/192.078125 THz 3.125GHz spacing";
               }
               enum "1560.76" {
                 description "1560.76 nm/192.081250 THz 3.125/6.25GHz spacing";
               }
               enum "1560.73" {
                 description "1560.73 nm/192.084375 THz 3.125GHz spacing";
               }
               enum "1560.71" {
                 description "1560.71 nm/192.087500 THz 3.125/6.25/12.5GHz spacing";
               }
               enum "1560.68" {
                 description "1560.68 nm/192.090625 THz 3.125GHz spacing";
               }
               enum "1560.66" {
                 description "1560.66 nm/192.093750 THz 3.125/6.25GHz spacing";
               }
               enum "1560.63" {
                 description "1560.63 nm/192.096875 THz 3.125GHz spacing";
               }
               enum "1560.61" {
                 description "1560.61 nm/192.100000 THz 3.125/6.25/12.5/100GHz spacing";
               }
               enum "1560.58" {
                 description "1560.58 nm/192.103125 THz 3.125GHz spacing";
               }
               enum "1560.56" {
                 description "1560.56 nm/192.106250 THz 3.125/6.25GHz spacing";
               }
               enum "1560.53" {
                 description "1560.53 nm/192.109375 THz 3.125GHz spacing";
               }
               enum "1560.50" {
                 description "1560.50 nm/192.112500 THz 3.125/6.25/12.5GHz spacing";
               }
               enum "1560.48" {
                 description "1560.48 nm/192.115625 THz 3.125GHz spacing";
               }
               enum "1560.45" {
                 description "1560.45 nm/192.118750 THz 3.125/6.25GHz spacing";
               }
               enum "1560.43" {
                 description "1560.43 nm/192.121875 THz 3.125GHz spacing";
               }
               enum "1560.40" {
                 description "1560.40 nm/192.125000 THz 3.125/6.25/12.5GHz spacing";
               }
               enum "1560.38" {
                 description "1560.38 nm/192.128125 THz 3.125GHz spacing";
               }
               enum "1560.35" {
                 description "1560.35 nm/192.131250 THz 3.125/6.25GHz spacing";
               }
               enum "1560.33" {
                 description "1560.33 nm/192.134375 THz 3.125GHz spacing";
               }
               enum "1560.30" {
                 description "1560.30 nm/192.137500 THz 3.125/6.25/12.5GHz spacing";
               }
               enum "1560.28" {
                 description "1560.28 nm/192.140625 THz 3.125GHz spacing";
               }
               enum "1560.25" {
                 description "1560.25 nm/192.143750 THz 3.125/6.25GHz spacing";
               }
               enum "1560.23" {
                 description "1560.23 nm/192.146875 THz 3.125GHz spacing";
               }
               enum "1560.20" {
                 description "1560.20 nm/192.150000 THz 3.125/6.25/12.5/50/75GHz spacing";
               }
               enum "1560.17" {
                 description "1560.17 nm/192.153125 THz 3.125GHz spacing";
               }
               enum "1560.15" {
                 description "1560.15 nm/192.156250 THz 3.125/6.25GHz spacing";
               }
               enum "1560.12" {
                 description "1560.12 nm/192.159375 THz 3.125GHz spacing";
               }
               enum "1560.10" {
                 description "1560.10 nm/192.162500 THz 3.125/6.25/12.5GHz spacing";
               }
               enum "1560.07" {
                 description "1560.07 nm/192.165625 THz 3.125GHz spacing";
               }
               enum "1560.05" {
                 description "1560.05 nm/192.168750 THz 3.125/6.25GHz spacing";
               }
               enum "1560.02" {
                 description "1560.02 nm/192.171875 THz 3.125GHz spacing";
               }
               enum "1560.00" {
                 description "1560.00 nm/192.175000 THz 3.125/6.25/12.5GHz spacing";
               }
               enum "1559.97" {
                 description "1559.97 nm/192.178125 THz 3.125GHz spacing";
               }
               enum "1559.95" {
                 description "1559.95 nm/192.181250 THz 3.125/6.25GHz spacing";
               }
               enum "1559.92" {
                 description "1559.92 nm/192.184375 THz 3.125GHz spacing";
               }
               enum "1559.90" {
                 description "1559.90 nm/192.187500 THz 3.125/6.25/12.5GHz spacing";
               }
               enum "1559.87" {
                 description "1559.87 nm/192.190625 THz 3.125GHz spacing";
               }
               enum "1559.84" {
                 description "1559.84 nm/192.193750 THz 3.125/6.25GHz spacing";
               }
               enum "1559.82" {
                 description "1559.82 nm/192.196875 THz 3.125GHz spacing";
               }
               enum "1559.79" {
                 description "1559.79 nm/192.200000 THz 3.125/6.25/12.5/100GHz spacing";
               }
               enum "1559.77" {
                 description "1559.77 nm/192.203125 THz 3.125GHz spacing";
               }
               enum "1559.74" {
                 description "1559.74 nm/192.206250 THz 3.125/6.25GHz spacing";
               }
               enum "1559.72" {
                 description "1559.72 nm/192.209375 THz 3.125GHz spacing";
               }
               enum "1559.69" {
                 description "1559.69 nm/192.212500 THz 3.125/6.25/12.5GHz spacing";
               }
               enum "1559.67" {
                 description "1559.67 nm/192.215625 THz 3.125GHz spacing";
               }
               enum "1559.64" {
                 description "1559.64 nm/192.218750 THz 3.125/6.25GHz spacing";
               }
               enum "1559.62" {
                 description "1559.62 nm/192.221875 THz 3.125GHz spacing";
               }
               enum "1559.59" {
                 description "1559.59 nm/192.225000 THz 3.125/6.25/12.5/75GHz spacing";
               }
               enum "1559.57" {
                 description "1559.57 nm/192.228125 THz 3.125GHz spacing";
               }
               enum "1559.54" {
                 description "1559.54 nm/192.231250 THz 3.125/6.25GHz spacing";
               }
               enum "1559.52" {
                 description "1559.52 nm/192.234375 THz 3.125GHz spacing";
               }
               enum "1559.49" {
                 description "1559.49 nm/192.237500 THz 3.125/6.25/12.5GHz spacing";
               }
               enum "1559.46" {
                 description "1559.46 nm/192.240625 THz 3.125GHz spacing";
               }
               enum "1559.44" {
                 description "1559.44 nm/192.243750 THz 3.125/6.25GHz spacing";
               }
               enum "1559.41" {
                 description "1559.41 nm/192.246875 THz 3.125GHz spacing";
               }
               enum "1559.39" {
                 description "1559.39 nm/192.250000 THz 3.125/6.25/12.5/50GHz spacing";
               }
               enum "1559.36" {
                 description "1559.36 nm/192.253125 THz 3.125GHz spacing";
               }
               enum "1559.34" {
                 description "1559.34 nm/192.256250 THz 3.125/6.25GHz spacing";
               }
               enum "1559.31" {
                 description "1559.31 nm/192.259375 THz 3.125GHz spacing";
               }
               enum "1559.29" {
                 description "1559.29 nm/192.262500 THz 3.125/6.25/12.5GHz spacing";
               }
               enum "1559.26" {
                 description "1559.26 nm/192.265625 THz 3.125GHz spacing";
               }
               enum "1559.24" {
                 description "1559.24 nm/192.268750 THz 3.125/6.25GHz spacing";
               }
               enum "1559.21" {
                 description "1559.21 nm/192.271875 THz 3.125GHz spacing";
               }
               enum "1559.19" {
                 description "1559.19 nm/192.275000 THz 3.125/6.25/12.5GHz spacing";
               }
               enum "1559.16" {
                 description "1559.16 nm/192.278125 THz 3.125GHz spacing";
               }
               enum "1559.14" {
                 description "1559.14 nm/192.281250 THz 3.125/6.25GHz spacing";
               }
               enum "1559.11" {
                 description "1559.11 nm/192.284375 THz 3.125GHz spacing";
               }
               enum "1559.08" {
                 description "1559.08 nm/192.287500 THz 3.125/6.25/12.5GHz spacing";
               }
               enum "1559.06" {
                 description "1559.06 nm/192.290625 THz 3.125GHz spacing";
               }
               enum "1559.03" {
                 description "1559.03 nm/192.293750 THz 3.125/6.25GHz spacing";
               }
               enum "1559.01" {
                 description "1559.01 nm/192.296875 THz 3.125GHz spacing";
               }
               enum "1558.98" {
                 description "1558.98 nm/192.300000 THz 3.125/6.25/12.5/50/75/100GHz spacing";
               }
               enum "1558.96" {
                 description "1558.96 nm/192.303125 THz 3.125GHz spacing";
               }
               enum "1558.93" {
                 description "1558.93 nm/192.306250 THz 3.125/6.25GHz spacing";
               }
               enum "1558.91" {
                 description "1558.91 nm/192.309375 THz 3.125GHz spacing";
               }
               enum "1558.88" {
                 description "1558.88 nm/192.312500 THz 3.125/6.25/12.5GHz spacing";
               }
               enum "1558.86" {
                 description "1558.86 nm/192.315625 THz 3.125GHz spacing";
               }
               enum "1558.83" {
                 description "1558.83 nm/192.318750 THz 3.125/6.25GHz spacing";
               }
               enum "1558.81" {
                 description "1558.81 nm/192.321875 THz 3.125GHz spacing";
               }
               enum "1558.78" {
                 description "1558.78 nm/192.325000 THz 3.125/6.25/12.5GHz spacing";
               }
               enum "1558.76" {
                 description "1558.76 nm/192.328125 THz 3.125GHz spacing";
               }
               enum "1558.73" {
                 description "1558.73 nm/192.331250 THz 3.125/6.25GHz spacing";
               }
               enum "1558.70" {
                 description "1558.70 nm/192.334375 THz 3.125GHz spacing";
               }
               enum "1558.68" {
                 description "1558.68 nm/192.337500 THz 3.125/6.25/12.5GHz spacing";
               }
               enum "1558.65" {
                 description "1558.65 nm/192.340625 THz 3.125GHz spacing";
               }
               enum "1558.63" {
                 description "1558.63 nm/192.343750 THz 3.125/6.25GHz spacing";
               }
               enum "1558.60" {
                 description "1558.60 nm/192.346875 THz 3.125GHz spacing";
               }
               enum "1558.58" {
                 description "1558.58 nm/192.350000 THz 3.125/6.25/12.5/50GHz spacing";
               }
               enum "1558.55" {
                 description "1558.55 nm/192.353125 THz 3.125GHz spacing";
               }
               enum "1558.53" {
                 description "1558.53 nm/192.356250 THz 3.125/6.25GHz spacing";
               }
               enum "1558.50" {
                 description "1558.50 nm/192.359375 THz 3.125GHz spacing";
               }
               enum "1558.48" {
                 description "1558.48 nm/192.362500 THz 3.125/6.25/12.5GHz spacing";
               }
               enum "1558.45" {
                 description "1558.45 nm/192.365625 THz 3.125GHz spacing";
               }
               enum "1558.43" {
                 description "1558.43 nm/192.368750 THz 3.125/6.25GHz spacing";
               }
               enum "1558.40" {
                 description "1558.40 nm/192.371875 THz 3.125GHz spacing";
               }
               enum "1558.38" {
                 description "1558.38 nm/192.375000 THz 3.125/6.25/12.5/75GHz spacing";
               }
               enum "1558.35" {
                 description "1558.35 nm/192.378125 THz 3.125GHz spacing";
               }
               enum "1558.32" {
                 description "1558.32 nm/192.381250 THz 3.125/6.25GHz spacing";
               }
               enum "1558.30" {
                 description "1558.30 nm/192.384375 THz 3.125GHz spacing";
               }
               enum "1558.27" {
                 description "1558.27 nm/192.387500 THz 3.125/6.25/12.5GHz spacing";
               }
               enum "1558.25" {
                 description "1558.25 nm/192.390625 THz 3.125GHz spacing";
               }
               enum "1558.22" {
                 description "1558.22 nm/192.393750 THz 3.125/6.25GHz spacing";
               }
               enum "1558.20" {
                 description "1558.20 nm/192.396875 THz 3.125GHz spacing";
               }
               enum "1558.17" {
                 description "1558.17 nm/192.400000 THz 3.125/6.25/12.5/100GHz spacing";
               }
               enum "1558.15" {
                 description "1558.15 nm/192.403125 THz 3.125GHz spacing";
               }
               enum "1558.12" {
                 description "1558.12 nm/192.406250 THz 3.125/6.25GHz spacing";
               }
               enum "1558.10" {
                 description "1558.10 nm/192.409375 THz 3.125GHz spacing";
               }
               enum "1558.07" {
                 description "1558.07 nm/192.412500 THz 3.125/6.25/12.5GHz spacing";
               }
               enum "1558.05" {
                 description "1558.05 nm/192.415625 THz 3.125GHz spacing";
               }
               enum "1558.02" {
                 description "1558.02 nm/192.418750 THz 3.125/6.25GHz spacing";
               }
               enum "1558.00" {
                 description "1558.00 nm/192.421875 THz 3.125GHz spacing";
               }
               enum "1557.97" {
                 description "1557.97 nm/192.425000 THz 3.125/6.25/12.5GHz spacing";
               }
               enum "1557.95" {
                 description "1557.95 nm/192.428125 THz 3.125GHz spacing";
               }
               enum "1557.92" {
                 description "1557.92 nm/192.431250 THz 3.125/6.25GHz spacing";
               }
               enum "1557.89" {
                 description "1557.89 nm/192.434375 THz 3.125GHz spacing";
               }
               enum "1557.87" {
                 description "1557.87 nm/192.437500 THz 3.125/6.25/12.5GHz spacing";
               }
               enum "1557.84" {
                 description "1557.84 nm/192.440625 THz 3.125GHz spacing";
               }
               enum "1557.82" {
                 description "1557.82 nm/192.443750 THz 3.125/6.25GHz spacing";
               }
               enum "1557.79" {
                 description "1557.79 nm/192.446875 THz 3.125GHz spacing";
               }
               enum "1557.77" {
                 description "1557.77 nm/192.450000 THz 3.125/6.25/12.5/50/75GHz spacing";
               }
               enum "1557.74" {
                 description "1557.74 nm/192.453125 THz 3.125GHz spacing";
               }
               enum "1557.72" {
                 description "1557.72 nm/192.456250 THz 3.125/6.25GHz spacing";
               }
               enum "1557.69" {
                 description "1557.69 nm/192.459375 THz 3.125GHz spacing";
               }
               enum "1557.67" {
                 description "1557.67 nm/192.462500 THz 3.125/6.25/12.5GHz spacing";
               }
               enum "1557.64" {
                 description "1557.64 nm/192.465625 THz 3.125GHz spacing";
               }
               enum "1557.62" {
                 description "1557.62 nm/192.468750 THz 3.125/6.25GHz spacing";
               }
               enum "1557.59" {
                 description "1557.59 nm/192.471875 THz 3.125GHz spacing";
               }
               enum "1557.57" {
                 description "1557.57 nm/192.475000 THz 3.125/6.25/12.5GHz spacing";
               }
               enum "1557.54" {
                 description "1557.54 nm/192.478125 THz 3.125GHz spacing";
               }
               enum "1557.52" {
                 description "1557.52 nm/192.481250 THz 3.125/6.25GHz spacing";
               }
               enum "1557.49" {
                 description "1557.49 nm/192.484375 THz 3.125GHz spacing";
               }
               enum "1557.46" {
                 description "1557.46 nm/192.487500 THz 3.125/6.25/12.5GHz spacing";
               }
               enum "1557.44" {
                 description "1557.44 nm/192.490625 THz 3.125GHz spacing";
               }
               enum "1557.41" {
                 description "1557.41 nm/192.493750 THz 3.125/6.25GHz spacing";
               }
               enum "1557.39" {
                 description "1557.39 nm/192.496875 THz 3.125GHz spacing";
               }
               enum "1557.36" {
                 description "1557.36 nm/192.500000 THz 3.125/6.25/12.5/100GHz spacing";
               }
               enum "1557.34" {
                 description "1557.34 nm/192.503125 THz 3.125GHz spacing";
               }
               enum "1557.31" {
                 description "1557.31 nm/192.506250 THz 3.125/6.25GHz spacing";
               }
               enum "1557.29" {
                 description "1557.29 nm/192.509375 THz 3.125GHz spacing";
               }
               enum "1557.26" {
                 description "1557.26 nm/192.512500 THz 3.125/6.25/12.5GHz spacing";
               }
               enum "1557.24" {
                 description "1557.24 nm/192.515625 THz 3.125GHz spacing";
               }
               enum "1557.21" {
                 description "1557.21 nm/192.518750 THz 3.125/6.25GHz spacing";
               }
               enum "1557.19" {
                 description "1557.19 nm/192.521875 THz 3.125GHz spacing";
               }
               enum "1557.16" {
                 description "1557.16 nm/192.525000 THz 3.125/6.25/12.5/75GHz spacing";
               }
               enum "1557.14" {
                 description "1557.14 nm/192.528125 THz 3.125GHz spacing";
               }
               enum "1557.11" {
                 description "1557.11 nm/192.531250 THz 3.125/6.25GHz spacing";
               }
               enum "1557.09" {
                 description "1557.09 nm/192.534375 THz 3.125GHz spacing";
               }
               enum "1557.06" {
                 description "1557.06 nm/192.537500 THz 3.125/6.25/12.5GHz spacing";
               }
               enum "1557.03" {
                 description "1557.03 nm/192.540625 THz 3.125GHz spacing";
               }
               enum "1557.01" {
                 description "1557.01 nm/192.543750 THz 3.125/6.25GHz spacing";
               }
               enum "1556.98" {
                 description "1556.98 nm/192.546875 THz 3.125GHz spacing";
               }
               enum "1556.96" {
                 description "1556.96 nm/192.550000 THz 3.125/6.25/12.5/50GHz spacing";
               }
               enum "1556.93" {
                 description "1556.93 nm/192.553125 THz 3.125GHz spacing";
               }
               enum "1556.91" {
                 description "1556.91 nm/192.556250 THz 3.125/6.25GHz spacing";
               }
               enum "1556.88" {
                 description "1556.88 nm/192.559375 THz 3.125GHz spacing";
               }
               enum "1556.86" {
                 description "1556.86 nm/192.562500 THz 3.125/6.25/12.5GHz spacing";
               }
               enum "1556.83" {
                 description "1556.83 nm/192.565625 THz 3.125GHz spacing";
               }
               enum "1556.81" {
                 description "1556.81 nm/192.568750 THz 3.125/6.25GHz spacing";
               }
               enum "1556.78" {
                 description "1556.78 nm/192.571875 THz 3.125GHz spacing";
               }
               enum "1556.76" {
                 description "1556.76 nm/192.575000 THz 3.125/6.25/12.5GHz spacing";
               }
               enum "1556.73" {
                 description "1556.73 nm/192.578125 THz 3.125GHz spacing";
               }
               enum "1556.71" {
                 description "1556.71 nm/192.581250 THz 3.125/6.25GHz spacing";
               }
               enum "1556.68" {
                 description "1556.68 nm/192.584375 THz 3.125GHz spacing";
               }
               enum "1556.66" {
                 description "1556.66 nm/192.587500 THz 3.125/6.25/12.5GHz spacing";
               }
               enum "1556.63" {
                 description "1556.63 nm/192.590625 THz 3.125GHz spacing";
               }
               enum "1556.61" {
                 description "1556.61 nm/192.593750 THz 3.125/6.25GHz spacing";
               }
               enum "1556.58" {
                 description "1556.58 nm/192.596875 THz 3.125GHz spacing";
               }
               enum "1556.55" {
                 description "1556.55 nm/192.600000 THz 3.125/6.25/12.5/50/75/100GHz spacing";
               }
               enum "1556.53" {
                 description "1556.53 nm/192.603125 THz 3.125GHz spacing";
               }
               enum "1556.50" {
                 description "1556.50 nm/192.606250 THz 3.125/6.25GHz spacing";
               }
               enum "1556.48" {
                 description "1556.48 nm/192.609375 THz 3.125GHz spacing";
               }
               enum "1556.45" {
                 description "1556.45 nm/192.612500 THz 3.125/6.25/12.5GHz spacing";
               }
               enum "1556.43" {
                 description "1556.43 nm/192.615625 THz 3.125GHz spacing";
               }
               enum "1556.40" {
                 description "1556.40 nm/192.618750 THz 3.125/6.25GHz spacing";
               }
               enum "1556.38" {
                 description "1556.38 nm/192.621875 THz 3.125GHz spacing";
               }
               enum "1556.35" {
                 description "1556.35 nm/192.625000 THz 3.125/6.25/12.5GHz spacing";
               }
               enum "1556.33" {
                 description "1556.33 nm/192.628125 THz 3.125GHz spacing";
               }
               enum "1556.30" {
                 description "1556.30 nm/192.631250 THz 3.125/6.25GHz spacing";
               }
               enum "1556.28" {
                 description "1556.28 nm/192.634375 THz 3.125GHz spacing";
               }
               enum "1556.25" {
                 description "1556.25 nm/192.637500 THz 3.125/6.25/12.5GHz spacing";
               }
               enum "1556.23" {
                 description "1556.23 nm/192.640625 THz 3.125GHz spacing";
               }
               enum "1556.20" {
                 description "1556.20 nm/192.643750 THz 3.125/6.25GHz spacing";
               }
               enum "1556.18" {
                 description "1556.18 nm/192.646875 THz 3.125GHz spacing";
               }
               enum "1556.15" {
                 description "1556.15 nm/192.650000 THz 3.125/6.25/12.5/50GHz spacing";
               }
               enum "1556.13" {
                 description "1556.13 nm/192.653125 THz 3.125GHz spacing";
               }
               enum "1556.10" {
                 description "1556.10 nm/192.656250 THz 3.125/6.25GHz spacing";
               }
               enum "1556.08" {
                 description "1556.08 nm/192.659375 THz 3.125GHz spacing";
               }
               enum "1556.05" {
                 description "1556.05 nm/192.662500 THz 3.125/6.25/12.5GHz spacing";
               }
               enum "1556.02" {
                 description "1556.02 nm/192.665625 THz 3.125GHz spacing";
               }
               enum "1556.00" {
                 description "1556.00 nm/192.668750 THz 3.125/6.25GHz spacing";
               }
               enum "1555.97" {
                 description "1555.97 nm/192.671875 THz 3.125GHz spacing";
               }
               enum "1555.95" {
                 description "1555.95 nm/192.675000 THz 3.125/6.25/12.5/75GHz spacing";
               }
               enum "1555.92" {
                 description "1555.92 nm/192.678125 THz 3.125GHz spacing";
               }
               enum "1555.90" {
                 description "1555.90 nm/192.681250 THz 3.125/6.25GHz spacing";
               }
               enum "1555.87" {
                 description "1555.87 nm/192.684375 THz 3.125GHz spacing";
               }
               enum "1555.85" {
                 description "1555.85 nm/192.687500 THz 3.125/6.25/12.5GHz spacing";
               }
               enum "1555.82" {
                 description "1555.82 nm/192.690625 THz 3.125GHz spacing";
               }
               enum "1555.80" {
                 description "1555.80 nm/192.693750 THz 3.125/6.25GHz spacing";
               }
               enum "1555.77" {
                 description "1555.77 nm/192.696875 THz 3.125GHz spacing";
               }
               enum "1555.75" {
                 description "1555.75 nm/192.700000 THz 3.125/6.25/12.5/100GHz spacing";
               }
               enum "1555.72" {
                 description "1555.72 nm/192.703125 THz 3.125GHz spacing";
               }
               enum "1555.70" {
                 description "1555.70 nm/192.706250 THz 3.125/6.25GHz spacing";
               }
               enum "1555.67" {
                 description "1555.67 nm/192.709375 THz 3.125GHz spacing";
               }
               enum "1555.65" {
                 description "1555.65 nm/192.712500 THz 3.125/6.25/12.5GHz spacing";
               }
               enum "1555.62" {
                 description "1555.62 nm/192.715625 THz 3.125GHz spacing";
               }
               enum "1555.60" {
                 description "1555.60 nm/192.718750 THz 3.125/6.25GHz spacing";
               }
               enum "1555.57" {
                 description "1555.57 nm/192.721875 THz 3.125GHz spacing";
               }
               enum "1555.55" {
                 description "1555.55 nm/192.725000 THz 3.125/6.25/12.5GHz spacing";
               }
               enum "1555.52" {
                 description "1555.52 nm/192.728125 THz 3.125GHz spacing";
               }
               enum "1555.49" {
                 description "1555.49 nm/192.731250 THz 3.125/6.25GHz spacing";
               }
               enum "1555.47" {
                 description "1555.47 nm/192.734375 THz 3.125GHz spacing";
               }
               enum "1555.44" {
                 description "1555.44 nm/192.737500 THz 3.125/6.25/12.5GHz spacing";
               }
               enum "1555.42" {
                 description "1555.42 nm/192.740625 THz 3.125GHz spacing";
               }
               enum "1555.39" {
                 description "1555.39 nm/192.743750 THz 3.125/6.25GHz spacing";
               }
               enum "1555.37" {
                 description "1555.37 nm/192.746875 THz 3.125GHz spacing";
               }
               enum "1555.34" {
                 description "1555.34 nm/192.750000 THz 3.125/6.25/12.5/50/75GHz spacing";
               }
               enum "1555.32" {
                 description "1555.32 nm/192.753125 THz 3.125GHz spacing";
               }
               enum "1555.29" {
                 description "1555.29 nm/192.756250 THz 3.125/6.25GHz spacing";
               }
               enum "1555.27" {
                 description "1555.27 nm/192.759375 THz 3.125GHz spacing";
               }
               enum "1555.24" {
                 description "1555.24 nm/192.762500 THz 3.125/6.25/12.5GHz spacing";
               }
               enum "1555.22" {
                 description "1555.22 nm/192.765625 THz 3.125GHz spacing";
               }
               enum "1555.19" {
                 description "1555.19 nm/192.768750 THz 3.125/6.25GHz spacing";
               }
               enum "1555.17" {
                 description "1555.17 nm/192.771875 THz 3.125GHz spacing";
               }
               enum "1555.14" {
                 description "1555.14 nm/192.775000 THz 3.125/6.25/12.5GHz spacing";
               }
               enum "1555.12" {
                 description "1555.12 nm/192.778125 THz 3.125GHz spacing";
               }
               enum "1555.09" {
                 description "1555.09 nm/192.781250 THz 3.125/6.25GHz spacing";
               }
               enum "1555.07" {
                 description "1555.07 nm/192.784375 THz 3.125GHz spacing";
               }
               enum "1555.04" {
                 description "1555.04 nm/192.787500 THz 3.125/6.25/12.5GHz spacing";
               }
               enum "1555.02" {
                 description "1555.02 nm/192.790625 THz 3.125GHz spacing";
               }
               enum "1554.99" {
                 description "1554.99 nm/192.793750 THz 3.125/6.25GHz spacing";
               }
               enum "1554.97" {
                 description "1554.97 nm/192.796875 THz 3.125GHz spacing";
               }
               enum "1554.94" {
                 description "1554.94 nm/192.800000 THz 3.125/6.25/12.5/100GHz spacing";
               }
               enum "1554.91" {
                 description "1554.91 nm/192.803125 THz 3.125GHz spacing";
               }
               enum "1554.89" {
                 description "1554.89 nm/192.806250 THz 3.125/6.25GHz spacing";
               }
               enum "1554.86" {
                 description "1554.86 nm/192.809375 THz 3.125GHz spacing";
               }
               enum "1554.84" {
                 description "1554.84 nm/192.812500 THz 3.125/6.25/12.5GHz spacing";
               }
               enum "1554.81" {
                 description "1554.81 nm/192.815625 THz 3.125GHz spacing";
               }
               enum "1554.79" {
                 description "1554.79 nm/192.818750 THz 3.125/6.25GHz spacing";
               }
               enum "1554.76" {
                 description "1554.76 nm/192.821875 THz 3.125GHz spacing";
               }
               enum "1554.74" {
                 description "1554.74 nm/192.825000 THz 3.125/6.25/12.5/75GHz spacing";
               }
               enum "1554.71" {
                 description "1554.71 nm/192.828125 THz 3.125GHz spacing";
               }
               enum "1554.69" {
                 description "1554.69 nm/192.831250 THz 3.125/6.25GHz spacing";
               }
               enum "1554.66" {
                 description "1554.66 nm/192.834375 THz 3.125GHz spacing";
               }
               enum "1554.64" {
                 description "1554.64 nm/192.837500 THz 3.125/6.25/12.5GHz spacing";
               }
               enum "1554.61" {
                 description "1554.61 nm/192.840625 THz 3.125GHz spacing";
               }
               enum "1554.59" {
                 description "1554.59 nm/192.843750 THz 3.125/6.25GHz spacing";
               }
               enum "1554.56" {
                 description "1554.56 nm/192.846875 THz 3.125GHz spacing";
               }
               enum "1554.54" {
                 description "1554.54 nm/192.850000 THz 3.125/6.25/12.5/50GHz spacing";
               }
               enum "1554.51" {
                 description "1554.51 nm/192.853125 THz 3.125GHz spacing";
               }
               enum "1554.49" {
                 description "1554.49 nm/192.856250 THz 3.125/6.25GHz spacing";
               }
               enum "1554.46" {
                 description "1554.46 nm/192.859375 THz 3.125GHz spacing";
               }
               enum "1554.44" {
                 description "1554.44 nm/192.862500 THz 3.125/6.25/12.5GHz spacing";
               }
               enum "1554.41" {
                 description "1554.41 nm/192.865625 THz 3.125GHz spacing";
               }
               enum "1554.39" {
                 description "1554.39 nm/192.868750 THz 3.125/6.25GHz spacing";
               }
               enum "1554.36" {
                 description "1554.36 nm/192.871875 THz 3.125GHz spacing";
               }
               enum "1554.34" {
                 description "1554.34 nm/192.875000 THz 3.125/6.25/12.5GHz spacing";
               }
               enum "1554.31" {
                 description "1554.31 nm/192.878125 THz 3.125GHz spacing";
               }
               enum "1554.29" {
                 description "1554.29 nm/192.881250 THz 3.125/6.25GHz spacing";
               }
               enum "1554.26" {
                 description "1554.26 nm/192.884375 THz 3.125GHz spacing";
               }
               enum "1554.23" {
                 description "1554.23 nm/192.887500 THz 3.125/6.25/12.5GHz spacing";
               }
               enum "1554.21" {
                 description "1554.21 nm/192.890625 THz 3.125GHz spacing";
               }
               enum "1554.18" {
                 description "1554.18 nm/192.893750 THz 3.125/6.25GHz spacing";
               }
               enum "1554.16" {
                 description "1554.16 nm/192.896875 THz 3.125GHz spacing";
               }
               enum "1554.13" {
                 description "1554.13 nm/192.900000 THz 3.125/6.25/12.5/50/75/100GHz spacing";
               }
               enum "1554.11" {
                 description "1554.11 nm/192.903125 THz 3.125GHz spacing";
               }
               enum "1554.08" {
                 description "1554.08 nm/192.906250 THz 3.125/6.25GHz spacing";
               }
               enum "1554.06" {
                 description "1554.06 nm/192.909375 THz 3.125GHz spacing";
               }
               enum "1554.03" {
                 description "1554.03 nm/192.912500 THz 3.125/6.25/12.5GHz spacing";
               }
               enum "1554.01" {
                 description "1554.01 nm/192.915625 THz 3.125GHz spacing";
               }
               enum "1553.98" {
                 description "1553.98 nm/192.918750 THz 3.125/6.25GHz spacing";
               }
               enum "1553.96" {
                 description "1553.96 nm/192.921875 THz 3.125GHz spacing";
               }
               enum "1553.93" {
                 description "1553.93 nm/192.925000 THz 3.125/6.25/12.5GHz spacing";
               }
               enum "1553.91" {
                 description "1553.91 nm/192.928125 THz 3.125GHz spacing";
               }
               enum "1553.88" {
                 description "1553.88 nm/192.931250 THz 3.125/6.25GHz spacing";
               }
               enum "1553.86" {
                 description "1553.86 nm/192.934375 THz 3.125GHz spacing";
               }
               enum "1553.83" {
                 description "1553.83 nm/192.937500 THz 3.125/6.25/12.5GHz spacing";
               }
               enum "1553.81" {
                 description "1553.81 nm/192.940625 THz 3.125GHz spacing";
               }
               enum "1553.78" {
                 description "1553.78 nm/192.943750 THz 3.125/6.25GHz spacing";
               }
               enum "1553.76" {
                 description "1553.76 nm/192.946875 THz 3.125GHz spacing";
               }
               enum "1553.73" {
                 description "1553.73 nm/192.950000 THz 3.125/6.25/12.5/50GHz spacing";
               }
               enum "1553.71" {
                 description "1553.71 nm/192.953125 THz 3.125GHz spacing";
               }
               enum "1553.68" {
                 description "1553.68 nm/192.956250 THz 3.125/6.25GHz spacing";
               }
               enum "1553.66" {
                 description "1553.66 nm/192.959375 THz 3.125GHz spacing";
               }
               enum "1553.63" {
                 description "1553.63 nm/192.962500 THz 3.125/6.25/12.5GHz spacing";
               }
               enum "1553.61" {
                 description "1553.61 nm/192.965625 THz 3.125GHz spacing";
               }
               enum "1553.58" {
                 description "1553.58 nm/192.968750 THz 3.125/6.25GHz spacing";
               }
               enum "1553.56" {
                 description "1553.56 nm/192.971875 THz 3.125GHz spacing";
               }
               enum "1553.53" {
                 description "1553.53 nm/192.975000 THz 3.125/6.25/12.5/75GHz spacing";
               }
               enum "1553.50" {
                 description "1553.50 nm/192.978125 THz 3.125GHz spacing";
               }
               enum "1553.48" {
                 description "1553.48 nm/192.981250 THz 3.125/6.25GHz spacing";
               }
               enum "1553.45" {
                 description "1553.45 nm/192.984375 THz 3.125GHz spacing";
               }
               enum "1553.43" {
                 description "1553.43 nm/192.987500 THz 3.125/6.25/12.5GHz spacing";
               }
               enum "1553.40" {
                 description "1553.40 nm/192.990625 THz 3.125GHz spacing";
               }
               enum "1553.38" {
                 description "1553.38 nm/192.993750 THz 3.125/6.25GHz spacing";
               }
               enum "1553.35" {
                 description "1553.35 nm/192.996875 THz 3.125GHz spacing";
               }
               enum "1553.33" {
                 description "1553.33 nm/193.000000 THz 3.125/6.25/12.5/100GHz spacing";
               }
               enum "1553.30" {
                 description "1553.30 nm/193.003125 THz 3.125GHz spacing";
               }
               enum "1553.28" {
                 description "1553.28 nm/193.006250 THz 3.125/6.25GHz spacing";
               }
               enum "1553.25" {
                 description "1553.25 nm/193.009375 THz 3.125GHz spacing";
               }
               enum "1553.23" {
                 description "1553.23 nm/193.012500 THz 3.125/6.25/12.5GHz spacing";
               }
               enum "1553.20" {
                 description "1553.20 nm/193.015625 THz 3.125GHz spacing";
               }
               enum "1553.18" {
                 description "1553.18 nm/193.018750 THz 3.125/6.25GHz spacing";
               }
               enum "1553.15" {
                 description "1553.15 nm/193.021875 THz 3.125GHz spacing";
               }
               enum "1553.13" {
                 description "1553.13 nm/193.025000 THz 3.125/6.25/12.5GHz spacing";
               }
               enum "1553.10" {
                 description "1553.10 nm/193.028125 THz 3.125GHz spacing";
               }
               enum "1553.08" {
                 description "1553.08 nm/193.031250 THz 3.125/6.25GHz spacing";
               }
               enum "1553.05" {
                 description "1553.05 nm/193.034375 THz 3.125GHz spacing";
               }
               enum "1553.03" {
                 description "1553.03 nm/193.037500 THz 3.125/6.25/12.5GHz spacing";
               }
               enum "1553.00" {
                 description "1553.00 nm/193.040625 THz 3.125GHz spacing";
               }
               enum "1552.98" {
                 description "1552.98 nm/193.043750 THz 3.125/6.25GHz spacing";
               }
               enum "1552.95" {
                 description "1552.95 nm/193.046875 THz 3.125GHz spacing";
               }
               enum "1552.93" {
                 description "1552.93 nm/193.050000 THz 3.125/6.25/12.5/50/75GHz spacing";
               }
               enum "1552.90" {
                 description "1552.90 nm/193.053125 THz 3.125GHz spacing";
               }
               enum "1552.88" {
                 description "1552.88 nm/193.056250 THz 3.125/6.25GHz spacing";
               }
               enum "1552.85" {
                 description "1552.85 nm/193.059375 THz 3.125GHz spacing";
               }
               enum "1552.83" {
                 description "1552.83 nm/193.062500 THz 3.125/6.25/12.5GHz spacing";
               }
               enum "1552.80" {
                 description "1552.80 nm/193.065625 THz 3.125GHz spacing";
               }
               enum "1552.78" {
                 description "1552.78 nm/193.068750 THz 3.125/6.25GHz spacing";
               }
               enum "1552.75" {
                 description "1552.75 nm/193.071875 THz 3.125GHz spacing";
               }
               enum "1552.73" {
                 description "1552.73 nm/193.075000 THz 3.125/6.25/12.5GHz spacing";
               }
               enum "1552.70" {
                 description "1552.70 nm/193.078125 THz 3.125GHz spacing";
               }
               enum "1552.68" {
                 description "1552.68 nm/193.081250 THz 3.125/6.25GHz spacing";
               }
               enum "1552.65" {
                 description "1552.65 nm/193.084375 THz 3.125GHz spacing";
               }
               enum "1552.62" {
                 description "1552.62 nm/193.087500 THz 3.125/6.25/12.5GHz spacing";
               }
               enum "1552.60" {
                 description "1552.60 nm/193.090625 THz 3.125GHz spacing";
               }
               enum "1552.57" {
                 description "1552.57 nm/193.093750 THz 3.125/6.25GHz spacing";
               }
               enum "1552.55" {
                 description "1552.55 nm/193.096875 THz 3.125GHz spacing";
               }
               enum "1552.52" {
                 description "1552.52 nm/193.100000 THz 3.125/6.25/12.5/100GHz spacing";
               }
               enum "1552.50" {
                 description "1552.50 nm/193.103125 THz 3.125GHz spacing";
               }
               enum "1552.47" {
                 description "1552.47 nm/193.106250 THz 3.125/6.25GHz spacing";
               }
               enum "1552.45" {
                 description "1552.45 nm/193.109375 THz 3.125GHz spacing";
               }
               enum "1552.42" {
                 description "1552.42 nm/193.112500 THz 3.125/6.25/12.5GHz spacing";
               }
               enum "1552.40" {
                 description "1552.40 nm/193.115625 THz 3.125GHz spacing";
               }
               enum "1552.37" {
                 description "1552.37 nm/193.118750 THz 3.125/6.25GHz spacing";
               }
               enum "1552.35" {
                 description "1552.35 nm/193.121875 THz 3.125GHz spacing";
               }
               enum "1552.32" {
                 description "1552.32 nm/193.125000 THz 3.125/6.25/12.5/75GHz spacing";
               }
               enum "1552.30" {
                 description "1552.30 nm/193.128125 THz 3.125GHz spacing";
               }
               enum "1552.27" {
                 description "1552.27 nm/193.131250 THz 3.125/6.25GHz spacing";
               }
               enum "1552.25" {
                 description "1552.25 nm/193.134375 THz 3.125GHz spacing";
               }
               enum "1552.22" {
                 description "1552.22 nm/193.137500 THz 3.125/6.25/12.5GHz spacing";
               }
               enum "1552.20" {
                 description "1552.20 nm/193.140625 THz 3.125GHz spacing";
               }
               enum "1552.17" {
                 description "1552.17 nm/193.143750 THz 3.125/6.25GHz spacing";
               }
               enum "1552.15" {
                 description "1552.15 nm/193.146875 THz 3.125GHz spacing";
               }
               enum "1552.12" {
                 description "1552.12 nm/193.150000 THz 3.125/6.25/12.5/50GHz spacing";
               }
               enum "1552.10" {
                 description "1552.10 nm/193.153125 THz 3.125GHz spacing";
               }
               enum "1552.07" {
                 description "1552.07 nm/193.156250 THz 3.125/6.25GHz spacing";
               }
               enum "1552.05" {
                 description "1552.05 nm/193.159375 THz 3.125GHz spacing";
               }
               enum "1552.02" {
                 description "1552.02 nm/193.162500 THz 3.125/6.25/12.5GHz spacing";
               }
               enum "1552.00" {
                 description "1552.00 nm/193.165625 THz 3.125GHz spacing";
               }
               enum "1551.97" {
                 description "1551.97 nm/193.168750 THz 3.125/6.25GHz spacing";
               }
               enum "1551.95" {
                 description "1551.95 nm/193.171875 THz 3.125GHz spacing";
               }
               enum "1551.92" {
                 description "1551.92 nm/193.175000 THz 3.125/6.25/12.5GHz spacing";
               }
               enum "1551.90" {
                 description "1551.90 nm/193.178125 THz 3.125GHz spacing";
               }
               enum "1551.87" {
                 description "1551.87 nm/193.181250 THz 3.125/6.25GHz spacing";
               }
               enum "1551.85" {
                 description "1551.85 nm/193.184375 THz 3.125GHz spacing";
               }
               enum "1551.82" {
                 description "1551.82 nm/193.187500 THz 3.125/6.25/12.5GHz spacing";
               }
               enum "1551.80" {
                 description "1551.80 nm/193.190625 THz 3.125GHz spacing";
               }
               enum "1551.77" {
                 description "1551.77 nm/193.193750 THz 3.125/6.25GHz spacing";
               }
               enum "1551.75" {
                 description "1551.75 nm/193.196875 THz 3.125GHz spacing";
               }
               enum "1551.72" {
                 description "1551.72 nm/193.200000 THz 3.125/6.25/12.5/50/75/100GHz spacing";
               }
               enum "1551.70" {
                 description "1551.70 nm/193.203125 THz 3.125GHz spacing";
               }
               enum "1551.67" {
                 description "1551.67 nm/193.206250 THz 3.125/6.25GHz spacing";
               }
               enum "1551.65" {
                 description "1551.65 nm/193.209375 THz 3.125GHz spacing";
               }
               enum "1551.62" {
                 description "1551.62 nm/193.212500 THz 3.125/6.25/12.5GHz spacing";
               }
               enum "1551.60" {
                 description "1551.60 nm/193.215625 THz 3.125GHz spacing";
               }
               enum "1551.57" {
                 description "1551.57 nm/193.218750 THz 3.125/6.25GHz spacing";
               }
               enum "1551.55" {
                 description "1551.55 nm/193.221875 THz 3.125GHz spacing";
               }
               enum "1551.52" {
                 description "1551.52 nm/193.225000 THz 3.125/6.25/12.5GHz spacing";
               }
               enum "1551.49" {
                 description "1551.49 nm/193.228125 THz 3.125GHz spacing";
               }
               enum "1551.47" {
                 description "1551.47 nm/193.231250 THz 3.125/6.25GHz spacing";
               }
               enum "1551.44" {
                 description "1551.44 nm/193.234375 THz 3.125GHz spacing";
               }
               enum "1551.42" {
                 description "1551.42 nm/193.237500 THz 3.125/6.25/12.5GHz spacing";
               }
               enum "1551.39" {
                 description "1551.39 nm/193.240625 THz 3.125GHz spacing";
               }
               enum "1551.37" {
                 description "1551.37 nm/193.243750 THz 3.125/6.25GHz spacing";
               }
               enum "1551.34" {
                 description "1551.34 nm/193.246875 THz 3.125GHz spacing";
               }
               enum "1551.32" {
                 description "1551.32 nm/193.250000 THz 3.125/6.25/12.5/50GHz spacing";
               }
               enum "1551.29" {
                 description "1551.29 nm/193.253125 THz 3.125GHz spacing";
               }
               enum "1551.27" {
                 description "1551.27 nm/193.256250 THz 3.125/6.25GHz spacing";
               }
               enum "1551.24" {
                 description "1551.24 nm/193.259375 THz 3.125GHz spacing";
               }
               enum "1551.22" {
                 description "1551.22 nm/193.262500 THz 3.125/6.25/12.5GHz spacing";
               }
               enum "1551.19" {
                 description "1551.19 nm/193.265625 THz 3.125GHz spacing";
               }
               enum "1551.17" {
                 description "1551.17 nm/193.268750 THz 3.125/6.25GHz spacing";
               }
               enum "1551.14" {
                 description "1551.14 nm/193.271875 THz 3.125GHz spacing";
               }
               enum "1551.12" {
                 description "1551.12 nm/193.275000 THz 3.125/6.25/12.5/75GHz spacing";
               }
               enum "1551.09" {
                 description "1551.09 nm/193.278125 THz 3.125GHz spacing";
               }
               enum "1551.07" {
                 description "1551.07 nm/193.281250 THz 3.125/6.25GHz spacing";
               }
               enum "1551.04" {
                 description "1551.04 nm/193.284375 THz 3.125GHz spacing";
               }
               enum "1551.02" {
                 description "1551.02 nm/193.287500 THz 3.125/6.25/12.5GHz spacing";
               }
               enum "1550.99" {
                 description "1550.99 nm/193.290625 THz 3.125GHz spacing";
               }
               enum "1550.97" {
                 description "1550.97 nm/193.293750 THz 3.125/6.25GHz spacing";
               }
               enum "1550.94" {
                 description "1550.94 nm/193.296875 THz 3.125GHz spacing";
               }
               enum "1550.92" {
                 description "1550.92 nm/193.300000 THz 3.125/6.25/12.5/100GHz spacing";
               }
               enum "1550.89" {
                 description "1550.89 nm/193.303125 THz 3.125GHz spacing";
               }
               enum "1550.87" {
                 description "1550.87 nm/193.306250 THz 3.125/6.25GHz spacing";
               }
               enum "1550.84" {
                 description "1550.84 nm/193.309375 THz 3.125GHz spacing";
               }
               enum "1550.82" {
                 description "1550.82 nm/193.312500 THz 3.125/6.25/12.5GHz spacing";
               }
               enum "1550.79" {
                 description "1550.79 nm/193.315625 THz 3.125GHz spacing";
               }
               enum "1550.77" {
                 description "1550.77 nm/193.318750 THz 3.125/6.25GHz spacing";
               }
               enum "1550.74" {
                 description "1550.74 nm/193.321875 THz 3.125GHz spacing";
               }
               enum "1550.72" {
                 description "1550.72 nm/193.325000 THz 3.125/6.25/12.5GHz spacing";
               }
               enum "1550.69" {
                 description "1550.69 nm/193.328125 THz 3.125GHz spacing";
               }
               enum "1550.67" {
                 description "1550.67 nm/193.331250 THz 3.125/6.25GHz spacing";
               }
               enum "1550.64" {
                 description "1550.64 nm/193.334375 THz 3.125GHz spacing";
               }
               enum "1550.62" {
                 description "1550.62 nm/193.337500 THz 3.125/6.25/12.5GHz spacing";
               }
               enum "1550.59" {
                 description "1550.59 nm/193.340625 THz 3.125GHz spacing";
               }
               enum "1550.57" {
                 description "1550.57 nm/193.343750 THz 3.125/6.25GHz spacing";
               }
               enum "1550.54" {
                 description "1550.54 nm/193.346875 THz 3.125GHz spacing";
               }
               enum "1550.52" {
                 description "1550.52 nm/193.350000 THz 3.125/6.25/12.5/50/75GHz spacing";
               }
               enum "1550.49" {
                 description "1550.49 nm/193.353125 THz 3.125GHz spacing";
               }
               enum "1550.47" {
                 description "1550.47 nm/193.356250 THz 3.125/6.25GHz spacing";
               }
               enum "1550.44" {
                 description "1550.44 nm/193.359375 THz 3.125GHz spacing";
               }
               enum "1550.42" {
                 description "1550.42 nm/193.362500 THz 3.125/6.25/12.5GHz spacing";
               }
               enum "1550.39" {
                 description "1550.39 nm/193.365625 THz 3.125GHz spacing";
               }
               enum "1550.37" {
                 description "1550.37 nm/193.368750 THz 3.125/6.25GHz spacing";
               }
               enum "1550.34" {
                 description "1550.34 nm/193.371875 THz 3.125GHz spacing";
               }
               enum "1550.32" {
                 description "1550.32 nm/193.375000 THz 3.125/6.25/12.5GHz spacing";
               }
               enum "1550.29" {
                 description "1550.29 nm/193.378125 THz 3.125GHz spacing";
               }
               enum "1550.27" {
                 description "1550.27 nm/193.381250 THz 3.125/6.25GHz spacing";
               }
               enum "1550.24" {
                 description "1550.24 nm/193.384375 THz 3.125GHz spacing";
               }
               enum "1550.22" {
                 description "1550.22 nm/193.387500 THz 3.125/6.25/12.5GHz spacing";
               }
               enum "1550.19" {
                 description "1550.19 nm/193.390625 THz 3.125GHz spacing";
               }
               enum "1550.17" {
                 description "1550.17 nm/193.393750 THz 3.125/6.25GHz spacing";
               }
               enum "1550.14" {
                 description "1550.14 nm/193.396875 THz 3.125GHz spacing";
               }
               enum "1550.12" {
                 description "1550.12 nm/193.400000 THz 3.125/6.25/12.5/100GHz spacing";
               }
               enum "1550.09" {
                 description "1550.09 nm/193.403125 THz 3.125GHz spacing";
               }
               enum "1550.07" {
                 description "1550.07 nm/193.406250 THz 3.125/6.25GHz spacing";
               }
               enum "1550.04" {
                 description "1550.04 nm/193.409375 THz 3.125GHz spacing";
               }
               enum "1550.02" {
                 description "1550.02 nm/193.412500 THz 3.125/6.25/12.5GHz spacing";
               }
               enum "1549.99" {
                 description "1549.99 nm/193.415625 THz 3.125GHz spacing";
               }
               enum "1549.97" {
                 description "1549.97 nm/193.418750 THz 3.125/6.25GHz spacing";
               }
               enum "1549.94" {
                 description "1549.94 nm/193.421875 THz 3.125GHz spacing";
               }
               enum "1549.92" {
                 description "1549.92 nm/193.425000 THz 3.125/6.25/12.5/75GHz spacing";
               }
               enum "1549.89" {
                 description "1549.89 nm/193.428125 THz 3.125GHz spacing";
               }
               enum "1549.87" {
                 description "1549.87 nm/193.431250 THz 3.125/6.25GHz spacing";
               }
               enum "1549.84" {
                 description "1549.84 nm/193.434375 THz 3.125GHz spacing";
               }
               enum "1549.82" {
                 description "1549.82 nm/193.437500 THz 3.125/6.25/12.5GHz spacing";
               }
               enum "1549.79" {
                 description "1549.79 nm/193.440625 THz 3.125GHz spacing";
               }
               enum "1549.77" {
                 description "1549.77 nm/193.443750 THz 3.125/6.25GHz spacing";
               }
               enum "1549.74" {
                 description "1549.74 nm/193.446875 THz 3.125GHz spacing";
               }
               enum "1549.72" {
                 description "1549.72 nm/193.450000 THz 3.125/6.25/12.5/50GHz spacing";
               }
               enum "1549.69" {
                 description "1549.69 nm/193.453125 THz 3.125GHz spacing";
               }
               enum "1549.67" {
                 description "1549.67 nm/193.456250 THz 3.125/6.25GHz spacing";
               }
               enum "1549.64" {
                 description "1549.64 nm/193.459375 THz 3.125GHz spacing";
               }
               enum "1549.62" {
                 description "1549.62 nm/193.462500 THz 3.125/6.25/12.5GHz spacing";
               }
               enum "1549.59" {
                 description "1549.59 nm/193.465625 THz 3.125GHz spacing";
               }
               enum "1549.57" {
                 description "1549.57 nm/193.468750 THz 3.125/6.25GHz spacing";
               }
               enum "1549.54" {
                 description "1549.54 nm/193.471875 THz 3.125GHz spacing";
               }
               enum "1549.52" {
                 description "1549.52 nm/193.475000 THz 3.125/6.25/12.5GHz spacing";
               }
               enum "1549.49" {
                 description "1549.49 nm/193.478125 THz 3.125GHz spacing";
               }
               enum "1549.47" {
                 description "1549.47 nm/193.481250 THz 3.125/6.25GHz spacing";
               }
               enum "1549.44" {
                 description "1549.44 nm/193.484375 THz 3.125GHz spacing";
               }
               enum "1549.42" {
                 description "1549.42 nm/193.487500 THz 3.125/6.25/12.5GHz spacing";
               }
               enum "1549.39" {
                 description "1549.39 nm/193.490625 THz 3.125GHz spacing";
               }
               enum "1549.37" {
                 description "1549.37 nm/193.493750 THz 3.125/6.25GHz spacing";
               }
               enum "1549.34" {
                 description "1549.34 nm/193.496875 THz 3.125GHz spacing";
               }
               enum "1549.32" {
                 description "1549.32 nm/193.500000 THz 3.125/6.25/12.5/50/75/100GHz spacing";
               }
               enum "1549.29" {
                 description "1549.29 nm/193.503125 THz 3.125GHz spacing";
               }
               enum "1549.26" {
                 description "1549.26 nm/193.506250 THz 3.125/6.25GHz spacing";
               }
               enum "1549.24" {
                 description "1549.24 nm/193.509375 THz 3.125GHz spacing";
               }
               enum "1549.21" {
                 description "1549.21 nm/193.512500 THz 3.125/6.25/12.5GHz spacing";
               }
               enum "1549.19" {
                 description "1549.19 nm/193.515625 THz 3.125GHz spacing";
               }
               enum "1549.16" {
                 description "1549.16 nm/193.518750 THz 3.125/6.25GHz spacing";
               }
               enum "1549.14" {
                 description "1549.14 nm/193.521875 THz 3.125GHz spacing";
               }
               enum "1549.11" {
                 description "1549.11 nm/193.525000 THz 3.125/6.25/12.5GHz spacing";
               }
               enum "1549.09" {
                 description "1549.09 nm/193.528125 THz 3.125GHz spacing";
               }
               enum "1549.06" {
                 description "1549.06 nm/193.531250 THz 3.125/6.25GHz spacing";
               }
               enum "1549.04" {
                 description "1549.04 nm/193.534375 THz 3.125GHz spacing";
               }
               enum "1549.01" {
                 description "1549.01 nm/193.537500 THz 3.125/6.25/12.5GHz spacing";
               }
               enum "1548.99" {
                 description "1548.99 nm/193.540625 THz 3.125GHz spacing";
               }
               enum "1548.96" {
                 description "1548.96 nm/193.543750 THz 3.125/6.25GHz spacing";
               }
               enum "1548.94" {
                 description "1548.94 nm/193.546875 THz 3.125GHz spacing";
               }
               enum "1548.91" {
                 description "1548.91 nm/193.550000 THz 3.125/6.25/12.5/50GHz spacing";
               }
               enum "1548.89" {
                 description "1548.89 nm/193.553125 THz 3.125GHz spacing";
               }
               enum "1548.86" {
                 description "1548.86 nm/193.556250 THz 3.125/6.25GHz spacing";
               }
               enum "1548.84" {
                 description "1548.84 nm/193.559375 THz 3.125GHz spacing";
               }
               enum "1548.81" {
                 description "1548.81 nm/193.562500 THz 3.125/6.25/12.5GHz spacing";
               }
               enum "1548.79" {
                 description "1548.79 nm/193.565625 THz 3.125GHz spacing";
               }
               enum "1548.76" {
                 description "1548.76 nm/193.568750 THz 3.125/6.25GHz spacing";
               }
               enum "1548.74" {
                 description "1548.74 nm/193.571875 THz 3.125GHz spacing";
               }
               enum "1548.71" {
                 description "1548.71 nm/193.575000 THz 3.125/6.25/12.5/75GHz spacing";
               }
               enum "1548.69" {
                 description "1548.69 nm/193.578125 THz 3.125GHz spacing";
               }
               enum "1548.66" {
                 description "1548.66 nm/193.581250 THz 3.125/6.25GHz spacing";
               }
               enum "1548.64" {
                 description "1548.64 nm/193.584375 THz 3.125GHz spacing";
               }
               enum "1548.61" {
                 description "1548.61 nm/193.587500 THz 3.125/6.25/12.5GHz spacing";
               }
               enum "1548.59" {
                 description "1548.59 nm/193.590625 THz 3.125GHz spacing";
               }
               enum "1548.56" {
                 description "1548.56 nm/193.593750 THz 3.125/6.25GHz spacing";
               }
               enum "1548.54" {
                 description "1548.54 nm/193.596875 THz 3.125GHz spacing";
               }
               enum "1548.51" {
                 description "1548.51 nm/193.600000 THz 3.125/6.25/12.5/100GHz spacing";
               }
               enum "1548.49" {
                 description "1548.49 nm/193.603125 THz 3.125GHz spacing";
               }
               enum "1548.46" {
                 description "1548.46 nm/193.606250 THz 3.125/6.25GHz spacing";
               }
               enum "1548.44" {
                 description "1548.44 nm/193.609375 THz 3.125GHz spacing";
               }
               enum "1548.41" {
                 description "1548.41 nm/193.612500 THz 3.125/6.25/12.5GHz spacing";
               }
               enum "1548.39" {
                 description "1548.39 nm/193.615625 THz 3.125GHz spacing";
               }
               enum "1548.36" {
                 description "1548.36 nm/193.618750 THz 3.125/6.25GHz spacing";
               }
               enum "1548.34" {
                 description "1548.34 nm/193.621875 THz 3.125GHz spacing";
               }
               enum "1548.31" {
                 description "1548.31 nm/193.625000 THz 3.125/6.25/12.5GHz spacing";
               }
               enum "1548.29" {
                 description "1548.29 nm/193.628125 THz 3.125GHz spacing";
               }
               enum "1548.26" {
                 description "1548.26 nm/193.631250 THz 3.125/6.25GHz spacing";
               }
               enum "1548.24" {
                 description "1548.24 nm/193.634375 THz 3.125GHz spacing";
               }
               enum "1548.21" {
                 description "1548.21 nm/193.637500 THz 3.125/6.25/12.5GHz spacing";
               }
               enum "1548.19" {
                 description "1548.19 nm/193.640625 THz 3.125GHz spacing";
               }
               enum "1548.16" {
                 description "1548.16 nm/193.643750 THz 3.125/6.25GHz spacing";
               }
               enum "1548.14" {
                 description "1548.14 nm/193.646875 THz 3.125GHz spacing";
               }
               enum "1548.11" {
                 description "1548.11 nm/193.650000 THz 3.125/6.25/12.5/50/75GHz spacing";
               }
               enum "1548.09" {
                 description "1548.09 nm/193.653125 THz 3.125GHz spacing";
               }
               enum "1548.06" {
                 description "1548.06 nm/193.656250 THz 3.125/6.25GHz spacing";
               }
               enum "1548.04" {
                 description "1548.04 nm/193.659375 THz 3.125GHz spacing";
               }
               enum "1548.02" {
                 description "1548.02 nm/193.662500 THz 3.125/6.25/12.5GHz spacing";
               }
               enum "1547.99" {
                 description "1547.99 nm/193.665625 THz 3.125GHz spacing";
               }
               enum "1547.97" {
                 description "1547.97 nm/193.668750 THz 3.125/6.25GHz spacing";
               }
               enum "1547.94" {
                 description "1547.94 nm/193.671875 THz 3.125GHz spacing";
               }
               enum "1547.92" {
                 description "1547.92 nm/193.675000 THz 3.125/6.25/12.5GHz spacing";
               }
               enum "1547.89" {
                 description "1547.89 nm/193.678125 THz 3.125GHz spacing";
               }
               enum "1547.87" {
                 description "1547.87 nm/193.681250 THz 3.125/6.25GHz spacing";
               }
               enum "1547.84" {
                 description "1547.84 nm/193.684375 THz 3.125GHz spacing";
               }
               enum "1547.82" {
                 description "1547.82 nm/193.687500 THz 3.125/6.25/12.5GHz spacing";
               }
               enum "1547.79" {
                 description "1547.79 nm/193.690625 THz 3.125GHz spacing";
               }
               enum "1547.77" {
                 description "1547.77 nm/193.693750 THz 3.125/6.25GHz spacing";
               }
               enum "1547.74" {
                 description "1547.74 nm/193.696875 THz 3.125GHz spacing";
               }
               enum "1547.72" {
                 description "1547.72 nm/193.700000 THz 3.125/6.25/12.5/100GHz spacing";
               }
               enum "1547.69" {
                 description "1547.69 nm/193.703125 THz 3.125GHz spacing";
               }
               enum "1547.67" {
                 description "1547.67 nm/193.706250 THz 3.125/6.25GHz spacing";
               }
               enum "1547.64" {
                 description "1547.64 nm/193.709375 THz 3.125GHz spacing";
               }
               enum "1547.62" {
                 description "1547.62 nm/193.712500 THz 3.125/6.25/12.5GHz spacing";
               }
               enum "1547.59" {
                 description "1547.59 nm/193.715625 THz 3.125GHz spacing";
               }
               enum "1547.57" {
                 description "1547.57 nm/193.718750 THz 3.125/6.25GHz spacing";
               }
               enum "1547.54" {
                 description "1547.54 nm/193.721875 THz 3.125GHz spacing";
               }
               enum "1547.52" {
                 description "1547.52 nm/193.725000 THz 3.125/6.25/12.5/75GHz spacing";
               }
               enum "1547.49" {
                 description "1547.49 nm/193.728125 THz 3.125GHz spacing";
               }
               enum "1547.47" {
                 description "1547.47 nm/193.731250 THz 3.125/6.25GHz spacing";
               }
               enum "1547.44" {
                 description "1547.44 nm/193.734375 THz 3.125GHz spacing";
               }
               enum "1547.42" {
                 description "1547.42 nm/193.737500 THz 3.125/6.25/12.5GHz spacing";
               }
               enum "1547.39" {
                 description "1547.39 nm/193.740625 THz 3.125GHz spacing";
               }
               enum "1547.37" {
                 description "1547.37 nm/193.743750 THz 3.125/6.25GHz spacing";
               }
               enum "1547.34" {
                 description "1547.34 nm/193.746875 THz 3.125GHz spacing";
               }
               enum "1547.32" {
                 description "1547.32 nm/193.750000 THz 3.125/6.25/12.5/50GHz spacing";
               }
               enum "1547.29" {
                 description "1547.29 nm/193.753125 THz 3.125GHz spacing";
               }
               enum "1547.27" {
                 description "1547.27 nm/193.756250 THz 3.125/6.25GHz spacing";
               }
               enum "1547.24" {
                 description "1547.24 nm/193.759375 THz 3.125GHz spacing";
               }
               enum "1547.22" {
                 description "1547.22 nm/193.762500 THz 3.125/6.25/12.5GHz spacing";
               }
               enum "1547.19" {
                 description "1547.19 nm/193.765625 THz 3.125GHz spacing";
               }
               enum "1547.17" {
                 description "1547.17 nm/193.768750 THz 3.125/6.25GHz spacing";
               }
               enum "1547.14" {
                 description "1547.14 nm/193.771875 THz 3.125GHz spacing";
               }
               enum "1547.12" {
                 description "1547.12 nm/193.775000 THz 3.125/6.25/12.5GHz spacing";
               }
               enum "1547.09" {
                 description "1547.09 nm/193.778125 THz 3.125GHz spacing";
               }
               enum "1547.07" {
                 description "1547.07 nm/193.781250 THz 3.125/6.25GHz spacing";
               }
               enum "1547.04" {
                 description "1547.04 nm/193.784375 THz 3.125GHz spacing";
               }
               enum "1547.02" {
                 description "1547.02 nm/193.787500 THz 3.125/6.25/12.5GHz spacing";
               }
               enum "1546.99" {
                 description "1546.99 nm/193.790625 THz 3.125GHz spacing";
               }
               enum "1546.97" {
                 description "1546.97 nm/193.793750 THz 3.125/6.25GHz spacing";
               }
               enum "1546.94" {
                 description "1546.94 nm/193.796875 THz 3.125GHz spacing";
               }
               enum "1546.92" {
                 description "1546.92 nm/193.800000 THz 3.125/6.25/12.5/50/75/100GHz spacing";
               }
               enum "1546.89" {
                 description "1546.89 nm/193.803125 THz 3.125GHz spacing";
               }
               enum "1546.87" {
                 description "1546.87 nm/193.806250 THz 3.125/6.25GHz spacing";
               }
               enum "1546.84" {
                 description "1546.84 nm/193.809375 THz 3.125GHz spacing";
               }
               enum "1546.82" {
                 description "1546.82 nm/193.812500 THz 3.125/6.25/12.5GHz spacing";
               }
               enum "1546.79" {
                 description "1546.79 nm/193.815625 THz 3.125GHz spacing";
               }
               enum "1546.77" {
                 description "1546.77 nm/193.818750 THz 3.125/6.25GHz spacing";
               }
               enum "1546.74" {
                 description "1546.74 nm/193.821875 THz 3.125GHz spacing";
               }
               enum "1546.72" {
                 description "1546.72 nm/193.825000 THz 3.125/6.25/12.5GHz spacing";
               }
               enum "1546.69" {
                 description "1546.69 nm/193.828125 THz 3.125GHz spacing";
               }
               enum "1546.67" {
                 description "1546.67 nm/193.831250 THz 3.125/6.25GHz spacing";
               }
               enum "1546.64" {
                 description "1546.64 nm/193.834375 THz 3.125GHz spacing";
               }
               enum "1546.62" {
                 description "1546.62 nm/193.837500 THz 3.125/6.25/12.5GHz spacing";
               }
               enum "1546.59" {
                 description "1546.59 nm/193.840625 THz 3.125GHz spacing";
               }
               enum "1546.57" {
                 description "1546.57 nm/193.843750 THz 3.125/6.25GHz spacing";
               }
               enum "1546.54" {
                 description "1546.54 nm/193.846875 THz 3.125GHz spacing";
               }
               enum "1546.52" {
                 description "1546.52 nm/193.850000 THz 3.125/6.25/12.5/50GHz spacing";
               }
               enum "1546.49" {
                 description "1546.49 nm/193.853125 THz 3.125GHz spacing";
               }
               enum "1546.47" {
                 description "1546.47 nm/193.856250 THz 3.125/6.25GHz spacing";
               }
               enum "1546.44" {
                 description "1546.44 nm/193.859375 THz 3.125GHz spacing";
               }
               enum "1546.42" {
                 description "1546.42 nm/193.862500 THz 3.125/6.25/12.5GHz spacing";
               }
               enum "1546.39" {
                 description "1546.39 nm/193.865625 THz 3.125GHz spacing";
               }
               enum "1546.37" {
                 description "1546.37 nm/193.868750 THz 3.125/6.25GHz spacing";
               }
               enum "1546.34" {
                 description "1546.34 nm/193.871875 THz 3.125GHz spacing";
               }
               enum "1546.32" {
                 description "1546.32 nm/193.875000 THz 3.125/6.25/12.5/75GHz spacing";
               }
               enum "1546.29" {
                 description "1546.29 nm/193.878125 THz 3.125GHz spacing";
               }
               enum "1546.27" {
                 description "1546.27 nm/193.881250 THz 3.125/6.25GHz spacing";
               }
               enum "1546.24" {
                 description "1546.24 nm/193.884375 THz 3.125GHz spacing";
               }
               enum "1546.22" {
                 description "1546.22 nm/193.887500 THz 3.125/6.25/12.5GHz spacing";
               }
               enum "1546.19" {
                 description "1546.19 nm/193.890625 THz 3.125GHz spacing";
               }
               enum "1546.17" {
                 description "1546.17 nm/193.893750 THz 3.125/6.25GHz spacing";
               }
               enum "1546.14" {
                 description "1546.14 nm/193.896875 THz 3.125GHz spacing";
               }
               enum "1546.12" {
                 description "1546.12 nm/193.900000 THz 3.125/6.25/12.5/100GHz spacing";
               }
               enum "1546.09" {
                 description "1546.09 nm/193.903125 THz 3.125GHz spacing";
               }
               enum "1546.07" {
                 description "1546.07 nm/193.906250 THz 3.125/6.25GHz spacing";
               }
               enum "1546.04" {
                 description "1546.04 nm/193.909375 THz 3.125GHz spacing";
               }
               enum "1546.02" {
                 description "1546.02 nm/193.912500 THz 3.125/6.25/12.5GHz spacing";
               }
               enum "1545.99" {
                 description "1545.99 nm/193.915625 THz 3.125GHz spacing";
               }
               enum "1545.97" {
                 description "1545.97 nm/193.918750 THz 3.125/6.25GHz spacing";
               }
               enum "1545.94" {
                 description "1545.94 nm/193.921875 THz 3.125GHz spacing";
               }
               enum "1545.92" {
                 description "1545.92 nm/193.925000 THz 3.125/6.25/12.5GHz spacing";
               }
               enum "1545.89" {
                 description "1545.89 nm/193.928125 THz 3.125GHz spacing";
               }
               enum "1545.87" {
                 description "1545.87 nm/193.931250 THz 3.125/6.25GHz spacing";
               }
               enum "1545.84" {
                 description "1545.84 nm/193.934375 THz 3.125GHz spacing";
               }
               enum "1545.82" {
                 description "1545.82 nm/193.937500 THz 3.125/6.25/12.5GHz spacing";
               }
               enum "1545.80" {
                 description "1545.80 nm/193.940625 THz 3.125GHz spacing";
               }
               enum "1545.77" {
                 description "1545.77 nm/193.943750 THz 3.125/6.25GHz spacing";
               }
               enum "1545.75" {
                 description "1545.75 nm/193.946875 THz 3.125GHz spacing";
               }
               enum "1545.72" {
                 description "1545.72 nm/193.950000 THz 3.125/6.25/12.5/50/75GHz spacing";
               }
               enum "1545.70" {
                 description "1545.70 nm/193.953125 THz 3.125GHz spacing";
               }
               enum "1545.67" {
                 description "1545.67 nm/193.956250 THz 3.125/6.25GHz spacing";
               }
               enum "1545.65" {
                 description "1545.65 nm/193.959375 THz 3.125GHz spacing";
               }
               enum "1545.62" {
                 description "1545.62 nm/193.962500 THz 3.125/6.25/12.5GHz spacing";
               }
               enum "1545.60" {
                 description "1545.60 nm/193.965625 THz 3.125GHz spacing";
               }
               enum "1545.57" {
                 description "1545.57 nm/193.968750 THz 3.125/6.25GHz spacing";
               }
               enum "1545.55" {
                 description "1545.55 nm/193.971875 THz 3.125GHz spacing";
               }
               enum "1545.52" {
                 description "1545.52 nm/193.975000 THz 3.125/6.25/12.5GHz spacing";
               }
               enum "1545.50" {
                 description "1545.50 nm/193.978125 THz 3.125GHz spacing";
               }
               enum "1545.47" {
                 description "1545.47 nm/193.981250 THz 3.125/6.25GHz spacing";
               }
               enum "1545.45" {
                 description "1545.45 nm/193.984375 THz 3.125GHz spacing";
               }
               enum "1545.42" {
                 description "1545.42 nm/193.987500 THz 3.125/6.25/12.5GHz spacing";
               }
               enum "1545.40" {
                 description "1545.40 nm/193.990625 THz 3.125GHz spacing";
               }
               enum "1545.37" {
                 description "1545.37 nm/193.993750 THz 3.125/6.25GHz spacing";
               }
               enum "1545.35" {
                 description "1545.35 nm/193.996875 THz 3.125GHz spacing";
               }
               enum "1545.32" {
                 description "1545.32 nm/194.000000 THz 3.125/6.25/12.5/100GHz spacing";
               }
               enum "1545.30" {
                 description "1545.30 nm/194.003125 THz 3.125GHz spacing";
               }
               enum "1545.27" {
                 description "1545.27 nm/194.006250 THz 3.125/6.25GHz spacing";
               }
               enum "1545.25" {
                 description "1545.25 nm/194.009375 THz 3.125GHz spacing";
               }
               enum "1545.22" {
                 description "1545.22 nm/194.012500 THz 3.125/6.25/12.5GHz spacing";
               }
               enum "1545.20" {
                 description "1545.20 nm/194.015625 THz 3.125GHz spacing";
               }
               enum "1545.17" {
                 description "1545.17 nm/194.018750 THz 3.125/6.25GHz spacing";
               }
               enum "1545.15" {
                 description "1545.15 nm/194.021875 THz 3.125GHz spacing";
               }
               enum "1545.12" {
                 description "1545.12 nm/194.025000 THz 3.125/6.25/12.5/75GHz spacing";
               }
               enum "1545.10" {
                 description "1545.10 nm/194.028125 THz 3.125GHz spacing";
               }
               enum "1545.07" {
                 description "1545.07 nm/194.031250 THz 3.125/6.25GHz spacing";
               }
               enum "1545.05" {
                 description "1545.05 nm/194.034375 THz 3.125GHz spacing";
               }
               enum "1545.02" {
                 description "1545.02 nm/194.037500 THz 3.125/6.25/12.5GHz spacing";
               }
               enum "1545.00" {
                 description "1545.00 nm/194.040625 THz 3.125GHz spacing";
               }
               enum "1544.97" {
                 description "1544.97 nm/194.043750 THz 3.125/6.25GHz spacing";
               }
               enum "1544.95" {
                 description "1544.95 nm/194.046875 THz 3.125GHz spacing";
               }
               enum "1544.92" {
                 description "1544.92 nm/194.050000 THz 3.125/6.25/12.5/50GHz spacing";
               }
               enum "1544.90" {
                 description "1544.90 nm/194.053125 THz 3.125GHz spacing";
               }
               enum "1544.87" {
                 description "1544.87 nm/194.056250 THz 3.125/6.25GHz spacing";
               }
               enum "1544.85" {
                 description "1544.85 nm/194.059375 THz 3.125GHz spacing";
               }
               enum "1544.82" {
                 description "1544.82 nm/194.062500 THz 3.125/6.25/12.5GHz spacing";
               }
               enum "1544.80" {
                 description "1544.80 nm/194.065625 THz 3.125GHz spacing";
               }
               enum "1544.77" {
                 description "1544.77 nm/194.068750 THz 3.125/6.25GHz spacing";
               }
               enum "1544.75" {
                 description "1544.75 nm/194.071875 THz 3.125GHz spacing";
               }
               enum "1544.72" {
                 description "1544.72 nm/194.075000 THz 3.125/6.25/12.5GHz spacing";
               }
               enum "1544.70" {
                 description "1544.70 nm/194.078125 THz 3.125GHz spacing";
               }
               enum "1544.68" {
                 description "1544.68 nm/194.081250 THz 3.125/6.25GHz spacing";
               }
               enum "1544.65" {
                 description "1544.65 nm/194.084375 THz 3.125GHz spacing";
               }
               enum "1544.63" {
                 description "1544.63 nm/194.087500 THz 3.125/6.25/12.5GHz spacing";
               }
               enum "1544.60" {
                 description "1544.60 nm/194.090625 THz 3.125GHz spacing";
               }
               enum "1544.58" {
                 description "1544.58 nm/194.093750 THz 3.125/6.25GHz spacing";
               }
               enum "1544.55" {
                 description "1544.55 nm/194.096875 THz 3.125GHz spacing";
               }
               enum "1544.53" {
                 description "1544.53 nm/194.100000 THz 3.125/6.25/12.5/50/75/100GHz spacing";
               }
               enum "1544.50" {
                 description "1544.50 nm/194.103125 THz 3.125GHz spacing";
               }
               enum "1544.48" {
                 description "1544.48 nm/194.106250 THz 3.125/6.25GHz spacing";
               }
               enum "1544.45" {
                 description "1544.45 nm/194.109375 THz 3.125GHz spacing";
               }
               enum "1544.43" {
                 description "1544.43 nm/194.112500 THz 3.125/6.25/12.5GHz spacing";
               }
               enum "1544.40" {
                 description "1544.40 nm/194.115625 THz 3.125GHz spacing";
               }
               enum "1544.38" {
                 description "1544.38 nm/194.118750 THz 3.125/6.25GHz spacing";
               }
               enum "1544.35" {
                 description "1544.35 nm/194.121875 THz 3.125GHz spacing";
               }
               enum "1544.33" {
                 description "1544.33 nm/194.125000 THz 3.125/6.25/12.5GHz spacing";
               }
               enum "1544.30" {
                 description "1544.30 nm/194.128125 THz 3.125GHz spacing";
               }
               enum "1544.28" {
                 description "1544.28 nm/194.131250 THz 3.125/6.25GHz spacing";
               }
               enum "1544.25" {
                 description "1544.25 nm/194.134375 THz 3.125GHz spacing";
               }
               enum "1544.23" {
                 description "1544.23 nm/194.137500 THz 3.125/6.25/12.5GHz spacing";
               }
               enum "1544.20" {
                 description "1544.20 nm/194.140625 THz 3.125GHz spacing";
               }
               enum "1544.18" {
                 description "1544.18 nm/194.143750 THz 3.125/6.25GHz spacing";
               }
               enum "1544.15" {
                 description "1544.15 nm/194.146875 THz 3.125GHz spacing";
               }
               enum "1544.13" {
                 description "1544.13 nm/194.150000 THz 3.125/6.25/12.5/50GHz spacing";
               }
               enum "1544.10" {
                 description "1544.10 nm/194.153125 THz 3.125GHz spacing";
               }
               enum "1544.08" {
                 description "1544.08 nm/194.156250 THz 3.125/6.25GHz spacing";
               }
               enum "1544.05" {
                 description "1544.05 nm/194.159375 THz 3.125GHz spacing";
               }
               enum "1544.03" {
                 description "1544.03 nm/194.162500 THz 3.125/6.25/12.5GHz spacing";
               }
               enum "1544.00" {
                 description "1544.00 nm/194.165625 THz 3.125GHz spacing";
               }
               enum "1543.98" {
                 description "1543.98 nm/194.168750 THz 3.125/6.25GHz spacing";
               }
               enum "1543.95" {
                 description "1543.95 nm/194.171875 THz 3.125GHz spacing";
               }
               enum "1543.93" {
                 description "1543.93 nm/194.175000 THz 3.125/6.25/12.5/75GHz spacing";
               }
               enum "1543.90" {
                 description "1543.90 nm/194.178125 THz 3.125GHz spacing";
               }
               enum "1543.88" {
                 description "1543.88 nm/194.181250 THz 3.125/6.25GHz spacing";
               }
               enum "1543.85" {
                 description "1543.85 nm/194.184375 THz 3.125GHz spacing";
               }
               enum "1543.83" {
                 description "1543.83 nm/194.187500 THz 3.125/6.25/12.5GHz spacing";
               }
               enum "1543.81" {
                 description "1543.81 nm/194.190625 THz 3.125GHz spacing";
               }
               enum "1543.78" {
                 description "1543.78 nm/194.193750 THz 3.125/6.25GHz spacing";
               }
               enum "1543.76" {
                 description "1543.76 nm/194.196875 THz 3.125GHz spacing";
               }
               enum "1543.73" {
                 description "1543.73 nm/194.200000 THz 3.125/6.25/12.5/100GHz spacing";
               }
               enum "1543.71" {
                 description "1543.71 nm/194.203125 THz 3.125GHz spacing";
               }
               enum "1543.68" {
                 description "1543.68 nm/194.206250 THz 3.125/6.25GHz spacing";
               }
               enum "1543.66" {
                 description "1543.66 nm/194.209375 THz 3.125GHz spacing";
               }
               enum "1543.63" {
                 description "1543.63 nm/194.212500 THz 3.125/6.25/12.5GHz spacing";
               }
               enum "1543.61" {
                 description "1543.61 nm/194.215625 THz 3.125GHz spacing";
               }
               enum "1543.58" {
                 description "1543.58 nm/194.218750 THz 3.125/6.25GHz spacing";
               }
               enum "1543.56" {
                 description "1543.56 nm/194.221875 THz 3.125GHz spacing";
               }
               enum "1543.53" {
                 description "1543.53 nm/194.225000 THz 3.125/6.25/12.5GHz spacing";
               }
               enum "1543.51" {
                 description "1543.51 nm/194.228125 THz 3.125GHz spacing";
               }
               enum "1543.48" {
                 description "1543.48 nm/194.231250 THz 3.125/6.25GHz spacing";
               }
               enum "1543.46" {
                 description "1543.46 nm/194.234375 THz 3.125GHz spacing";
               }
               enum "1543.43" {
                 description "1543.43 nm/194.237500 THz 3.125/6.25/12.5GHz spacing";
               }
               enum "1543.41" {
                 description "1543.41 nm/194.240625 THz 3.125GHz spacing";
               }
               enum "1543.38" {
                 description "1543.38 nm/194.243750 THz 3.125/6.25GHz spacing";
               }
               enum "1543.36" {
                 description "1543.36 nm/194.246875 THz 3.125GHz spacing";
               }
               enum "1543.33" {
                 description "1543.33 nm/194.250000 THz 3.125/6.25/12.5/50/75GHz spacing";
               }
               enum "1543.31" {
                 description "1543.31 nm/194.253125 THz 3.125GHz spacing";
               }
               enum "1543.28" {
                 description "1543.28 nm/194.256250 THz 3.125/6.25GHz spacing";
               }
               enum "1543.26" {
                 description "1543.26 nm/194.259375 THz 3.125GHz spacing";
               }
               enum "1543.23" {
                 description "1543.23 nm/194.262500 THz 3.125/6.25/12.5GHz spacing";
               }
               enum "1543.21" {
                 description "1543.21 nm/194.265625 THz 3.125GHz spacing";
               }
               enum "1543.18" {
                 description "1543.18 nm/194.268750 THz 3.125/6.25GHz spacing";
               }
               enum "1543.16" {
                 description "1543.16 nm/194.271875 THz 3.125GHz spacing";
               }
               enum "1543.13" {
                 description "1543.13 nm/194.275000 THz 3.125/6.25/12.5GHz spacing";
               }
               enum "1543.11" {
                 description "1543.11 nm/194.278125 THz 3.125GHz spacing";
               }
               enum "1543.08" {
                 description "1543.08 nm/194.281250 THz 3.125/6.25GHz spacing";
               }
               enum "1543.06" {
                 description "1543.06 nm/194.284375 THz 3.125GHz spacing";
               }
               enum "1543.04" {
                 description "1543.04 nm/194.287500 THz 3.125/6.25/12.5GHz spacing";
               }
               enum "1543.01" {
                 description "1543.01 nm/194.290625 THz 3.125GHz spacing";
               }
               enum "1542.99" {
                 description "1542.99 nm/194.293750 THz 3.125/6.25GHz spacing";
               }
               enum "1542.96" {
                 description "1542.96 nm/194.296875 THz 3.125GHz spacing";
               }
               enum "1542.94" {
                 description "1542.94 nm/194.300000 THz 3.125/6.25/12.5/100GHz spacing";
               }
               enum "1542.91" {
                 description "1542.91 nm/194.303125 THz 3.125GHz spacing";
               }
               enum "1542.89" {
                 description "1542.89 nm/194.306250 THz 3.125/6.25GHz spacing";
               }
               enum "1542.86" {
                 description "1542.86 nm/194.309375 THz 3.125GHz spacing";
               }
               enum "1542.84" {
                 description "1542.84 nm/194.312500 THz 3.125/6.25/12.5GHz spacing";
               }
               enum "1542.81" {
                 description "1542.81 nm/194.315625 THz 3.125GHz spacing";
               }
               enum "1542.79" {
                 description "1542.79 nm/194.318750 THz 3.125/6.25GHz spacing";
               }
               enum "1542.76" {
                 description "1542.76 nm/194.321875 THz 3.125GHz spacing";
               }
               enum "1542.74" {
                 description "1542.74 nm/194.325000 THz 3.125/6.25/12.5/75GHz spacing";
               }
               enum "1542.71" {
                 description "1542.71 nm/194.328125 THz 3.125GHz spacing";
               }
               enum "1542.69" {
                 description "1542.69 nm/194.331250 THz 3.125/6.25GHz spacing";
               }
               enum "1542.66" {
                 description "1542.66 nm/194.334375 THz 3.125GHz spacing";
               }
               enum "1542.64" {
                 description "1542.64 nm/194.337500 THz 3.125/6.25/12.5GHz spacing";
               }
               enum "1542.61" {
                 description "1542.61 nm/194.340625 THz 3.125GHz spacing";
               }
               enum "1542.59" {
                 description "1542.59 nm/194.343750 THz 3.125/6.25GHz spacing";
               }
               enum "1542.56" {
                 description "1542.56 nm/194.346875 THz 3.125GHz spacing";
               }
               enum "1542.54" {
                 description "1542.54 nm/194.350000 THz 3.125/6.25/12.5/50GHz spacing";
               }
               enum "1542.51" {
                 description "1542.51 nm/194.353125 THz 3.125GHz spacing";
               }
               enum "1542.49" {
                 description "1542.49 nm/194.356250 THz 3.125/6.25GHz spacing";
               }
               enum "1542.46" {
                 description "1542.46 nm/194.359375 THz 3.125GHz spacing";
               }
               enum "1542.44" {
                 description "1542.44 nm/194.362500 THz 3.125/6.25/12.5GHz spacing";
               }
               enum "1542.42" {
                 description "1542.42 nm/194.365625 THz 3.125GHz spacing";
               }
               enum "1542.39" {
                 description "1542.39 nm/194.368750 THz 3.125/6.25GHz spacing";
               }
               enum "1542.37" {
                 description "1542.37 nm/194.371875 THz 3.125GHz spacing";
               }
               enum "1542.34" {
                 description "1542.34 nm/194.375000 THz 3.125/6.25/12.5GHz spacing";
               }
               enum "1542.32" {
                 description "1542.32 nm/194.378125 THz 3.125GHz spacing";
               }
               enum "1542.29" {
                 description "1542.29 nm/194.381250 THz 3.125/6.25GHz spacing";
               }
               enum "1542.27" {
                 description "1542.27 nm/194.384375 THz 3.125GHz spacing";
               }
               enum "1542.24" {
                 description "1542.24 nm/194.387500 THz 3.125/6.25/12.5GHz spacing";
               }
               enum "1542.22" {
                 description "1542.22 nm/194.390625 THz 3.125GHz spacing";
               }
               enum "1542.19" {
                 description "1542.19 nm/194.393750 THz 3.125/6.25GHz spacing";
               }
               enum "1542.17" {
                 description "1542.17 nm/194.396875 THz 3.125GHz spacing";
               }
               enum "1542.14" {
                 description "1542.14 nm/194.400000 THz 3.125/6.25/12.5/50/75/100GHz spacing";
               }
               enum "1542.12" {
                 description "1542.12 nm/194.403125 THz 3.125GHz spacing";
               }
               enum "1542.09" {
                 description "1542.09 nm/194.406250 THz 3.125/6.25GHz spacing";
               }
               enum "1542.07" {
                 description "1542.07 nm/194.409375 THz 3.125GHz spacing";
               }
               enum "1542.04" {
                 description "1542.04 nm/194.412500 THz 3.125/6.25/12.5GHz spacing";
               }
               enum "1542.02" {
                 description "1542.02 nm/194.415625 THz 3.125GHz spacing";
               }
               enum "1541.99" {
                 description "1541.99 nm/194.418750 THz 3.125/6.25GHz spacing";
               }
               enum "1541.97" {
                 description "1541.97 nm/194.421875 THz 3.125GHz spacing";
               }
               enum "1541.94" {
                 description "1541.94 nm/194.425000 THz 3.125/6.25/12.5GHz spacing";
               }
               enum "1541.92" {
                 description "1541.92 nm/194.428125 THz 3.125GHz spacing";
               }
               enum "1541.89" {
                 description "1541.89 nm/194.431250 THz 3.125/6.25GHz spacing";
               }
               enum "1541.87" {
                 description "1541.87 nm/194.434375 THz 3.125GHz spacing";
               }
               enum "1541.84" {
                 description "1541.84 nm/194.437500 THz 3.125/6.25/12.5GHz spacing";
               }
               enum "1541.82" {
                 description "1541.82 nm/194.440625 THz 3.125GHz spacing";
               }
               enum "1541.80" {
                 description "1541.80 nm/194.443750 THz 3.125/6.25GHz spacing";
               }
               enum "1541.77" {
                 description "1541.77 nm/194.446875 THz 3.125GHz spacing";
               }
               enum "1541.75" {
                 description "1541.75 nm/194.450000 THz 3.125/6.25/12.5/50GHz spacing";
               }
               enum "1541.72" {
                 description "1541.72 nm/194.453125 THz 3.125GHz spacing";
               }
               enum "1541.70" {
                 description "1541.70 nm/194.456250 THz 3.125/6.25GHz spacing";
               }
               enum "1541.67" {
                 description "1541.67 nm/194.459375 THz 3.125GHz spacing";
               }
               enum "1541.65" {
                 description "1541.65 nm/194.462500 THz 3.125/6.25/12.5GHz spacing";
               }
               enum "1541.62" {
                 description "1541.62 nm/194.465625 THz 3.125GHz spacing";
               }
               enum "1541.60" {
                 description "1541.60 nm/194.468750 THz 3.125/6.25GHz spacing";
               }
               enum "1541.57" {
                 description "1541.57 nm/194.471875 THz 3.125GHz spacing";
               }
               enum "1541.55" {
                 description "1541.55 nm/194.475000 THz 3.125/6.25/12.5/75GHz spacing";
               }
               enum "1541.52" {
                 description "1541.52 nm/194.478125 THz 3.125GHz spacing";
               }
               enum "1541.50" {
                 description "1541.50 nm/194.481250 THz 3.125/6.25GHz spacing";
               }
               enum "1541.47" {
                 description "1541.47 nm/194.484375 THz 3.125GHz spacing";
               }
               enum "1541.45" {
                 description "1541.45 nm/194.487500 THz 3.125/6.25/12.5GHz spacing";
               }
               enum "1541.42" {
                 description "1541.42 nm/194.490625 THz 3.125GHz spacing";
               }
               enum "1541.40" {
                 description "1541.40 nm/194.493750 THz 3.125/6.25GHz spacing";
               }
               enum "1541.37" {
                 description "1541.37 nm/194.496875 THz 3.125GHz spacing";
               }
               enum "1541.35" {
                 description "1541.35 nm/194.500000 THz 3.125/6.25/12.5/100GHz spacing";
               }
               enum "1541.32" {
                 description "1541.32 nm/194.503125 THz 3.125GHz spacing";
               }
               enum "1541.30" {
                 description "1541.30 nm/194.506250 THz 3.125/6.25GHz spacing";
               }
               enum "1541.28" {
                 description "1541.28 nm/194.509375 THz 3.125GHz spacing";
               }
               enum "1541.25" {
                 description "1541.25 nm/194.512500 THz 3.125/6.25/12.5GHz spacing";
               }
               enum "1541.23" {
                 description "1541.23 nm/194.515625 THz 3.125GHz spacing";
               }
               enum "1541.20" {
                 description "1541.20 nm/194.518750 THz 3.125/6.25GHz spacing";
               }
               enum "1541.18" {
                 description "1541.18 nm/194.521875 THz 3.125GHz spacing";
               }
               enum "1541.15" {
                 description "1541.15 nm/194.525000 THz 3.125/6.25/12.5GHz spacing";
               }
               enum "1541.13" {
                 description "1541.13 nm/194.528125 THz 3.125GHz spacing";
               }
               enum "1541.10" {
                 description "1541.10 nm/194.531250 THz 3.125/6.25GHz spacing";
               }
               enum "1541.08" {
                 description "1541.08 nm/194.534375 THz 3.125GHz spacing";
               }
               enum "1541.05" {
                 description "1541.05 nm/194.537500 THz 3.125/6.25/12.5GHz spacing";
               }
               enum "1541.03" {
                 description "1541.03 nm/194.540625 THz 3.125GHz spacing";
               }
               enum "1541.00" {
                 description "1541.00 nm/194.543750 THz 3.125/6.25GHz spacing";
               }
               enum "1540.98" {
                 description "1540.98 nm/194.546875 THz 3.125GHz spacing";
               }
               enum "1540.95" {
                 description "1540.95 nm/194.550000 THz 3.125/6.25/12.5/50/75GHz spacing";
               }
               enum "1540.93" {
                 description "1540.93 nm/194.553125 THz 3.125GHz spacing";
               }
               enum "1540.90" {
                 description "1540.90 nm/194.556250 THz 3.125/6.25GHz spacing";
               }
               enum "1540.88" {
                 description "1540.88 nm/194.559375 THz 3.125GHz spacing";
               }
               enum "1540.85" {
                 description "1540.85 nm/194.562500 THz 3.125/6.25/12.5GHz spacing";
               }
               enum "1540.83" {
                 description "1540.83 nm/194.565625 THz 3.125GHz spacing";
               }
               enum "1540.80" {
                 description "1540.80 nm/194.568750 THz 3.125/6.25GHz spacing";
               }
               enum "1540.78" {
                 description "1540.78 nm/194.571875 THz 3.125GHz spacing";
               }
               enum "1540.76" {
                 description "1540.76 nm/194.575000 THz 3.125/6.25/12.5GHz spacing";
               }
               enum "1540.73" {
                 description "1540.73 nm/194.578125 THz 3.125GHz spacing";
               }
               enum "1540.71" {
                 description "1540.71 nm/194.581250 THz 3.125/6.25GHz spacing";
               }
               enum "1540.68" {
                 description "1540.68 nm/194.584375 THz 3.125GHz spacing";
               }
               enum "1540.66" {
                 description "1540.66 nm/194.587500 THz 3.125/6.25/12.5GHz spacing";
               }
               enum "1540.63" {
                 description "1540.63 nm/194.590625 THz 3.125GHz spacing";
               }
               enum "1540.61" {
                 description "1540.61 nm/194.593750 THz 3.125/6.25GHz spacing";
               }
               enum "1540.58" {
                 description "1540.58 nm/194.596875 THz 3.125GHz spacing";
               }
               enum "1540.56" {
                 description "1540.56 nm/194.600000 THz 3.125/6.25/12.5/100GHz spacing";
               }
               enum "1540.53" {
                 description "1540.53 nm/194.603125 THz 3.125GHz spacing";
               }
               enum "1540.51" {
                 description "1540.51 nm/194.606250 THz 3.125/6.25GHz spacing";
               }
               enum "1540.48" {
                 description "1540.48 nm/194.609375 THz 3.125GHz spacing";
               }
               enum "1540.46" {
                 description "1540.46 nm/194.612500 THz 3.125/6.25/12.5GHz spacing";
               }
               enum "1540.43" {
                 description "1540.43 nm/194.615625 THz 3.125GHz spacing";
               }
               enum "1540.41" {
                 description "1540.41 nm/194.618750 THz 3.125/6.25GHz spacing";
               }
               enum "1540.38" {
                 description "1540.38 nm/194.621875 THz 3.125GHz spacing";
               }
               enum "1540.36" {
                 description "1540.36 nm/194.625000 THz 3.125/6.25/12.5/75GHz spacing";
               }
               enum "1540.33" {
                 description "1540.33 nm/194.628125 THz 3.125GHz spacing";
               }
               enum "1540.31" {
                 description "1540.31 nm/194.631250 THz 3.125/6.25GHz spacing";
               }
               enum "1540.29" {
                 description "1540.29 nm/194.634375 THz 3.125GHz spacing";
               }
               enum "1540.26" {
                 description "1540.26 nm/194.637500 THz 3.125/6.25/12.5GHz spacing";
               }
               enum "1540.24" {
                 description "1540.24 nm/194.640625 THz 3.125GHz spacing";
               }
               enum "1540.21" {
                 description "1540.21 nm/194.643750 THz 3.125/6.25GHz spacing";
               }
               enum "1540.19" {
                 description "1540.19 nm/194.646875 THz 3.125GHz spacing";
               }
               enum "1540.16" {
                 description "1540.16 nm/194.650000 THz 3.125/6.25/12.5/50GHz spacing";
               }
               enum "1540.14" {
                 description "1540.14 nm/194.653125 THz 3.125GHz spacing";
               }
               enum "1540.11" {
                 description "1540.11 nm/194.656250 THz 3.125/6.25GHz spacing";
               }
               enum "1540.09" {
                 description "1540.09 nm/194.659375 THz 3.125GHz spacing";
               }
               enum "1540.06" {
                 description "1540.06 nm/194.662500 THz 3.125/6.25/12.5GHz spacing";
               }
               enum "1540.04" {
                 description "1540.04 nm/194.665625 THz 3.125GHz spacing";
               }
               enum "1540.01" {
                 description "1540.01 nm/194.668750 THz 3.125/6.25GHz spacing";
               }
               enum "1539.99" {
                 description "1539.99 nm/194.671875 THz 3.125GHz spacing";
               }
               enum "1539.96" {
                 description "1539.96 nm/194.675000 THz 3.125/6.25/12.5/75GHz spacing";
               }
               enum "1539.94" {
                 description "1539.94 nm/194.678125 THz 3.125GHz spacing";
               }
               enum "1539.91" {
                 description "1539.91 nm/194.681250 THz 3.125/6.25GHz spacing";
               }
               enum "1539.89" {
                 description "1539.89 nm/194.684375 THz 3.125GHz spacing";
               }
               enum "1539.86" {
                 description "1539.86 nm/194.687500 THz 3.125/6.25/12.5GHz spacing";
               }
               enum "1539.84" {
                 description "1539.84 nm/194.690625 THz 3.125GHz spacing";
               }
               enum "1539.82" {
                 description "1539.82 nm/194.693750 THz 3.125/6.25GHz spacing";
               }
               enum "1539.79" {
                 description "1539.79 nm/194.696875 THz 3.125GHz spacing";
               }
               enum "1539.77" {
                 description "1539.77 nm/194.700000 THz 3.125/6.25/12.5/50/75/100GHz spacing";
               }
               enum "1539.74" {
                 description "1539.74 nm/194.703125 THz 3.125GHz spacing";
               }
               enum "1539.72" {
                 description "1539.72 nm/194.706250 THz 3.125/6.25GHz spacing";
               }
               enum "1539.69" {
                 description "1539.69 nm/194.709375 THz 3.125GHz spacing";
               }
               enum "1539.67" {
                 description "1539.67 nm/194.712500 THz 3.125/6.25/12.5GHz spacing";
               }
               enum "1539.64" {
                 description "1539.64 nm/194.715625 THz 3.125GHz spacing";
               }
               enum "1539.62" {
                 description "1539.62 nm/194.718750 THz 3.125/6.25GHz spacing";
               }
               enum "1539.59" {
                 description "1539.59 nm/194.721875 THz 3.125GHz spacing";
               }
               enum "1539.57" {
                 description "1539.57 nm/194.725000 THz 3.125/6.25/12.5GHz spacing";
               }
               enum "1539.54" {
                 description "1539.54 nm/194.728125 THz 3.125GHz spacing";
               }
               enum "1539.52" {
                 description "1539.52 nm/194.731250 THz 3.125/6.25GHz spacing";
               }
               enum "1539.49" {
                 description "1539.49 nm/194.734375 THz 3.125GHz spacing";
               }
               enum "1539.47" {
                 description "1539.47 nm/194.737500 THz 3.125/6.25/12.5GHz spacing";
               }
               enum "1539.44" {
                 description "1539.44 nm/194.740625 THz 3.125GHz spacing";
               }
               enum "1539.42" {
                 description "1539.42 nm/194.743750 THz 3.125/6.25GHz spacing";
               }
               enum "1539.40" {
                 description "1539.40 nm/194.746875 THz 3.125GHz spacing";
               }
               enum "1539.37" {
                 description "1539.37 nm/194.750000 THz 3.125/6.25/12.5/50GHz spacing";
               }
               enum "1539.35" {
                 description "1539.35 nm/194.753125 THz 3.125GHz spacing";
               }
               enum "1539.32" {
                 description "1539.32 nm/194.756250 THz 3.125/6.25GHz spacing";
               }
               enum "1539.30" {
                 description "1539.30 nm/194.759375 THz 3.125GHz spacing";
               }
               enum "1539.27" {
                 description "1539.27 nm/194.762500 THz 3.125/6.25/12.5GHz spacing";
               }
               enum "1539.25" {
                 description "1539.25 nm/194.765625 THz 3.125GHz spacing";
               }
               enum "1539.22" {
                 description "1539.22 nm/194.768750 THz 3.125/6.25GHz spacing";
               }
               enum "1539.20" {
                 description "1539.20 nm/194.771875 THz 3.125GHz spacing";
               }
               enum "1539.17" {
                 description "1539.17 nm/194.775000 THz 3.125/6.25/12.5/75GHz spacing";
               }
               enum "1539.15" {
                 description "1539.15 nm/194.778125 THz 3.125GHz spacing";
               }
               enum "1539.12" {
                 description "1539.12 nm/194.781250 THz 3.125/6.25GHz spacing";
               }
               enum "1539.10" {
                 description "1539.10 nm/194.784375 THz 3.125GHz spacing";
               }
               enum "1539.07" {
                 description "1539.07 nm/194.787500 THz 3.125/6.25/12.5GHz spacing";
               }
               enum "1539.05" {
                 description "1539.05 nm/194.790625 THz 3.125GHz spacing";
               }
               enum "1539.03" {
                 description "1539.03 nm/194.793750 THz 3.125/6.25GHz spacing";
               }
               enum "1539.00" {
                 description "1539.00 nm/194.796875 THz 3.125GHz spacing";
               }
               enum "1538.98" {
                 description "1538.98 nm/194.800000 THz 3.125/6.25/12.5/100GHz spacing";
               }
               enum "1538.95" {
                 description "1538.95 nm/194.803125 THz 3.125GHz spacing";
               }
               enum "1538.93" {
                 description "1538.93 nm/194.806250 THz 3.125/6.25GHz spacing";
               }
               enum "1538.90" {
                 description "1538.90 nm/194.809375 THz 3.125GHz spacing";
               }
               enum "1538.88" {
                 description "1538.88 nm/194.812500 THz 3.125/6.25/12.5GHz spacing";
               }
               enum "1538.85" {
                 description "1538.85 nm/194.815625 THz 3.125GHz spacing";
               }
               enum "1538.83" {
                 description "1538.83 nm/194.818750 THz 3.125/6.25GHz spacing";
               }
               enum "1538.80" {
                 description "1538.80 nm/194.821875 THz 3.125GHz spacing";
               }
               enum "1538.78" {
                 description "1538.78 nm/194.825000 THz 3.125/6.25/12.5GHz spacing";
               }
               enum "1538.75" {
                 description "1538.75 nm/194.828125 THz 3.125GHz spacing";
               }
               enum "1538.73" {
                 description "1538.73 nm/194.831250 THz 3.125/6.25GHz spacing";
               }
               enum "1538.70" {
                 description "1538.70 nm/194.834375 THz 3.125GHz spacing";
               }
               enum "1538.68" {
                 description "1538.68 nm/194.837500 THz 3.125/6.25/12.5GHz spacing";
               }
               enum "1538.65" {
                 description "1538.65 nm/194.840625 THz 3.125GHz spacing";
               }
               enum "1538.63" {
                 description "1538.63 nm/194.843750 THz 3.125/6.25GHz spacing";
               }
               enum "1538.61" {
                 description "1538.61 nm/194.846875 THz 3.125GHz spacing";
               }
               enum "1538.58" {
                 description "1538.58 nm/194.850000 THz 3.125/6.25/12.5/50/75GHz spacing";
               }
               enum "1538.56" {
                 description "1538.56 nm/194.853125 THz 3.125GHz spacing";
               }
               enum "1538.53" {
                 description "1538.53 nm/194.856250 THz 3.125/6.25GHz spacing";
               }
               enum "1538.51" {
                 description "1538.51 nm/194.859375 THz 3.125GHz spacing";
               }
               enum "1538.48" {
                 description "1538.48 nm/194.862500 THz 3.125/6.25/12.5GHz spacing";
               }
               enum "1538.46" {
                 description "1538.46 nm/194.865625 THz 3.125GHz spacing";
               }
               enum "1538.43" {
                 description "1538.43 nm/194.868750 THz 3.125/6.25GHz spacing";
               }
               enum "1538.41" {
                 description "1538.41 nm/194.871875 THz 3.125GHz spacing";
               }
               enum "1538.38" {
                 description "1538.38 nm/194.875000 THz 3.125/6.25/12.5GHz spacing";
               }
               enum "1538.36" {
                 description "1538.36 nm/194.878125 THz 3.125GHz spacing";
               }
               enum "1538.33" {
                 description "1538.33 nm/194.881250 THz 3.125/6.25GHz spacing";
               }
               enum "1538.31" {
                 description "1538.31 nm/194.884375 THz 3.125GHz spacing";
               }
               enum "1538.28" {
                 description "1538.28 nm/194.887500 THz 3.125/6.25/12.5GHz spacing";
               }
               enum "1538.26" {
                 description "1538.26 nm/194.890625 THz 3.125GHz spacing";
               }
               enum "1538.24" {
                 description "1538.24 nm/194.893750 THz 3.125/6.25GHz spacing";
               }
               enum "1538.21" {
                 description "1538.21 nm/194.896875 THz 3.125GHz spacing";
               }
               enum "1538.19" {
                 description "1538.19 nm/194.900000 THz 3.125/6.25/12.5/100GHz spacing";
               }
               enum "1538.16" {
                 description "1538.16 nm/194.903125 THz 3.125GHz spacing";
               }
               enum "1538.14" {
                 description "1538.14 nm/194.906250 THz 3.125/6.25GHz spacing";
               }
               enum "1538.11" {
                 description "1538.11 nm/194.909375 THz 3.125GHz spacing";
               }
               enum "1538.09" {
                 description "1538.09 nm/194.912500 THz 3.125/6.25/12.5GHz spacing";
               }
               enum "1538.06" {
                 description "1538.06 nm/194.915625 THz 3.125GHz spacing";
               }
               enum "1538.04" {
                 description "1538.04 nm/194.918750 THz 3.125/6.25GHz spacing";
               }
               enum "1538.01" {
                 description "1538.01 nm/194.921875 THz 3.125GHz spacing";
               }
               enum "1537.99" {
                 description "1537.99 nm/194.925000 THz 3.125/6.25/12.5/75GHz spacing";
               }
               enum "1537.96" {
                 description "1537.96 nm/194.928125 THz 3.125GHz spacing";
               }
               enum "1537.94" {
                 description "1537.94 nm/194.931250 THz 3.125/6.25GHz spacing";
               }
               enum "1537.91" {
                 description "1537.91 nm/194.934375 THz 3.125GHz spacing";
               }
               enum "1537.89" {
                 description "1537.89 nm/194.937500 THz 3.125/6.25/12.5GHz spacing";
               }
               enum "1537.87" {
                 description "1537.87 nm/194.940625 THz 3.125GHz spacing";
               }
               enum "1537.84" {
                 description "1537.84 nm/194.943750 THz 3.125/6.25GHz spacing";
               }
               enum "1537.82" {
                 description "1537.82 nm/194.946875 THz 3.125GHz spacing";
               }
               enum "1537.79" {
                 description "1537.79 nm/194.950000 THz 3.125/6.25/12.5/50GHz spacing";
               }
               enum "1537.77" {
                 description "1537.77 nm/194.953125 THz 3.125GHz spacing";
               }
               enum "1537.74" {
                 description "1537.74 nm/194.956250 THz 3.125/6.25GHz spacing";
               }
               enum "1537.72" {
                 description "1537.72 nm/194.959375 THz 3.125GHz spacing";
               }
               enum "1537.69" {
                 description "1537.69 nm/194.962500 THz 3.125/6.25/12.5GHz spacing";
               }
               enum "1537.67" {
                 description "1537.67 nm/194.965625 THz 3.125GHz spacing";
               }
               enum "1537.64" {
                 description "1537.64 nm/194.968750 THz 3.125/6.25GHz spacing";
               }
               enum "1537.62" {
                 description "1537.62 nm/194.971875 THz 3.125GHz spacing";
               }
               enum "1537.59" {
                 description "1537.59 nm/194.975000 THz 3.125/6.25/12.5GHz spacing";
               }
               enum "1537.57" {
                 description "1537.57 nm/194.978125 THz 3.125GHz spacing";
               }
               enum "1537.55" {
                 description "1537.55 nm/194.981250 THz 3.125/6.25GHz spacing";
               }
               enum "1537.52" {
                 description "1537.52 nm/194.984375 THz 3.125GHz spacing";
               }
               enum "1537.50" {
                 description "1537.50 nm/194.987500 THz 3.125/6.25/12.5GHz spacing";
               }
               enum "1537.47" {
                 description "1537.47 nm/194.990625 THz 3.125GHz spacing";
               }
               enum "1537.45" {
                 description "1537.45 nm/194.993750 THz 3.125/6.25GHz spacing";
               }
               enum "1537.42" {
                 description "1537.42 nm/194.996875 THz 3.125GHz spacing";
               }
               enum "1537.40" {
                 description "1537.40 nm/195.000000 THz 3.125/6.25/12.5/50/75/100GHz spacing";
               }
               enum "1537.37" {
                 description "1537.37 nm/195.003125 THz 3.125GHz spacing";
               }
               enum "1537.35" {
                 description "1537.35 nm/195.006250 THz 3.125/6.25GHz spacing";
               }
               enum "1537.32" {
                 description "1537.32 nm/195.009375 THz 3.125GHz spacing";
               }
               enum "1537.30" {
                 description "1537.30 nm/195.012500 THz 3.125/6.25/12.5GHz spacing";
               }
               enum "1537.27" {
                 description "1537.27 nm/195.015625 THz 3.125GHz spacing";
               }
               enum "1537.25" {
                 description "1537.25 nm/195.018750 THz 3.125/6.25GHz spacing";
               }
               enum "1537.22" {
                 description "1537.22 nm/195.021875 THz 3.125GHz spacing";
               }
               enum "1537.20" {
                 description "1537.20 nm/195.025000 THz 3.125/6.25/12.5GHz spacing";
               }
               enum "1537.18" {
                 description "1537.18 nm/195.028125 THz 3.125GHz spacing";
               }
               enum "1537.15" {
                 description "1537.15 nm/195.031250 THz 3.125/6.25GHz spacing";
               }
               enum "1537.13" {
                 description "1537.13 nm/195.034375 THz 3.125GHz spacing";
               }
               enum "1537.10" {
                 description "1537.10 nm/195.037500 THz 3.125/6.25/12.5GHz spacing";
               }
               enum "1537.08" {
                 description "1537.08 nm/195.040625 THz 3.125GHz spacing";
               }
               enum "1537.05" {
                 description "1537.05 nm/195.043750 THz 3.125/6.25GHz spacing";
               }
               enum "1537.03" {
                 description "1537.03 nm/195.046875 THz 3.125GHz spacing";
               }
               enum "1537.00" {
                 description "1537.00 nm/195.050000 THz 3.125/6.25/12.5/50GHz spacing";
               }
               enum "1536.98" {
                 description "1536.98 nm/195.053125 THz 3.125GHz spacing";
               }
               enum "1536.95" {
                 description "1536.95 nm/195.056250 THz 3.125/6.25GHz spacing";
               }
               enum "1536.93" {
                 description "1536.93 nm/195.059375 THz 3.125GHz spacing";
               }
               enum "1536.90" {
                 description "1536.90 nm/195.062500 THz 3.125/6.25/12.5GHz spacing";
               }
               enum "1536.88" {
                 description "1536.88 nm/195.065625 THz 3.125GHz spacing";
               }
               enum "1536.86" {
                 description "1536.86 nm/195.068750 THz 3.125/6.25GHz spacing";
               }
               enum "1536.83" {
                 description "1536.83 nm/195.071875 THz 3.125GHz spacing";
               }
               enum "1536.81" {
                 description "1536.81 nm/195.075000 THz 3.125/6.25/12.5/75GHz spacing";
               }
               enum "1536.78" {
                 description "1536.78 nm/195.078125 THz 3.125GHz spacing";
               }
               enum "1536.76" {
                 description "1536.76 nm/195.081250 THz 3.125/6.25GHz spacing";
               }
               enum "1536.73" {
                 description "1536.73 nm/195.084375 THz 3.125GHz spacing";
               }
               enum "1536.71" {
                 description "1536.71 nm/195.087500 THz 3.125/6.25/12.5GHz spacing";
               }
               enum "1536.68" {
                 description "1536.68 nm/195.090625 THz 3.125GHz spacing";
               }
               enum "1536.66" {
                 description "1536.66 nm/195.093750 THz 3.125/6.25GHz spacing";
               }
               enum "1536.63" {
                 description "1536.63 nm/195.096875 THz 3.125GHz spacing";
               }
               enum "1536.61" {
                 description "1536.61 nm/195.100000 THz 3.125/6.25/12.5/100GHz spacing";
               }
               enum "1536.58" {
                 description "1536.58 nm/195.103125 THz 3.125GHz spacing";
               }
               enum "1536.56" {
                 description "1536.56 nm/195.106250 THz 3.125/6.25GHz spacing";
               }
               enum "1536.54" {
                 description "1536.54 nm/195.109375 THz 3.125GHz spacing";
               }
               enum "1536.51" {
                 description "1536.51 nm/195.112500 THz 3.125/6.25/12.5GHz spacing";
               }
               enum "1536.49" {
                 description "1536.49 nm/195.115625 THz 3.125GHz spacing";
               }
               enum "1536.46" {
                 description "1536.46 nm/195.118750 THz 3.125/6.25GHz spacing";
               }
               enum "1536.44" {
                 description "1536.44 nm/195.121875 THz 3.125GHz spacing";
               }
               enum "1536.41" {
                 description "1536.41 nm/195.125000 THz 3.125/6.25/12.5GHz spacing";
               }
               enum "1536.39" {
                 description "1536.39 nm/195.128125 THz 3.125GHz spacing";
               }
               enum "1536.36" {
                 description "1536.36 nm/195.131250 THz 3.125/6.25GHz spacing";
               }
               enum "1536.34" {
                 description "1536.34 nm/195.134375 THz 3.125GHz spacing";
               }
               enum "1536.31" {
                 description "1536.31 nm/195.137500 THz 3.125/6.25/12.5GHz spacing";
               }
               enum "1536.29" {
                 description "1536.29 nm/195.140625 THz 3.125GHz spacing";
               }
               enum "1536.26" {
                 description "1536.26 nm/195.143750 THz 3.125/6.25GHz spacing";
               }
               enum "1536.24" {
                 description "1536.24 nm/195.146875 THz 3.125GHz spacing";
               }
               enum "1536.22" {
                 description "1536.22 nm/195.150000 THz 3.125/6.25/12.5/50/75GHz spacing";
               }
               enum "1536.19" {
                 description "1536.19 nm/195.153125 THz 3.125GHz spacing";
               }
               enum "1536.17" {
                 description "1536.17 nm/195.156250 THz 3.125/6.25GHz spacing";
               }
               enum "1536.14" {
                 description "1536.14 nm/195.159375 THz 3.125GHz spacing";
               }
               enum "1536.12" {
                 description "1536.12 nm/195.162500 THz 3.125/6.25/12.5GHz spacing";
               }
               enum "1536.09" {
                 description "1536.09 nm/195.165625 THz 3.125GHz spacing";
               }
               enum "1536.07" {
                 description "1536.07 nm/195.168750 THz 3.125/6.25GHz spacing";
               }
               enum "1536.04" {
                 description "1536.04 nm/195.171875 THz 3.125GHz spacing";
               }
               enum "1536.02" {
                 description "1536.02 nm/195.175000 THz 3.125/6.25/12.5GHz spacing";
               }
               enum "1535.99" {
                 description "1535.99 nm/195.178125 THz 3.125GHz spacing";
               }
               enum "1535.97" {
                 description "1535.97 nm/195.181250 THz 3.125/6.25GHz spacing";
               }
               enum "1535.94" {
                 description "1535.94 nm/195.184375 THz 3.125GHz spacing";
               }
               enum "1535.92" {
                 description "1535.92 nm/195.187500 THz 3.125/6.25/12.5GHz spacing";
               }
               enum "1535.90" {
                 description "1535.90 nm/195.190625 THz 3.125GHz spacing";
               }
               enum "1535.87" {
                 description "1535.87 nm/195.193750 THz 3.125/6.25GHz spacing";
               }
               enum "1535.85" {
                 description "1535.85 nm/195.196875 THz 3.125GHz spacing";
               }
               enum "1535.82" {
                 description "1535.82 nm/195.200000 THz 3.125/6.25/12.5/100GHz spacing";
               }
               enum "1535.80" {
                 description "1535.80 nm/195.203125 THz 3.125GHz spacing";
               }
               enum "1535.77" {
                 description "1535.77 nm/195.206250 THz 3.125/6.25GHz spacing";
               }
               enum "1535.75" {
                 description "1535.75 nm/195.209375 THz 3.125GHz spacing";
               }
               enum "1535.72" {
                 description "1535.72 nm/195.212500 THz 3.125/6.25/12.5GHz spacing";
               }
               enum "1535.70" {
                 description "1535.70 nm/195.215625 THz 3.125GHz spacing";
               }
               enum "1535.67" {
                 description "1535.67 nm/195.218750 THz 3.125/6.25GHz spacing";
               }
               enum "1535.65" {
                 description "1535.65 nm/195.221875 THz 3.125GHz spacing";
               }
               enum "1535.63" {
                 description "1535.63 nm/195.225000 THz 3.125/6.25/12.5/75GHz spacing";
               }
               enum "1535.60" {
                 description "1535.60 nm/195.228125 THz 3.125GHz spacing";
               }
               enum "1535.58" {
                 description "1535.58 nm/195.231250 THz 3.125/6.25GHz spacing";
               }
               enum "1535.55" {
                 description "1535.55 nm/195.234375 THz 3.125GHz spacing";
               }
               enum "1535.53" {
                 description "1535.53 nm/195.237500 THz 3.125/6.25/12.5GHz spacing";
               }
               enum "1535.50" {
                 description "1535.50 nm/195.240625 THz 3.125GHz spacing";
               }
               enum "1535.48" {
                 description "1535.48 nm/195.243750 THz 3.125/6.25GHz spacing";
               }
               enum "1535.45" {
                 description "1535.45 nm/195.246875 THz 3.125GHz spacing";
               }
               enum "1535.43" {
                 description "1535.43 nm/195.250000 THz 3.125/6.25/12.5/50GHz spacing";
               }
               enum "1535.40" {
                 description "1535.40 nm/195.253125 THz 3.125GHz spacing";
               }
               enum "1535.38" {
                 description "1535.38 nm/195.256250 THz 3.125/6.25GHz spacing";
               }
               enum "1535.36" {
                 description "1535.36 nm/195.259375 THz 3.125GHz spacing";
               }
               enum "1535.33" {
                 description "1535.33 nm/195.262500 THz 3.125/6.25/12.5GHz spacing";
               }
               enum "1535.31" {
                 description "1535.31 nm/195.265625 THz 3.125GHz spacing";
               }
               enum "1535.28" {
                 description "1535.28 nm/195.268750 THz 3.125/6.25GHz spacing";
               }
               enum "1535.26" {
                 description "1535.26 nm/195.271875 THz 3.125GHz spacing";
               }
               enum "1535.23" {
                 description "1535.23 nm/195.275000 THz 3.125/6.25/12.5GHz spacing";
               }
               enum "1535.21" {
                 description "1535.21 nm/195.278125 THz 3.125GHz spacing";
               }
               enum "1535.18" {
                 description "1535.18 nm/195.281250 THz 3.125/6.25GHz spacing";
               }
               enum "1535.16" {
                 description "1535.16 nm/195.284375 THz 3.125GHz spacing";
               }
               enum "1535.13" {
                 description "1535.13 nm/195.287500 THz 3.125/6.25/12.5GHz spacing";
               }
               enum "1535.11" {
                 description "1535.11 nm/195.290625 THz 3.125GHz spacing";
               }
               enum "1535.08" {
                 description "1535.08 nm/195.293750 THz 3.125/6.25GHz spacing";
               }
               enum "1535.06" {
                 description "1535.06 nm/195.296875 THz 3.125GHz spacing";
               }
               enum "1535.04" {
                 description "1535.04 nm/195.300000 THz 3.125/6.25/12.5/50/75/100GHz spacing";
               }
               enum "1535.01" {
                 description "1535.01 nm/195.303125 THz 3.125GHz spacing";
               }
               enum "1534.99" {
                 description "1534.99 nm/195.306250 THz 3.125/6.25GHz spacing";
               }
               enum "1534.96" {
                 description "1534.96 nm/195.309375 THz 3.125GHz spacing";
               }
               enum "1534.94" {
                 description "1534.94 nm/195.312500 THz 3.125/6.25/12.5GHz spacing";
               }
               enum "1534.91" {
                 description "1534.91 nm/195.315625 THz 3.125GHz spacing";
               }
               enum "1534.89" {
                 description "1534.89 nm/195.318750 THz 3.125/6.25GHz spacing";
               }
               enum "1534.86" {
                 description "1534.86 nm/195.321875 THz 3.125GHz spacing";
               }
               enum "1534.84" {
                 description "1534.84 nm/195.325000 THz 3.125/6.25/12.5GHz spacing";
               }
               enum "1534.81" {
                 description "1534.81 nm/195.328125 THz 3.125GHz spacing";
               }
               enum "1534.79" {
                 description "1534.79 nm/195.331250 THz 3.125/6.25GHz spacing";
               }
               enum "1534.77" {
                 description "1534.77 nm/195.334375 THz 3.125GHz spacing";
               }
               enum "1534.74" {
                 description "1534.74 nm/195.337500 THz 3.125/6.25/12.5GHz spacing";
               }
               enum "1534.72" {
                 description "1534.72 nm/195.340625 THz 3.125GHz spacing";
               }
               enum "1534.69" {
                 description "1534.69 nm/195.343750 THz 3.125/6.25GHz spacing";
               }
               enum "1534.67" {
                 description "1534.67 nm/195.346875 THz 3.125GHz spacing";
               }
               enum "1534.64" {
                 description "1534.64 nm/195.350000 THz 3.125/6.25/12.5/50GHz spacing";
               }
               enum "1534.62" {
                 description "1534.62 nm/195.353125 THz 3.125GHz spacing";
               }
               enum "1534.59" {
                 description "1534.59 nm/195.356250 THz 3.125/6.25GHz spacing";
               }
               enum "1534.57" {
                 description "1534.57 nm/195.359375 THz 3.125GHz spacing";
               }
               enum "1534.54" {
                 description "1534.54 nm/195.362500 THz 3.125/6.25/12.5GHz spacing";
               }
               enum "1534.52" {
                 description "1534.52 nm/195.365625 THz 3.125GHz spacing";
               }
               enum "1534.50" {
                 description "1534.50 nm/195.368750 THz 3.125/6.25GHz spacing";
               }
               enum "1534.47" {
                 description "1534.47 nm/195.371875 THz 3.125GHz spacing";
               }
               enum "1534.45" {
                 description "1534.45 nm/195.375000 THz 3.125/6.25/12.5/75GHz spacing";
               }
               enum "1534.42" {
                 description "1534.42 nm/195.378125 THz 3.125GHz spacing";
               }
               enum "1534.40" {
                 description "1534.40 nm/195.381250 THz 3.125/6.25GHz spacing";
               }
               enum "1534.37" {
                 description "1534.37 nm/195.384375 THz 3.125GHz spacing";
               }
               enum "1534.35" {
                 description "1534.35 nm/195.387500 THz 3.125/6.25/12.5GHz spacing";
               }
               enum "1534.32" {
                 description "1534.32 nm/195.390625 THz 3.125GHz spacing";
               }
               enum "1534.30" {
                 description "1534.30 nm/195.393750 THz 3.125/6.25GHz spacing";
               }
               enum "1534.27" {
                 description "1534.27 nm/195.396875 THz 3.125GHz spacing";
               }
               enum "1534.25" {
                 description "1534.25 nm/195.400000 THz 3.125/6.25/12.5/100GHz spacing";
               }
               enum "1534.23" {
                 description "1534.23 nm/195.403125 THz 3.125GHz spacing";
               }
               enum "1534.20" {
                 description "1534.20 nm/195.406250 THz 3.125/6.25GHz spacing";
               }
               enum "1534.18" {
                 description "1534.18 nm/195.409375 THz 3.125GHz spacing";
               }
               enum "1534.15" {
                 description "1534.15 nm/195.412500 THz 3.125/6.25/12.5GHz spacing";
               }
               enum "1534.13" {
                 description "1534.13 nm/195.415625 THz 3.125GHz spacing";
               }
               enum "1534.10" {
                 description "1534.10 nm/195.418750 THz 3.125/6.25GHz spacing";
               }
               enum "1534.08" {
                 description "1534.08 nm/195.421875 THz 3.125GHz spacing";
               }
               enum "1534.05" {
                 description "1534.05 nm/195.425000 THz 3.125/6.25/12.5GHz spacing";
               }
               enum "1534.03" {
                 description "1534.03 nm/195.428125 THz 3.125GHz spacing";
               }
               enum "1534.00" {
                 description "1534.00 nm/195.431250 THz 3.125/6.25GHz spacing";
               }
               enum "1533.98" {
                 description "1533.98 nm/195.434375 THz 3.125GHz spacing";
               }
               enum "1533.96" {
                 description "1533.96 nm/195.437500 THz 3.125/6.25/12.5GHz spacing";
               }
               enum "1533.93" {
                 description "1533.93 nm/195.440625 THz 3.125GHz spacing";
               }
               enum "1533.91" {
                 description "1533.91 nm/195.443750 THz 3.125/6.25GHz spacing";
               }
               enum "1533.88" {
                 description "1533.88 nm/195.446875 THz 3.125GHz spacing";
               }
               enum "1533.86" {
                 description "1533.86 nm/195.450000 THz 3.125/6.25/12.5/50/75GHz spacing";
               }
               enum "1533.83" {
                 description "1533.83 nm/195.453125 THz 3.125GHz spacing";
               }
               enum "1533.81" {
                 description "1533.81 nm/195.456250 THz 3.125/6.25GHz spacing";
               }
               enum "1533.78" {
                 description "1533.78 nm/195.459375 THz 3.125GHz spacing";
               }
               enum "1533.76" {
                 description "1533.76 nm/195.462500 THz 3.125/6.25/12.5GHz spacing";
               }
               enum "1533.73" {
                 description "1533.73 nm/195.465625 THz 3.125GHz spacing";
               }
               enum "1533.71" {
                 description "1533.71 nm/195.468750 THz 3.125/6.25GHz spacing";
               }
               enum "1533.69" {
                 description "1533.69 nm/195.471875 THz 3.125GHz spacing";
               }
               enum "1533.66" {
                 description "1533.66 nm/195.475000 THz 3.125/6.25/12.5GHz spacing";
               }
               enum "1533.64" {
                 description "1533.64 nm/195.478125 THz 3.125GHz spacing";
               }
               enum "1533.61" {
                 description "1533.61 nm/195.481250 THz 3.125/6.25GHz spacing";
               }
               enum "1533.59" {
                 description "1533.59 nm/195.484375 THz 3.125GHz spacing";
               }
               enum "1533.56" {
                 description "1533.56 nm/195.487500 THz 3.125/6.25/12.5GHz spacing";
               }
               enum "1533.54" {
                 description "1533.54 nm/195.490625 THz 3.125GHz spacing";
               }
               enum "1533.51" {
                 description "1533.51 nm/195.493750 THz 3.125/6.25GHz spacing";
               }
               enum "1533.49" {
                 description "1533.49 nm/195.496875 THz 3.125GHz spacing";
               }
               enum "1533.47" {
                 description "1533.47 nm/195.500000 THz 3.125/6.25/12.5/100GHz spacing";
               }
               enum "1533.44" {
                 description "1533.44 nm/195.503125 THz 3.125GHz spacing";
               }
               enum "1533.42" {
                 description "1533.42 nm/195.506250 THz 3.125/6.25GHz spacing";
               }
               enum "1533.39" {
                 description "1533.39 nm/195.509375 THz 3.125GHz spacing";
               }
               enum "1533.37" {
                 description "1533.37 nm/195.512500 THz 3.125/6.25/12.5GHz spacing";
               }
               enum "1533.34" {
                 description "1533.34 nm/195.515625 THz 3.125GHz spacing";
               }
               enum "1533.32" {
                 description "1533.32 nm/195.518750 THz 3.125/6.25GHz spacing";
               }
               enum "1533.29" {
                 description "1533.29 nm/195.521875 THz 3.125GHz spacing";
               }
               enum "1533.27" {
                 description "1533.27 nm/195.525000 THz 3.125/6.25/12.5/75GHz spacing";
               }
               enum "1533.24" {
                 description "1533.24 nm/195.528125 THz 3.125GHz spacing";
               }
               enum "1533.22" {
                 description "1533.22 nm/195.531250 THz 3.125/6.25GHz spacing";
               }
               enum "1533.20" {
                 description "1533.20 nm/195.534375 THz 3.125GHz spacing";
               }
               enum "1533.17" {
                 description "1533.17 nm/195.537500 THz 3.125/6.25/12.5GHz spacing";
               }
               enum "1533.15" {
                 description "1533.15 nm/195.540625 THz 3.125GHz spacing";
               }
               enum "1533.12" {
                 description "1533.12 nm/195.543750 THz 3.125/6.25GHz spacing";
               }
               enum "1533.10" {
                 description "1533.10 nm/195.546875 THz 3.125GHz spacing";
               }
               enum "1533.07" {
                 description "1533.07 nm/195.550000 THz 3.125/6.25/12.5/50GHz spacing";
               }
               enum "1533.05" {
                 description "1533.05 nm/195.553125 THz 3.125GHz spacing";
               }
               enum "1533.02" {
                 description "1533.02 nm/195.556250 THz 3.125/6.25GHz spacing";
               }
               enum "1533.00" {
                 description "1533.00 nm/195.559375 THz 3.125GHz spacing";
               }
               enum "1532.98" {
                 description "1532.98 nm/195.562500 THz 3.125/6.25/12.5GHz spacing";
               }
               enum "1532.95" {
                 description "1532.95 nm/195.565625 THz 3.125GHz spacing";
               }
               enum "1532.93" {
                 description "1532.93 nm/195.568750 THz 3.125/6.25GHz spacing";
               }
               enum "1532.90" {
                 description "1532.90 nm/195.571875 THz 3.125GHz spacing";
               }
               enum "1532.88" {
                 description "1532.88 nm/195.575000 THz 3.125/6.25/12.5GHz spacing";
               }
               enum "1532.85" {
                 description "1532.85 nm/195.578125 THz 3.125GHz spacing";
               }
               enum "1532.83" {
                 description "1532.83 nm/195.581250 THz 3.125/6.25GHz spacing";
               }
               enum "1532.80" {
                 description "1532.80 nm/195.584375 THz 3.125GHz spacing";
               }
               enum "1532.78" {
                 description "1532.78 nm/195.587500 THz 3.125/6.25/12.5GHz spacing";
               }
               enum "1532.75" {
                 description "1532.75 nm/195.590625 THz 3.125GHz spacing";
               }
               enum "1532.73" {
                 description "1532.73 nm/195.593750 THz 3.125/6.25GHz spacing";
               }
               enum "1532.71" {
                 description "1532.71 nm/195.596875 THz 3.125GHz spacing";
               }
               enum "1532.68" {
                 description "1532.68 nm/195.600000 THz 3.125/6.25/12.5/50/75/100GHz spacing";
               }
               enum "1532.66" {
                 description "1532.66 nm/195.603125 THz 3.125GHz spacing";
               }
               enum "1532.63" {
                 description "1532.63 nm/195.606250 THz 3.125/6.25GHz spacing";
               }
               enum "1532.61" {
                 description "1532.61 nm/195.609375 THz 3.125GHz spacing";
               }
               enum "1532.58" {
                 description "1532.58 nm/195.612500 THz 3.125/6.25/12.5GHz spacing";
               }
               enum "1532.56" {
                 description "1532.56 nm/195.615625 THz 3.125GHz spacing";
               }
               enum "1532.53" {
                 description "1532.53 nm/195.618750 THz 3.125/6.25GHz spacing";
               }
               enum "1532.51" {
                 description "1532.51 nm/195.621875 THz 3.125GHz spacing";
               }
               enum "1532.49" {
                 description "1532.49 nm/195.625000 THz 3.125/6.25/12.5GHz spacing";
               }
               enum "1532.46" {
                 description "1532.46 nm/195.628125 THz 3.125GHz spacing";
               }
               enum "1532.44" {
                 description "1532.44 nm/195.631250 THz 3.125/6.25GHz spacing";
               }
               enum "1532.41" {
                 description "1532.41 nm/195.634375 THz 3.125GHz spacing";
               }
               enum "1532.39" {
                 description "1532.39 nm/195.637500 THz 3.125/6.25/12.5GHz spacing";
               }
               enum "1532.36" {
                 description "1532.36 nm/195.640625 THz 3.125GHz spacing";
               }
               enum "1532.34" {
                 description "1532.34 nm/195.643750 THz 3.125/6.25GHz spacing";
               }
               enum "1532.31" {
                 description "1532.31 nm/195.646875 THz 3.125GHz spacing";
               }
               enum "1532.29" {
                 description "1532.29 nm/195.650000 THz 3.125/6.25/12.5/50GHz spacing";
               }
               enum "1532.27" {
                 description "1532.27 nm/195.653125 THz 3.125GHz spacing";
               }
               enum "1532.24" {
                 description "1532.24 nm/195.656250 THz 3.125/6.25GHz spacing";
               }
               enum "1532.22" {
                 description "1532.22 nm/195.659375 THz 3.125GHz spacing";
               }
               enum "1532.19" {
                 description "1532.19 nm/195.662500 THz 3.125/6.25/12.5GHz spacing";
               }
               enum "1532.17" {
                 description "1532.17 nm/195.665625 THz 3.125GHz spacing";
               }
               enum "1532.14" {
                 description "1532.14 nm/195.668750 THz 3.125/6.25GHz spacing";
               }
               enum "1532.12" {
                 description "1532.12 nm/195.671875 THz 3.125GHz spacing";
               }
               enum "1532.09" {
                 description "1532.09 nm/195.675000 THz 3.125/6.25/12.5/75GHz spacing";
               }
               enum "1532.07" {
                 description "1532.07 nm/195.678125 THz 3.125GHz spacing";
               }
               enum "1532.04" {
                 description "1532.04 nm/195.681250 THz 3.125/6.25GHz spacing";
               }
               enum "1532.02" {
                 description "1532.02 nm/195.684375 THz 3.125GHz spacing";
               }
               enum "1532.00" {
                 description "1532.00 nm/195.687500 THz 3.125/6.25/12.5GHz spacing";
               }
               enum "1531.97" {
                 description "1531.97 nm/195.690625 THz 3.125GHz spacing";
               }
               enum "1531.95" {
                 description "1531.95 nm/195.693750 THz 3.125/6.25GHz spacing";
               }
               enum "1531.92" {
                 description "1531.92 nm/195.696875 THz 3.125GHz spacing";
               }
               enum "1531.90" {
                 description "1531.90 nm/195.700000 THz 3.125/6.25/12.5/100GHz spacing";
               }
               enum "1531.87" {
                 description "1531.87 nm/195.703125 THz 3.125GHz spacing";
               }
               enum "1531.85" {
                 description "1531.85 nm/195.706250 THz 3.125/6.25GHz spacing";
               }
               enum "1531.82" {
                 description "1531.82 nm/195.709375 THz 3.125GHz spacing";
               }
               enum "1531.80" {
                 description "1531.80 nm/195.712500 THz 3.125/6.25/12.5GHz spacing";
               }
               enum "1531.78" {
                 description "1531.78 nm/195.715625 THz 3.125GHz spacing";
               }
               enum "1531.75" {
                 description "1531.75 nm/195.718750 THz 3.125/6.25GHz spacing";
               }
               enum "1531.73" {
                 description "1531.73 nm/195.721875 THz 3.125GHz spacing";
               }
               enum "1531.70" {
                 description "1531.70 nm/195.725000 THz 3.125/6.25/12.5GHz spacing";
               }
               enum "1531.68" {
                 description "1531.68 nm/195.728125 THz 3.125GHz spacing";
               }
               enum "1531.65" {
                 description "1531.65 nm/195.731250 THz 3.125/6.25GHz spacing";
               }
               enum "1531.63" {
                 description "1531.63 nm/195.734375 THz 3.125GHz spacing";
               }
               enum "1531.60" {
                 description "1531.60 nm/195.737500 THz 3.125/6.25/12.5GHz spacing";
               }
               enum "1531.58" {
                 description "1531.58 nm/195.740625 THz 3.125GHz spacing";
               }
               enum "1531.56" {
                 description "1531.56 nm/195.743750 THz 3.125/6.25GHz spacing";
               }
               enum "1531.53" {
                 description "1531.53 nm/195.746875 THz 3.125GHz spacing";
               }
               enum "1531.51" {
                 description "1531.51 nm/195.750000 THz 3.125/6.25/12.5/50/75GHz spacing";
               }
               enum "1531.48" {
                 description "1531.48 nm/195.753125 THz 3.125GHz spacing";
               }
               enum "1531.46" {
                 description "1531.46 nm/195.756250 THz 3.125/6.25GHz spacing";
               }
               enum "1531.43" {
                 description "1531.43 nm/195.759375 THz 3.125GHz spacing";
               }
               enum "1531.41" {
                 description "1531.41 nm/195.762500 THz 3.125/6.25/12.5GHz spacing";
               }
               enum "1531.38" {
                 description "1531.38 nm/195.765625 THz 3.125GHz spacing";
               }
               enum "1531.36" {
                 description "1531.36 nm/195.768750 THz 3.125/6.25GHz spacing";
               }
               enum "1531.34" {
                 description "1531.34 nm/195.771875 THz 3.125GHz spacing";
               }
               enum "1531.31" {
                 description "1531.31 nm/195.775000 THz 3.125/6.25/12.5GHz spacing";
               }
               enum "1531.29" {
                 description "1531.29 nm/195.778125 THz 3.125GHz spacing";
               }
               enum "1531.26" {
                 description "1531.26 nm/195.781250 THz 3.125/6.25GHz spacing";
               }
               enum "1531.24" {
                 description "1531.24 nm/195.784375 THz 3.125GHz spacing";
               }
               enum "1531.21" {
                 description "1531.21 nm/195.787500 THz 3.125/6.25/12.5GHz spacing";
               }
               enum "1531.19" {
                 description "1531.19 nm/195.790625 THz 3.125GHz spacing";
               }
               enum "1531.16" {
                 description "1531.16 nm/195.793750 THz 3.125/6.25GHz spacing";
               }
               enum "1531.14" {
                 description "1531.14 nm/195.796875 THz 3.125GHz spacing";
               }
               enum "1531.12" {
                 description "1531.12 nm/195.800000 THz 3.125/6.25/12.5/100GHz spacing";
               }
               enum "1531.09" {
                 description "1531.09 nm/195.803125 THz 3.125GHz spacing";
               }
               enum "1531.07" {
                 description "1531.07 nm/195.806250 THz 3.125/6.25GHz spacing";
               }
               enum "1531.04" {
                 description "1531.04 nm/195.809375 THz 3.125GHz spacing";
               }
               enum "1531.02" {
                 description "1531.02 nm/195.812500 THz 3.125/6.25/12.5GHz spacing";
               }
               enum "1530.99" {
                 description "1530.99 nm/195.815625 THz 3.125GHz spacing";
               }
               enum "1530.97" {
                 description "1530.97 nm/195.818750 THz 3.125/6.25GHz spacing";
               }
               enum "1530.94" {
                 description "1530.94 nm/195.821875 THz 3.125GHz spacing";
               }
               enum "1530.92" {
                 description "1530.92 nm/195.825000 THz 3.125/6.25/12.5/75GHz spacing";
               }
               enum "1530.90" {
                 description "1530.90 nm/195.828125 THz 3.125GHz spacing";
               }
               enum "1530.87" {
                 description "1530.87 nm/195.831250 THz 3.125/6.25GHz spacing";
               }
               enum "1530.85" {
                 description "1530.85 nm/195.834375 THz 3.125GHz spacing";
               }
               enum "1530.82" {
                 description "1530.82 nm/195.837500 THz 3.125/6.25/12.5GHz spacing";
               }
               enum "1530.80" {
                 description "1530.80 nm/195.840625 THz 3.125GHz spacing";
               }
               enum "1530.77" {
                 description "1530.77 nm/195.843750 THz 3.125/6.25GHz spacing";
               }
               enum "1530.75" {
                 description "1530.75 nm/195.846875 THz 3.125GHz spacing";
               }
               enum "1530.72" {
                 description "1530.72 nm/195.850000 THz 3.125/6.25/12.5/50GHz spacing";
               }
               enum "1530.70" {
                 description "1530.70 nm/195.853125 THz 3.125GHz spacing";
               }
               enum "1530.68" {
                 description "1530.68 nm/195.856250 THz 3.125/6.25GHz spacing";
               }
               enum "1530.65" {
                 description "1530.65 nm/195.859375 THz 3.125GHz spacing";
               }
               enum "1530.63" {
                 description "1530.63 nm/195.862500 THz 3.125/6.25/12.5GHz spacing";
               }
               enum "1530.60" {
                 description "1530.60 nm/195.865625 THz 3.125GHz spacing";
               }
               enum "1530.58" {
                 description "1530.58 nm/195.868750 THz 3.125/6.25GHz spacing";
               }
               enum "1530.55" {
                 description "1530.55 nm/195.871875 THz 3.125GHz spacing";
               }
               enum "1530.53" {
                 description "1530.53 nm/195.875000 THz 3.125/6.25/12.5GHz spacing";
               }
               enum "1530.51" {
                 description "1530.51 nm/195.878125 THz 3.125GHz spacing";
               }
               enum "1530.48" {
                 description "1530.48 nm/195.881250 THz 3.125/6.25GHz spacing";
               }
               enum "1530.46" {
                 description "1530.46 nm/195.884375 THz 3.125GHz spacing";
               }
               enum "1530.43" {
                 description "1530.43 nm/195.887500 THz 3.125/6.25/12.5GHz spacing";
               }
               enum "1530.41" {
                 description "1530.41 nm/195.890625 THz 3.125GHz spacing";
               }
               enum "1530.38" {
                 description "1530.38 nm/195.893750 THz 3.125/6.25GHz spacing";
               }
               enum "1530.36" {
                 description "1530.36 nm/195.896875 THz 3.125GHz spacing";
               }
               enum "1530.33" {
                 description "1530.33 nm/195.900000 THz 3.125/6.25/12.5/50/75/100GHz spacing";
               }
               enum "1530.31" {
                 description "1530.31 nm/195.903125 THz 3.125GHz spacing";
               }
               enum "1530.29" {
                 description "1530.29 nm/195.906250 THz 3.125/6.25GHz spacing";
               }
               enum "1530.26" {
                 description "1530.26 nm/195.909375 THz 3.125GHz spacing";
               }
               enum "1530.24" {
                 description "1530.24 nm/195.912500 THz 3.125/6.25/12.5GHz spacing";
               }
               enum "1530.21" {
                 description "1530.21 nm/195.915625 THz 3.125GHz spacing";
               }
               enum "1530.19" {
                 description "1530.19 nm/195.918750 THz 3.125/6.25GHz spacing";
               }
               enum "1530.16" {
                 description "1530.16 nm/195.921875 THz 3.125GHz spacing";
               }
               enum "1530.14" {
                 description "1530.14 nm/195.925000 THz 3.125/6.25/12.5GHz spacing";
               }
               enum "1530.11" {
                 description "1530.11 nm/195.928125 THz 3.125GHz spacing";
               }
               enum "1530.09" {
                 description "1530.09 nm/195.931250 THz 3.125/6.25GHz spacing";
               }
               enum "1530.07" {
                 description "1530.07 nm/195.934375 THz 3.125GHz spacing";
               }
               enum "1530.04" {
                 description "1530.04 nm/195.937500 THz 3.125/6.25/12.5GHz spacing";
               }
               enum "1530.02" {
                 description "1530.02 nm/195.940625 THz 3.125GHz spacing";
               }
               enum "1529.99" {
                 description "1529.99 nm/195.943750 THz 3.125/6.25GHz spacing";
               }
               enum "1529.97" {
                 description "1529.97 nm/195.946875 THz 3.125GHz spacing";
               }
               enum "1529.94" {
                 description "1529.94 nm/195.950000 THz 3.125/6.25/12.5/50GHz spacing";
               }
               enum "1529.92" {
                 description "1529.92 nm/195.953125 THz 3.125GHz spacing";
               }
               enum "1529.89" {
                 description "1529.89 nm/195.956250 THz 3.125/6.25GHz spacing";
               }
               enum "1529.87" {
                 description "1529.87 nm/195.959375 THz 3.125GHz spacing";
               }
               enum "1529.85" {
                 description "1529.85 nm/195.962500 THz 3.125/6.25/12.5GHz spacing";
               }
               enum "1529.82" {
                 description "1529.82 nm/195.965625 THz 3.125GHz spacing";
               }
               enum "1529.80" {
                 description "1529.80 nm/195.968750 THz 3.125/6.25GHz spacing";
               }
               enum "1529.77" {
                 description "1529.77 nm/195.971875 THz 3.125GHz spacing";
               }
               enum "1529.75" {
                 description "1529.75 nm/195.975000 THz 3.125/6.25/12.5/75GHz spacing";
               }
               enum "1529.72" {
                 description "1529.72 nm/195.978125 THz 3.125GHz spacing";
               }
               enum "1529.70" {
                 description "1529.70 nm/195.981250 THz 3.125/6.25GHz spacing";
               }
               enum "1529.68" {
                 description "1529.68 nm/195.984375 THz 3.125GHz spacing";
               }
               enum "1529.65" {
                 description "1529.65 nm/195.987500 THz 3.125/6.25/12.5GHz spacing";
               }
               enum "1529.63" {
                 description "1529.63 nm/195.990625 THz 3.125GHz spacing";
               }
               enum "1529.60" {
                 description "1529.60 nm/195.993750 THz 3.125/6.25GHz spacing";
               }
               enum "1529.58" {
                 description "1529.58 nm/195.996875 THz 3.125GHz spacing";
               }
               enum "1529.55" {
                 description "1529.55 nm/196.000000 THz 3.125/6.25/12.5/100GHz spacing";
               }
               enum "1529.53" {
                 description "1529.53 nm/196.003125 THz 3.125GHz spacing";
               }
               enum "1529.50" {
                 description "1529.50 nm/196.006250 THz 3.125/6.25GHz spacing";
               }
               enum "1529.48" {
                 description "1529.48 nm/196.009375 THz 3.125GHz spacing";
               }
               enum "1529.46" {
                 description "1529.46 nm/196.012500 THz 3.125/6.25/12.5GHz spacing";
               }
               enum "1529.43" {
                 description "1529.43 nm/196.015625 THz 3.125GHz spacing";
               }
               enum "1529.41" {
                 description "1529.41 nm/196.018750 THz 3.125/6.25GHz spacing";
               }
               enum "1529.38" {
                 description "1529.38 nm/196.021875 THz 3.125GHz spacing";
               }
               enum "1529.36" {
                 description "1529.36 nm/196.025000 THz 3.125/6.25/12.5GHz spacing";
               }
               enum "1529.33" {
                 description "1529.33 nm/196.028125 THz 3.125GHz spacing";
               }
               enum "1529.31" {
                 description "1529.31 nm/196.031250 THz 3.125/6.25GHz spacing";
               }
               enum "1529.29" {
                 description "1529.29 nm/196.034375 THz 3.125GHz spacing";
               }
               enum "1529.26" {
                 description "1529.26 nm/196.037500 THz 3.125/6.25/12.5GHz spacing";
               }
               enum "1529.24" {
                 description "1529.24 nm/196.040625 THz 3.125GHz spacing";
               }
               enum "1529.21" {
                 description "1529.21 nm/196.043750 THz 3.125/6.25GHz spacing";
               }
               enum "1529.19" {
                 description "1529.19 nm/196.046875 THz 3.125GHz spacing";
               }
               enum "1529.16" {
                 description "1529.16 nm/196.050000 THz 3.125/6.25/12.5/50/75GHz spacing";
               }
               enum "1529.14" {
                 description "1529.14 nm/196.053125 THz 3.125GHz spacing";
               }
               enum "1529.11" {
                 description "1529.11 nm/196.056250 THz 3.125/6.25GHz spacing";
               }
               enum "1529.09" {
                 description "1529.09 nm/196.059375 THz 3.125GHz spacing";
               }
               enum "1529.07" {
                 description "1529.07 nm/196.062500 THz 3.125/6.25/12.5GHz spacing";
               }
               enum "1529.04" {
                 description "1529.04 nm/196.065625 THz 3.125GHz spacing";
               }
               enum "1529.02" {
                 description "1529.02 nm/196.068750 THz 3.125/6.25GHz spacing";
               }
               enum "1528.99" {
                 description "1528.99 nm/196.071875 THz 3.125GHz spacing";
               }
               enum "1528.97" {
                 description "1528.97 nm/196.075000 THz 3.125/6.25/12.5GHz spacing";
               }
               enum "1528.94" {
                 description "1528.94 nm/196.078125 THz 3.125GHz spacing";
               }
               enum "1528.92" {
                 description "1528.92 nm/196.081250 THz 3.125/6.25GHz spacing";
               }
               enum "1528.90" {
                 description "1528.90 nm/196.084375 THz 3.125GHz spacing";
               }
               enum "1528.87" {
                 description "1528.87 nm/196.087500 THz 3.125/6.25/12.5GHz spacing";
               }
               enum "1528.85" {
                 description "1528.85 nm/196.090625 THz 3.125GHz spacing";
               }
               enum "1528.82" {
                 description "1528.82 nm/196.093750 THz 3.125/6.25GHz spacing";
               }
               enum "1528.80" {
                 description "1528.80 nm/196.096875 THz 3.125GHz spacing";
               }
               enum "1528.77" {
                 description "1528.77 nm/196.100000 THz 3.125/6.25/12.5/50/75/100GHz spacing";
               }
               enum "1528.75" {
                 description "1528.75 nm/196.103125 THz 3.125GHz spacing";
               }
               enum "1528.72" {
                 description "1528.72 nm/196.106250 THz 3.125/6.25GHz spacing";
               }
               enum "1528.70" {
                 description "1528.70 nm/196.109375 THz 3.125GHz spacing";
               }
               enum "1528.68" {
                 description "1528.68 nm/196.112500 THz 3.125/6.25/12.5GHz spacing";
               }
               enum "1528.65" {
                 description "1528.65 nm/196.115625 THz 3.125GHz spacing";
               }
               enum "1528.63" {
                 description "1528.63 nm/196.118750 THz 3.125/6.25GHz spacing";
               }
               enum "1528.60" {
                 description "1528.60 nm/196.121875 THz 3.125GHz spacing";
               }
               enum "1528.58" {
                 description "1528.58 nm/196.125000 THz 3.125/6.25/12.5/75GHz spacing";
               }
               enum "1528.55" {
                 description "1528.55 nm/196.128125 THz 3.125GHz spacing";
               }
               enum "1528.53" {
                 description "1528.53 nm/196.131250 THz 3.125/6.25GHz spacing";
               }
               enum "1528.51" {
                 description "1528.51 nm/196.134375 THz 3.125GHz spacing";
               }
               enum "1528.48" {
                 description "1528.48 nm/196.137500 THz 3.125/6.25/12.5GHz spacing";
               }
               enum "1528.46" {
                 description "1528.46 nm/196.140625 THz 3.125GHz spacing";
               }
               enum "1528.43" {
                 description "1528.43 nm/196.143750 THz 3.125/6.25GHz spacing";
               }
               enum "1528.41" {
                 description "1528.41 nm/196.146875 THz 3.125GHz spacing";
               }
               enum "1528.38" {
                 description "1528.38 nm/196.15040 THz 50Ghz spacing";
               }
             }
           }
           leaf tx-power {
             description "Transmit laser output power";
             units "dBm";
             type string {
             }
           }
           container loopback {
             presence "enable loopback";
             description "Put the optics in loopback mode";
             uses apply-advanced;
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "Sky-Compatible Soft Decision Forward Error Correction";
               }
               enum "sdfec25" {
                 description "Denali-Compatible Soft Decision Forward Error Correction with 25 percent overhead";
               }
               enum "hgfec" {
                 description "High Gain Forward Error Correction";
               }
               enum "sdfec15" {
                 description "Soft Decision Forward Error Correction with 15 percent overhead";
               }
             }
           }
           leaf high-polarization {
             description "High polarization tracking mode";
             type empty;
           }
           container signal-degrade {
             description "Signal degrade thresholds";
             uses apply-advanced;
             leaf interval {
               description "Time interval";
               default "10";
               units "milliseconds";
               type union {
                 type string {
                   pattern "<.*>|$.*";
                 }
                 type uint32 {
                   range "1 .. 1000";
                 }
               }
             }
             leaf ber-threshold-clear {
               description "Ber threshold for signal degrade clear (format: xe-n, example: 4.5e-3)";
               type string {
               }
             }
             leaf ber-threshold-signal-degrade {
               description "Ber threshold for signal-degrade (format: xe-n, example: 4.5e-3)";
               type string {
               }
             }
             leaf q-threshold-signal-degrade-clear {
               description "Q threshold for signal-degrade clear (e.g. 14.26)";
               units "dB";
               type string;
             }
             leaf q-threshold-signal-degrade {
               description "Q threshold for signal-degrade (e.g. 9.26)";
               units "dB";
               type string;
             }
           }
           list alarm {
             key name;
             ordered-by user;
             description "Set optic alarms";
             leaf name {
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-signal-power-high-tca {
               description "Rx signal power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-signal-power-low-tca {
               description "Rx signal power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                 }
               }
               leaf threshold-24hrs {
                 description "TCA Threshold for 24-hour interval in celsius";
                 type string {
                 }
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                 }
               }
               leaf threshold-24hrs {
                 description "TCA Threshold for 24-hour interval in celsius";
                 type string {
                 }
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container fec-ber {
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                 }
               }
               leaf threshold-24hrs {
                 description "TCA Threshold for 24-hour interval in mA";
                 type string {
                 }
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                 }
               }
               leaf threshold-24hrs {
                 description "TCA Threshold for 24-hour interval in mA";
                 type string {
                 }
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                 }
               }
               leaf threshold-24hrs {
                 description "TCA Threshold for 24-hour interval in ps/nm";
                 type string {
                 }
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                 }
               }
               leaf threshold-24hrs {
                 description "TCA Threshold for 24-hour interval in ps/nm";
                 type string {
                 }
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes)";
                 type string {
                 }
               }
               leaf threshold-24hrs {
                 description "TCA Threshold for 24-hour interval";
                 type string {
                 }
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm ";
                 type string {
                 }
               }
               leaf threshold-24hrs {
                 description "TCA Threshold for 24-hour interval in dBm";
                 type string {
                 }
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
           }
           list warning {
             key name;
             ordered-by user;
             description "Set optic warnings";
             leaf name {
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
           choice lane-info {
             case case_1 {
             }
             case case_2 {
             }
           }
         }
         container och-options {
           description "Optical channel configuration options";
           uses och-attributes;
         }
         container otu-options {
           description "Optical transmission unit configuration options";
           uses otu-attributes;
         }
         container odu-options {
           description "Optical data unit configuration options";
           uses odu-attributes;
         }
         container ett-options {
           description "Transport ethernet client configuration options";
           uses ett-attributes;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               type empty;
             }
             leaf non-revertive {
               description "Do not revert back (default mode) from active backup link to primary, if primary is UP";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             description "Source address filters";
             leaf name {
               description "Remote MAC address";
               type jt:mac-addr;
             }
           }
           container load-balance {
             uses aggregate-load-balance;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
               mandatory true;
             }
             leaf local-address {
               description "BFD local address";
               type jt:ipaddr;
               mandatory true;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             type union {
               type string {
                 pattern "<.*>|$.*";
               }
               type uint16;
             }
           }
           container minimum-bandwidth {
             presence "enable minimum-bandwidth";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bits per sec";
                 }
                 enum "kbps" {
                   description "Links are in kilo bits per sec";
                 }
                 enum "mbps" {
                   description "Links are in mega bits per sec";
                 }
                 enum "gbps" {
                   description "Links are in giga bits per sec ";
                 }
               }
             }
           }
           choice redundancy_choice {
             case case_1 {
             }
             case case_2 {
             }
           }
           container rebalance-periodic {
             uses apply-advanced;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
               }
             }
           }
           container local-bias {
             presence "enable local-bias";
             description "Turn on local bias functionality";
             uses apply-advanced;
             leaf disable {
               description "Disable local-bias";
               type empty;
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             container link-protection {
               presence "enable link-protection";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
           }
           list link-protection-sub-group {
             key name;
             ordered-by user;
             description "Link Protection subgroup configuration";
             leaf name {
               description "Name of the subgroup";
               type string {
                 length "2 .. 64";
               }
             }
             uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             leaf mac-learn-enable {
               description "Learn MAC addresses dynamically";
               type empty;
             }
           }
         }
         container es-options {
           description "ES PIC interface-specific options";
           uses apply-advanced;
           leaf backup-interface {
             description "Name of backup interface";
             type union {
               type jt:interface-device;
               type string {
                 pattern "<.*>|$.*";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
           leaf sos {
             description "Enable SOS";
             type empty;
           }
         }
         container dsl-sfp-options {
           description "DSL SFP options";
           uses apply-advanced;
           container adsl-options {
             description "ADSL options";
             uses apply-advanced;
             leaf vpi {
               description "Virtual path identifier";
               type union {
                 type string {
                   pattern "<.*>|$.*";
                 }
                 type uint32 {
                   range "0 .. 255";
                 }
               }
             }
             leaf vci {
               description "Virtual circuit identifier";
               type union {
                 type string {
                   pattern "<.*>|$.*";
                 }
                 type uint32 {
                   range "32 .. 65535";
                 }
               }
             }
             leaf encap {
               description "Encapsulation";
               type enumeration {
                 enum "bypass" {
                   description "Bypass";
                 }
                 enum "llcsnap-bridged-802dot1q" {
                   description "LLCSNAP bridged 802.1q";
                 }
                 enum "llcsnap-routed-ip" {
                   description "LLCSNAP routed ip";
                 }
                 enum "vc-mux-bridged" {
                   description "VC MUX bridged";
                 }
                 enum "vc-mux-routed-ip" {
                   description "VC MUX routed ip";
                 }
                 enum "generic" {
                   description "Generic";
                 }
               }
             }
             leaf annex {
               description "Annex type";
               type enumeration {
                 enum "auto" {
                   description "Annex type auto";
                 }
                 enum "annexj-off" {
                   description "Annex type annexj turn off";
                 }
               }
             }
           }
           container vdsl-options {
             description "VDSL options";
             uses apply-advanced;
             leaf profile {
               description "VDSL profile";
               type enumeration {
                 enum "auto" {
                   description "Automatic";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
                 enum "30a" {
                   description "Profile 30a";
                 }
               }
             }
             leaf carrier {
               description "Carrier setting";
               type enumeration {
                 enum "auto" {
                   description "Automatic";
                 }
                 enum "a43" {
                   description "Carrier A43";
                 }
                 enum "b43" {
                   description "Carrier B43";
                 }
               }
             }
           }
           container gfast-options {
             description "G.fast options";
             uses apply-advanced;
             leaf carrier {
               description "Carrier setting";
               type enumeration {
                 enum "a43" {
                   description "Carrier A43";
                 }
                 enum "a43c" {
                   description "Carrier A43C";
                 }
                 enum "b43" {
                   description "Carrier B43";
                 }
                 enum "b43c" {
                   description "Carrier B43C";
                 }
               }
             }
           }
         }
         container shdsl-options {
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   presence "enable aps";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                     mandatory true;
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                     mandatory true;
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                     mandatory true;
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                     mandatory true;
                   }
                 }
               }
             }
           }
           container redundancy {
             description "Container interface redundancy options";
             uses apply-advanced;
             container hold-time {
               description "Hold time for link up and link down";
               leaf up {
                 description "Link up hold time";
                 units "milliseconds";
                 type union {
                   type string {
                     pattern "<.*>|$.*";
                   }
                   type uint32 {
                     range "0 .. 65534";
                   }
                 }
                 mandatory true;
               }
               leaf down {
                 description "Link down hold time";
                 units "milliseconds";
                 type union {
                   type string {
                     pattern "<.*>|$.*";
                   }
                   type uint32 {
                     range "0 .. 65534";
                   }
                 }
                 mandatory true;
               }
             }
           }
           leaf-list container-list {
             ordered-by user;
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         list unit {
           key name;
           description "Logical interface";
           leaf name {
             type string;
           }
           uses apply-advanced;
           leaf interface-tag {
             description "Interface tag name";
             type string {
               length "1 .. 64";
             }
           }
           leaf alias {
             description "Interface alias";
             type string;
           }
           container peer-psd {
             presence "enable peer-psd";
             description "Peer psd";
             leaf psd-name {
               description "Peer psd name";
               type string;
               mandatory true;
             }
           }
           container peer-interface {
             presence "enable peer-interface";
             description "Peer interface";
             uses apply-advanced;
             leaf interface-name {
               description "Peer interface name";
               type union {
                 type jt:interface-unit;
                 type string {
                   pattern "<.*>|$.*";
                 }
               }
             }
           }
           container interface-shared-with {
             presence "enable interface-shared-with";
             description "Specify which PSD owns this logical interface";
             uses apply-advanced;
             leaf psd-name {
               description "Name of protected system domain (psd[1-31], ex. psd2)";
               type string {
               }
               mandatory true;
             }
           }
           choice enable-disable {
             case case_1 {
               leaf disable {
                 description "Disable this logical interface";
                 type empty;
               }
             }
           }
           leaf extended-telemetry {
             description "Enable extended telemetry";
             type empty;
           }
           leaf passive-monitor-mode {
             description "Use interface to tap packets from another router";
             type empty;
           }
           leaf clear-dont-fragment-bit {
             description "Clear DF bit in packet (AS PIC and J-series only as well as MIF)";
             type empty;
           }
           leaf description {
             description "Text description of interface";
             type string;
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
               }
               enum "ppp-over-ether" {
                 description "PPPoE encapsulation";
               }
               enum "atm-ppp-vc-mux" {
                 description "ATM PPP over raw AAL5";
               }
               enum "atm-ppp-llc" {
                 description "ATM PPP over AAL5/LLC";
               }
               enum "atm-ppp-funi" {
                 description "ATM PPP over FUNI";
               }
               enum "atm-mlppp-llc" {
                 description "ATM MLPPP over AAL5/LLC";
               }
               enum "frame-relay-ppp" {
                 description "PPP over Frame Relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "ethernet-tcc" {
                 description "Ethernet translational cross-connect";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               status deprecated;
               type empty;
             }
             leaf no-routing-services {
               description "Don't enable routing services";
               status deprecated;
               type empty;
             }
           }
           container routing-service {
             description "Routing Services on this interface";
             uses apply-advanced;
             choice enable-disable {
               case case_1 {
                 leaf enable {
                   description "Enable Routing Service";
                   type empty;
                 }
               }
               case case_2 {
                 leaf disable {
                   description "Disable Routing Service";
                   type empty;
                 }
               }
             }
           }
           container arp-resp {
             presence "enable arp-resp";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 type string;
               }
             }
             case case_2 {
               leaf vlan-id-range {
                 description "Virtual LAN identifier range of form vid1-vid2";
                 type jt:vlan-range;
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 type jt:vlan-range;
               }
             }
             case case_5 {
               leaf-list vlan-tag {
                 ordered-by user;
                 description "IEEE 802.1q tag list for VLAN tagged frames";
                 status deprecated;
                 type string;
               }
             }
             case case_6 {
               container vlan-tags {
                 presence "enable vlan-tags";
                 description "IEEE 802.1q tags";
                 leaf outer {
                   description "[tpid.]vlan-id, tpid format is 0xNNNN and is optional";
                   type string;
                   mandatory true;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                       }
                     }
                   }
                   case case_3 {
                     leaf-list inner-list {
                       description "List of VLAN identifiers";
                       type jt:vlan-range;
                     }
                   }
                 }
               }
             }
           }
           leaf native-inner-vlan-id {
             description "Native virtual LAN identifier for singly tagged frames";
             type union {
               type string {
                 pattern "<.*>|$.*";
               }
               type uint32 {
                 range "0 .. 4094";
               }
             }
           }
           container accept-source-mac {
             description "Remote media access control address to/from which to accept traffic";
             uses apply-advanced;
             list mac-address {
               key name;
               description "Remote MAC address";
               uses mac_list;
             }
           }
           container input-vlan-map {
             description "VLAN map operation on input";
             uses vlan_map;
           }
           container output-vlan-map {
             description "VLAN map operation on output";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           choice psn_vci_type {
             case case_1 {
             }
             case case_2 {
             }
           }
           container atm-l2circuit-mode {
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             description "ATM VCI range start <start-vci> end <end-vci>";
             leaf start {
               description "ATM VCI range's start value";
               type union {
                 type string {
                   pattern "<.*>|$.*";
                 }
                 type uint16 {
                   range "32 .. 4094";
                 }
               }
               mandatory true;
             }
             leaf end {
               description "ATM VCI range's end value";
               type union {
                 type string {
                   pattern "<.*>|$.*";
                 }
                 type uint16 {
                   range "32 .. 4094";
                 }
               }
               mandatory true;
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             description "OAM cell period";
             choice oam_period_choices {
               case case_1 {
                 leaf oam-period {
                   description "OAM cell period";
                   units "seconds";
                   type union {
                     type string {
                       pattern "<.*>|$.*";
                     }
                     type uint32 {
                       range "1 .. 900";
                     }
                   }
                 }
               }
               case case_2 {
                 container disable {
                   presence "enable disable";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           choice keepalive_choices {
             case case_1 {
               container keepalives {
                 description "Send or demand keepalive messages";
                 presence "enable keepalives";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             type string;
           }
           leaf peer-unit {
             description "Peer unit number";
             type union {
               type string {
                 pattern "<.*>|$.*";
               }
               type uint32 {
                 range "0 .. 16385";
               }
             }
           }
           container tunnel {
             description "Tunnel parameters";
             uses apply-advanced;
             container encapsulation {
               presence "enable encapsulation";
               description "Encapsulation over tunnel";
               container vxlan-gpe {
                 presence "enable vxlan-gpe";
                 uses apply-advanced;
                 container source {
                   uses apply-advanced;
                   leaf address {
                     description "Interface address prefix";
                     type jt:ipv4addr;
                   }
                   leaf mac-address {
                     description "Interface source mac address";
                     type jt:mac-addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                   leaf mac-address {
                     description "Interface destination mac address";
                     type jt:mac-addr;
                   }
                 }
                 leaf tunnel-endpoint {
                   description "Tunnel end point type";
                   type enumeration {
                     enum "vxlan" {
                       description "To configure vxlan tunnel-end-point";
                     }
                   }
                   mandatory true;
                 }
                 container source-udp-port-range {
                   description "Value range for source-udp-port";
                   leaf min {
                     description "Minimum range value";
                     type union {
                       type string {
                         pattern "<.*>|$.*";
                       }
                       type uint32 {
                         range "1 .. 65535";
                       }
                     }
                     mandatory true;
                   }
                   leaf max {
                     description "Maximum range value";
                     type union {
                       type string {
                         pattern "<.*>|$.*";
                       }
                       type uint32 {
                         range "1 .. 65535";
                       }
                     }
                     mandatory true;
                   }
                 }
                 leaf destination-udp-port {
                   description "Value to write to the destination-udp-port field";
                   type union {
                     type string {
                       pattern "<.*>|$.*";
                     }
                     type uint32 {
                       range "1 .. 65535";
                     }
                   }
                   mandatory true;
                 }
                 leaf vni {
                   description "Value to write to the vni field";
                   type union {
                     type string {
                       pattern "<.*>|$.*";
                     }
                     type uint32 {
                       range "0 .. 16777214";
                     }
                   }
                   mandatory true;
                 }
               }
             }
             choice source_type {
               case case_1 {
                 leaf source {
                   description "Tunnel source address";
                   type jt:ipaddr;
                 }
               }
               case case_2 {
               }
               case case_3 {
               }
             }
             choice destination_type {
               case case_1 {
                 leaf destination {
                   description "Tunnel destination address";
                   type jt:ipaddr;
                 }
               }
               case case_2 {
               }
             }
             leaf backup-destination {
               description "Backup tunnel destination";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 type string {
                 }
               }
             }
           }
           leaf compression-device {
             description "Logical interface used for compression";
             type union {
               type jt:interface-unit;
               type string {
                 pattern "<.*>|$.*";
               }
             }
           }
           container layer2-policer {
             description "Layer2 policing for logical interface";
             uses apply-advanced;
             choice layer2-input-policer-choice {
               case case_1 {
                 leaf input-policer {
                   description "Two-color policer for received packets";
                   type string;
                 }
               }
               case case_2 {
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           choice virtual-gateway {
             case case_1 {
               leaf no-auto-virtual-gateway-esi {
                 description "Disable auto ESI generation for virtual gateway address";
                 type empty;
               }
             }
             case case_2 {
               container virtual-gateway-esi {
                 description "ESI configuration of virtual gateway";
                 uses apply-advanced;
                 leaf identifier {
                   description "ESI value for the interface";
                   type jt:esi;
                   mandatory true;
                 }
                 choice mode {
                   case case_1 {
                     leaf single-active {
                       description "Single-active mode";
                       type empty;
                     }
                   }
                   case case_2 {
                     leaf all-active {
                       description "All-active mode";
                       type empty;
                     }
                   }
                 }
               }
             }
           }
           container service {
             description "Service operations";
             uses apply-advanced;
             list pcef {
               key name;
               ordered-by user;
               description "PCEF configuration";
               leaf name {
                 description "PCEF Profile name";
                 type string;
                 mandatory true;
               }
               uses apply-advanced;
               leaf activate-all {
                 description "Activate all rules and rulebases in the pcef profile";
                 type empty;
               }
               list activate {
                 key name;
                 ordered-by user;
                 description "Name of pcef profile rule or rulebase to activate";
                 leaf name {
                   description "Name of pcef profile rule or rulebase to activate";
                   type string;
                 }
                 uses apply-advanced;
               }
             }
           }
           choice generate-eui64-choice {
             leaf generate-eui64 {
               description "To generate Link Local EUI-64 addresses";
               type empty;
             }
             leaf no-generate-eui64 {
               description "Don't to generate Link Local EUI-64 addresses";
               type empty;
             }
           }
           container family {
             description "Protocol family";
             container inet {
               presence "enable inet";
               description "IPv4 parameters";
               uses apply-advanced;
               container class-based-filtering {
                 description "Enable class based filter on interface";
                 uses apply-advanced;
               }
               container dhcp {
                 description "Dynamic Host Configuration Protocol client configuration";
                 presence "enable dhcp";
                 uses dhcp-client-type;
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   type empty;
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 type union {
                   type string {
                     pattern "<.*>|$.*";
                   }
                   type uint32 {
                     range "1 .. 2000000";
                   }
                 }
               }
               leaf no-redirects {
                 description "Do not redirect traffic";
                 type empty;
               }
               leaf nat-outside-interface {
                 description "Public interface used for NAT";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               leaf allow-filter-on-re {
                 description "Enable kernel filter on network ports";
                 type empty;
               }
               container filter {
                 description "Packet filtering";
                 uses apply-advanced;
                 choice input_choice {
                   case case_1 {
                     container input {
                       description "Filter to be applied to received packets";
                       leaf filter-name {
                         description "Name of the filter";
                         type string;
                         mandatory true;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       description "Filter to be applied to transmitted packets";
                       leaf filter-name {
                         description "Name of the filter";
                         type string;
                         mandatory true;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
               }
               container simple-filter {
                 description "Filter for doing multifield classification";
                 uses apply-advanced;
                 leaf input {
                   description "Name of simple filter applied to received packets";
                   type string;
                 }
               }
               container policer {
                 description "Interface policing";
                 uses apply-advanced;
                 leaf arp {
                   description "Name of policer applied to received ARP packets";
                   type string;
                 }
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               container service {
                 description "Service operations";
                 uses apply-advanced;
                 container input {
                   description "Service sets to consider for received packets";
                   uses apply-advanced;
                   list service-set {
                     key name;
                     ordered-by user;
                     description "Service set to consider for received packets";
                     leaf name {
                       description "Name of service set";
                       type string {
                       }
                     }
                     uses apply-advanced;
                     leaf service-filter {
                       description "Name of service filter";
                       type string;
                     }
                   }
                   leaf post-service-filter {
                     description "Post-service filter to apply to received packets";
                     type string;
                   }
                 }
                 container output {
                   description "Service sets to consider for transmitted packets";
                   uses apply-advanced;
                   list service-set {
                     key name;
                     ordered-by user;
                     description "Service set to consider for transmitted packets";
                     leaf name {
                       description "Name of service set";
                       type string {
                       }
                     }
                     uses apply-advanced;
                     leaf service-filter {
                       description "Name of service filter";
                       type string;
                     }
                   }
                 }
               }
               list next-hop-tunnel {
                 key name;
                 ordered-by user;
                 description "One or more next-hop tunnel tables";
                 leaf name {
                   description "Next-hop tunnel gateway address";
                   type string;
                   mandatory true;
                 }
                 uses apply-advanced;
                 leaf ipsec-vpn {
                   description "Name of IPSec VPN";
                   type string;
                   mandatory true;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address/destination prefix";
                 leaf name {
                   description "Interface address/destination prefix";
                   type jt:ipv4prefix;
                 }
                 uses apply-advanced;
                 leaf destination {
                   description "Destination address";
                   type jt:ipv4addr;
                 }
                 leaf destination-profile {
                   description "Profile to use for destination address";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     type union {
                       type string {
                         pattern "<.*>|$.*";
                       }
                       type uint32 {
                         range "1 .. 4294967295";
                       }
                     }
                     mandatory true;
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     type union {
                       type string {
                         pattern "<.*>|$.*";
                       }
                       type uint32 {
                         range "1 .. 4294967295";
                       }
                     }
                     mandatory true;
                   }
                   leaf type {
                     description "Tag type must be [1-16]";
                     type union {
                       type string {
                         pattern "<.*>|$.*";
                       }
                       type uint32 {
                         range "1 .. 16";
                       }
                     }
                   }
                 }
                 list multipoint-destination {
                   key name;
                   ordered-by user;
                   description "Multipoint NBMA destination";
                   leaf name {
                     description "Destination address";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     description "OAM cell period";
                     choice oam_period_choices {
                       case case_1 {
                         leaf oam_period {
                           description "OAM cell period";
                           units "seconds";
                           type union {
                             type string {
                               pattern "<.*>|$.*";
                             }
                             type uint32 {
                               range "1 .. 900";
                             }
                           }
                         }
                       }
                       case case_2 {
                         container disable {
                           presence "enable disable";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     uses epd_threshold_config;
                   }
                 }
                 list arp {
                   key name;
                   ordered-by user;
                   description "Static Address Resolution Protocol entries";
                   leaf name {
                     description "Destination IP address";
                     type jt:ipv4addr;
                     mandatory true;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     type empty;
                   }
                   leaf flood-as-unknown-unicast {
                     description "Broadcast the packet with unicast MAC";
                     type empty;
                   }
                 }
                 list vrrp-group {
                   key name;
                   ordered-by user;
                   description "VRRP group";
                   uses vrrp-group;
                 }
                 leaf virtual-gateway-address {
                   description "Virtual Gateway IP address";
                   type jt:ipv4addr;
                 }
               }
               container unnumbered-address {
                 description "Unnumbered interface address/destination prefix";
                 leaf source {
                   description "Interface from which to take local address";
                   type union {
                     type jt:interface-unit;
                     type string {
                       pattern "<.*>|$.*";
                     }
                   }
                   mandatory true;
                 }
                 leaf preferred-source-address {
                   description "Preferred address on the donor interface";
                   type string;
                 }
                 leaf destination {
                   description "Destination address";
                   type jt:ipv4addr;
                 }
                 leaf destination-profile {
                   description "Profile to use for destination address";
                   type string;
                 }
               }
               leaf negotiate-address {
                 description "Negotiate address with remote";
                 type empty;
               }
               leaf destination-udp-port {
                 description "Choose destination UDP port number";
                 type union {
                   type string {
                     pattern "<.*>|$.*";
                   }
                   type uint32 {
                     range "10000 .. 10009";
                   }
                 }
               }
               container auto-configure {
                 description "Auto configuration";
                 uses dynamic_ipv4_type;
               }
             }
             container mlppp {
               description "Multilink PPP protocol parameters";
               uses apply-advanced;
               leaf bundle {
                 description "Logical interface name this link will join";
                 type string;
                 mandatory true;
               }
               choice anchor-points {
                 case case_1 {
                 }
                 case case_2 {
                 }
               }
               leaf dynamic-profile {
                 description " dynamic profile for interface to use";
                 type string {
                   length "1 .. 80";
                 }
               }
             }
             container mlfr-end-to-end {
               presence "enable mlfr-end-to-end";
               description "Multilink Frame Relay end-to-end protocol parameters";
               uses apply-advanced;
               leaf bundle {
                 description "Logical interface name this link will join";
                 type union {
                   type jt:interface-unit;
                   type string {
                     pattern "<.*>|$.*";
                   }
                 }
                 mandatory true;
               }
             }
             container mlfr-uni-nni {
               presence "enable mlfr-uni-nni";
               description "Multilink Frame Relay UNI NNI protocol parameters";
               uses apply-advanced;
               leaf bundle {
                 description "Logical interface name this link will join";
                 type union {
                   type jt:interface-unit;
                   type string {
                     pattern "<.*>|$.*";
                   }
                 }
                 mandatory true;
               }
             }
             container ccc {
               presence "enable ccc";
               description "Circuit cross-connect parameters";
               uses apply-advanced;
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                 }
               }
               leaf keep-address-and-control {
                 description "Don't strip PPP address and control bytes";
                 type empty;
               }
             }
             container tcc {
               presence "enable tcc";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
             }
             container vpls {
               presence "enable vpls";
               description "Virtual private LAN service parameters";
               uses apply-advanced;
               leaf core-facing {
                 description "Interface is core facing";
                 type empty;
               }
             }
             container ethernet-switching {
               description "Ethernet switching parameters";
               presence "enable ethernet-switching";
               uses ethernet-switching-type;
             }
             container any {
               presence "enable any";
               description "Parameters for 'any' family";
               uses apply-advanced;
               container filter {
                 description "Layer 2 packet filtering";
                 uses apply-advanced;
                 leaf input {
                   description "Name of filter applied to received packets";
                   type string {
                   }
                 }
                 leaf group {
                   description "Group to which interface belongs";
                   type union {
                     type string {
                       pattern "<.*>|$.*";
                     }
                     type uint32 {
                       range "1 .. 255";
                     }
                   }
                 }
               }
             }
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           container load-balancing-options {
             description "AMS subunit load balancing options";
             uses apply-advanced;
             leaf preferred-active {
               description "Preferred active Interface name";
               type union {
                 type jt:interface-device;
                 type string {
                   pattern "<.*>|$.*";
                 }
               }
             }
             leaf disable-hash {
               description "Hash based distribution is not needed for this subunit";
               type empty;
             }
             leaf modulo-key {
               description "Modulo based distribution";
               type enumeration {
                 enum "source-ip" {
                   description "Source Ip Address";
                 }
                 enum "destination-ip" {
                   description "Destination Ip Address";
                 }
               }
             }
             container hash-keys {
               uses apply-advanced;
               leaf-list ingress-key {
                 ordered-by user;
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 ordered-by user;
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
               leaf ipv6-source-prefix-length {
                 description "IPv6 source prefix length for hash computation";
                 type enumeration {
                   enum "56" {
                     description "56 bit IPv6 address prefix";
                   }
                   enum "64" {
                     description "64 bit IPv6 address prefix";
                   }
                   enum "96" {
                     description "96 bit IPv6 address prefix";
                   }
                   enum "128" {
                     description "Complete 128 bit IPv6 address";
                   }
                 }
               }
             }
           }
           container interface-state {
             description "IRB interface state computation";
             uses apply-advanced;
             choice state {
               case case_1 {
                 leaf local {
                   description "IRB State computation based on local interface state";
                   type empty;
                 }
               }
               case case_2 {
                 leaf remote {
                   description "IRB State computation based on remote reachability";
                   type empty;
                 }
               }
               case case_3 {
                 leaf local-remote {
                   description "IRB State computation based on local or remote reachability";
                   type empty;
                 }
               }
               case case_4 {
                 leaf local-interface {
                   description "IRB State computation based on loopback AE port state";
                   type union {
                     type jt:interface-name;
                     type string {
                       pattern "<.*>|$.*";
                     }
                   }
                 }
               }
             }
             leaf local-count {
               description "Minimum number of local layer2 link in up state to consider IRB up";
               type union {
                 type uint16;
                 type string {
                   pattern "<.*>|$.*";
                 }
               }
             }
             leaf vtep-count {
               description "Minimum number of VTEP link in up state to consider IRB up";
               type union {
                 type uint16;
                 type string {
                   pattern "<.*>|$.*";
                 }
               }
             }
             container hold-time {
               description "Delay before marking interface up or down for defect";
               uses apply-advanced;
               leaf up {
                 description "Delay in seconds before marking IRB interface up";
                 units "seconds";
                 type union {
                   type uint32;
                   type string {
                     pattern "<.*>|$.*";
                   }
                 }
               }
               leaf down {
                 description "Delay in seconds before marking IRB interface down";
                 units "seconds";
                 type union {
                   type uint32;
                   type string {
                     pattern "<.*>|$.*";
                   }
                 }
               }
             }
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf no-dhcp-flood {
             description "Disable dhcp flooding";
             type empty;
           }
           leaf etree-ac-role {
             description "ETREE attachment circuit role";
             type enumeration {
               enum "root" {
                 description "ETREE root interface";
               }
               enum "leaf" {
                 description "ETREE leaf interface";
               }
             }
           }
         }
         container no-partition {
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           description "Channelized interface partition";
           leaf name {
             description "Sublevel interface partition index (for example, 1, 3-4)";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
               }
               enum "bc" {
                 description "B channel interface";
               }
             }
             mandatory true;
           }
         }
       }
       list interface {
         key name;
         uses interfaces_type;
       }
     }
     container multi-chassis {
       presence "enable multi-chassis";
       description "Multi-chassis configuration";
       uses apply-advanced;
       container mc-lag {
         presence "enable mc-lag";
         description "Multi-chassis Lag configuration";
         uses apply-advanced;
         container consistency-check {
           presence "enable consistency-check";
           description "Consistency Check properties";
           uses apply-advanced;
           leaf comparison-delay-time {
             description "Time after which local and remote config are compared";
             units "seconds";
             type union {
               type string {
                 pattern "<.*>|$.*";
               }
               type uint32 {
                 range "5 .. 600";
               }
             }
           }
           container traceoptions {
             description "Trace options for MCLAG_CFGCHK";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 units "bytes";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Trace flag information";
               leaf name {
                 type enumeration {
                   enum "error" {
                     description "Trace all errors";
                   }
                   enum "event" {
                     description "Trace all events";
                   }
                   enum "packet" {
                     description "Trace all packets";
                   }
                   enum "pipe" {
                     description "Trace pipe messages";
                   }
                   enum "pipe-detail" {
                     description "Trace pipe messages in detail";
                   }
                   enum "all" {
                     description "Trace everything";
                   }
                 }
               }
             }
           }
         }
       }
     }
     container jsrc-partition {
       description "JSRC partition configuration";
       leaf jsrc-partition-name {
         description "JSRC partition name";
         type string {
           length "1 .. 63";
         }
       }
     }
     container snmp {
       description "Simple Network Management Protocol configuration";
       uses apply-advanced;
       leaf system-name {
         description "System name override";
         type string;
       }
       leaf description {
         description "System description";
         type string;
       }
       leaf location {
         description "Physical location of system";
         type string;
       }
       leaf contact {
         description "Contact information for administrator";
         type string;
       }
       leaf-list interface {
         ordered-by user;
         description "Restrict SNMP requests to interfaces";
         type union {
           type jt:interface-name;
           type string {
             pattern "<.*>|$.*";
           }
         }
       }
       leaf packet-size {
         description "Maximum SNMP send message size";
         default "65535";
         type union {
           type string {
             pattern "<.*>|$.*";
           }
           type uint32 {
             range "484 .. 65535";
           }
         }
       }
       container filter-interfaces {
         presence "enable filter-interfaces";
         description "List of interfaces that needs to be filtered";
         uses apply-advanced;
         list interfaces {
           key name;
           ordered-by user;
           description "Filter specified interfaces";
           leaf name {
             type string;
           }
           uses apply-advanced;
         }
         leaf all-internal-interfaces {
           description "Filter all internal interfaces";
           type empty;
         }
       }
       leaf if-count-with-filter-interfaces {
         description "Filter interfaces config for ifNumber and ipv6Interfaces";
         type empty;
       }
       leaf filter-duplicates {
         description "Filter requests with duplicate source address/port and request ID";
         type empty;
       }
       container nonvolatile {
         description "Configure the handling of nonvolatile SNMP Set requests";
         uses apply-advanced;
         leaf commit-delay {
           description "Delay between affirmative SNMP Set reply and start of commit";
           default "5";
           units "seconds";
           type union {
             type uint32;
             type string {
               pattern "<.*>|$.*";
             }
           }
         }
       }
       container engine-id {
         description "SNMPv3 engine ID";
         uses apply-advanced;
         choice engine-id-choice {
           case case_1 {
             leaf use-mac-address {
               description "Uses management interface MAC Address for the engine ID";
               type empty;
             }
           }
           case case_2 {
             leaf use-default-ip-address {
               description "Use default IP address for the engine ID";
               type empty;
             }
           }
           case case_3 {
             leaf local {
               description "Local engine ID";
               type string {
               }
             }
           }
           case case_4 {
             leaf unique-id {
               description "Use hexadecimal string for engine ID";
               type string {
                 length "5 .. 32";
               }
             }
           }
         }
       }
       container v3 {
         description "SNMPv3 configuration information";
         uses apply-advanced;
         container usm {
           description "User-based security model (USM) information";
           uses apply-advanced;
           container local-engine {
             description "Local engine user configuration";
             uses apply-advanced;
             list user {
               key name;
               ordered-by user;
               description "SNMPv3 USM user information";
               uses v3-user-config;
             }
           }
           list remote-engine {
             key name;
             ordered-by user;
             description "Remote engine user configuration";
             leaf name {
               description "Remote engine id (Hex format)";
               type string {
               }
             }
             uses apply-advanced;
             list user {
               key name;
               ordered-by user;
               description "SNMPv3 USM user information";
               uses v3-user-config;
             }
           }
         }
         container vacm {
           description "View-based access control model (VACM) information";
           uses apply-advanced;
           container security-to-group {
             description "Assigns security names to group";
             uses apply-advanced;
             list security-model {
               key name;
               ordered-by user;
               description "Security model context for group assignment";
               leaf name {
                 description "SNMPv3 security-to-group model name";
                 type enumeration {
                   enum "usm" {
                     description "User-based security model";
                   }
                   enum "v1" {
                     description "SNMPv1 model";
                   }
                   enum "v2c" {
                     description "SNMPv2c model";
                   }
                 }
               }
               uses apply-advanced;
               list security-name {
                 key name;
                 ordered-by user;
                 description "Security name to assign to group";
                 leaf name {
                   description "Security name";
                   type string {
                     length "1 .. 32";
                   }
                 }
                 uses apply-advanced;
                 leaf group {
                   description "Group to which to assign security name";
                   type string {
                     length "1 .. 32";
                   }
                 }
               }
             }
           }
           container access {
             description "Specify SNMP access limits";
             uses apply-advanced;
             list group {
               key name;
               ordered-by user;
               description "Group access configuration";
               leaf name {
                 description "SNMPv3 VACM group name";
                 type string {
                   length "1 .. 32";
                 }
               }
               uses apply-advanced;
               container default-context-prefix {
                 description "Default context-prefix access configuration";
                 uses apply-advanced;
                 list security-model {
                   key name;
                   ordered-by user;
                   description "Security model access configuration";
                   uses security-model-access;
                 }
               }
               list context-prefix {
                 key name;
                 ordered-by user;
                 description "Context-prefix access configuration";
                 leaf name {
                   description "SNMPv3 VACM context prefix";
                   type string {
                   }
                 }
                 uses apply-advanced;
                 list security-model {
                   key name;
                   ordered-by user;
                   description "Security model access configuration";
                   uses security-model-access;
                 }
               }
             }
           }
         }
         list target-address {
           key name;
           ordered-by user;
           description "Identifies notification targets as well as allowed management stations";
           leaf name {
             description "SNMP target address name";
             type string {
               length "1 .. 32";
             }
           }
           uses apply-advanced;
           leaf address {
             description "SNMP target address";
             type jt:ipaddr;
             mandatory true;
           }
           leaf port {
             description "SNMP target port number";
             default "162";
             type union {
               type uint16;
               type string {
                 pattern "<.*>|$.*";
               }
             }
           }
           leaf timeout {
             description "Acknowledgment timeout for confirmed SNMP notifications";
             default "15";
             units "seconds";
             type union {
               type uint32;
               type string {
                 pattern "<.*>|$.*";
               }
             }
           }
           leaf retry-count {
             description "Maximum retry count for confirmed SNMP notifications";
             default "3";
             type union {
               type string {
                 pattern "<.*>|$.*";
               }
               type uint32 {
                 range "0 .. 255";
               }
             }
           }
           leaf tag-list {
             description "SNMP tag list used to select target addresses";
             type string {
               length "0 .. 255";
             }
           }
           leaf address-mask {
             description "Mask range of addresses for community string access control.";
             type jt:ipaddr;
           }
           leaf routing-instance {
             description "Routing instance for trap destination";
             type string {
             }
           }
           leaf logical-system {
             description "Logical-system name for trap destination";
             type string {
             }
           }
           leaf target-parameters {
             description "SNMPv3 target parameter name in the target parameters table";
             type string {
               length "1 .. 32";
             }
             mandatory true;
           }
         }
         list target-parameters {
           key name;
           ordered-by user;
           description "Parameters and filter name used when sending notifications";
           leaf name {
             description "SNMPv3 target parameters name";
             type string {
               length "1 .. 32";
             }
           }
           uses apply-advanced;
           container parameters {
             description "Parameters used when sending notifications";
             uses apply-advanced;
             leaf message-processing-model {
               description "The message processing model to be used when generating SNMP notifications";
               type enumeration {
                 enum "v1" {
                   description "SNMPv1 model";
                 }
                 enum "v2c" {
                   description "SNMPv2c model";
                 }
                 enum "v3" {
                   description "SNMPv3 model";
                 }
               }
               mandatory true;
             }
             leaf security-model {
               description "Security-model used when generating SNMP notifications";
               type enumeration {
                 enum "usm" {
                   description "User-based security model";
                 }
                 enum "v1" {
                   description "SNMPv1 model";
                 }
                 enum "v2c" {
                   description "SNMPv2c model";
                 }
               }
               mandatory true;
             }
             leaf security-level {
               description "Security-level used when generating SNMP notifications";
               type enumeration {
                 enum "none" {
                   description "None (noAuthNoPriv)";
                 }
                 enum "authentication" {
                   description "Authentication (authNoPriv)";
                 }
                 enum "privacy" {
                   description "Privacy and authentication (authPriv)";
                 }
               }
               mandatory true;
             }
             leaf security-name {
               description "Security name used when generating SNMP notifications";
               type string {
                 length "1 .. 32";
               }
               mandatory true;
             }
           }
           container notify-filter {
             description "Notify filter to apply to notifications";
             leaf filter {
               description "Filter name to apply to notifications";
               type string {
                 length "1 .. 32";
               }
             }
           }
         }
         list notify {
           key name;
           ordered-by user;
           description "Used to select management targets for notifications as well as the type of notifications";
           leaf name {
             description "Notify name";
             type string {
               length "1 .. 32";
             }
           }
           uses apply-advanced;
           leaf type {
             description "Notification type";
             default "trap";
             type enumeration {
               enum "trap" {
                 description "SNMP trap";
               }
               enum "inform" {
                 description "Inform request";
               }
             }
           }
           leaf tag {
             description "Notifications will be sent to all targets configured with this tag";
             type string {
               length "0 .. 255";
             }
           }
         }
         list notify-filter {
           key name;
           ordered-by user;
           description "Filters to apply to SNMP notifications";
           leaf name {
             description "SNMP profile name in the notify filter table";
             type string {
               length "1 .. 32";
             }
           }
           uses apply-advanced;
           list oid {
             key name;
             ordered-by user;
             description "OID include/exclude list";
             leaf name {
               description "OID to include/exclude from notify filter";
               type string {
               }
             }
             choice filter-action {
               case case_1 {
                 leaf include {
                   description "Include this OID in the notify filter";
                   type empty;
                 }
               }
               case case_2 {
                 leaf exclude {
                   description "Exclude this OID from the notify filter";
                   type empty;
                 }
               }
             }
           }
         }
         leaf management-routing-instance {
           description "Enable SNMPv3 access for all routing instances from this default context";
           type string {
           }
         }
         list snmp-community {
           key name;
           ordered-by user;
           description "SNMP community and view-based access control model configuration";
           leaf name {
             description "Unique index value in this community table entry";
             type string {
               length "1 .. 32";
             }
           }
           uses apply-advanced;
           leaf community-name {
             description "SNMPv1/v2c community name (default is same as community-index)";
             type jt:unreadable;
           }
           leaf security-name {
             description "Security name used when performing access control";
             type string {
               length "1 .. 32";
             }
             mandatory true;
           }
           leaf context {
             description "Context used when performing access control";
             type string {
               length "0 .. 32";
             }
           }
           leaf tag {
             description "Tag identifier for set of targets allowed to use this community string";
             type string {
               length "0 .. 255";
             }
           }
         }
       }
       list proxy {
         key name;
         ordered-by user;
         description "SNMP proxy configuration";
         leaf name {
           description "Unique proxy name";
           type string;
         }
         uses apply-advanced;
         leaf device-name {
           description "Satellite/Proxied Device name or IP address";
           type string;
           mandatory true;
         }
         choice version {
           case case_1 {
             container version-v1 {
               description "For v1 proxy configuration define snmp-community";
               uses comm-object;
             }
           }
           case case_2 {
             container version-v2c {
               description "For v2c proxy configuration define snmp-community";
               uses comm-object;
             }
           }
           case case_3 {
             container version-v3 {
               description "For v3 proxy configuration define security-name";
               uses sec-object;
             }
           }
         }
         list routing-instance {
           key name;
           ordered-by user;
           description "Associate routing-instance name for proxy forwarding";
           leaf name {
             description "Routing-instance name for proxy forwarding";
             type string;
           }
           uses apply-advanced;
         }
         list logical-system {
           key name;
           ordered-by user;
           description "Associate logical-system name for proxy forwarding";
           leaf name {
             description "Associate logical-system name for proxy forwarding";
             type string {
             }
           }
           uses apply-advanced;
           list routing-instance {
             key name;
             ordered-by user;
             description "Associate routing-instance name for proxy forwarding";
             leaf name {
               description "Routing-instance name for proxy forwarding";
               type string;
             }
             uses apply-advanced;
           }
         }
         leaf nfx-host {
           description "Set routing-instance for NFX Host";
           type empty;
         }
       }
       container subagent {
         description "SNMP subagent configuration";
         uses apply-advanced;
         container tcp {
           presence "enable tcp";
           description "Allow SNMP subagent tcp connection";
           uses apply-advanced;
           container routing-instance {
             description "Specify routing-instance name for tcp connection";
             uses apply-advanced;
             leaf default {
               description "Allow connections over default routing-instance";
               type empty;
             }
           }
         }
       }
       container access {
         description "SNMPv3 access information";
         status deprecated;
         uses apply-advanced;
         list user {
           key name;
           ordered-by user;
           description "SNMPv3 USM user information";
           leaf name {
             description "SNMPv3 USM username";
             type string {
             }
           }
           uses apply-advanced;
           leaf authentication-type {
             description "SNMPv3 USM authentication type";
             type enumeration {
               enum "none" {
                 description "No authentication";
               }
               enum "md5" {
                 description "MD5 hash algorithm";
               }
               enum "sha" {
                 description "SHA hash algorithm";
               }
             }
           }
           leaf authentication-password {
             description "SNMPv3 USM authentication password";
             type jt:unreadable;
           }
           leaf privacy-type {
             description "SNMPv3 USM privacy type";
             type enumeration {
               enum "none" {
                 description "No privacy";
               }
               enum "des" {
                 description "DES algorithm";
               }
             }
           }
           leaf privacy-password {
             description "SNMPv3 USM privacy password";
             type jt:unreadable;
           }
           list clients {
             key name;
             ordered-by user;
             description "List of source address prefix ranges to accept";
             leaf name {
               description "Address or prefix";
               type jt:ipprefix;
             }
             leaf restrict {
               description "Deny access";
               type empty;
             }
           }
         }
         list group {
           key name;
           ordered-by user;
           description "SNMPv3 USM group information";
           leaf name {
             description "SNMPv3 USM group name";
             type string {
             }
           }
           uses apply-advanced;
           leaf-list user {
             ordered-by user;
             description "SNMPv3 USM username";
             type string;
           }
           leaf model {
             description "SNMPv3 security model";
             type enumeration {
               enum "usm" {
                 description "User-based security model";
               }
             }
           }
         }
         list context {
           key name;
           ordered-by user;
           description "SNMPv3 context information";
           leaf name {
             description "SNMPv3 context name";
             type string {
             }
           }
           uses apply-advanced;
           leaf description {
             description "SNMPv3 context description";
             type string;
           }
           list group {
             key name;
             ordered-by user;
             description "Access group";
             leaf name {
               description "SNMPv3 USM group name";
               type string {
               }
             }
             uses apply-advanced;
             leaf model {
               description "SNMPv3 security model";
               type enumeration {
                 enum "usm" {
                   description "User-based security model";
                 }
               }
             }
             leaf security-level {
               description "SNMPv3 security level";
               type enumeration {
                 enum "none" {
                   description "None: NoAuthNoPriv";
                 }
                 enum "authentication" {
                   description "Authentication: AuthNoPriv";
                 }
                 enum "privacy" {
                   description "Privacy: AuthPriv";
                 }
               }
             }
             leaf read-view {
               description "Read view name";
               type string {
               }
             }
             leaf write-view {
               description "Write view name";
               type string {
               }
             }
           }
         }
       }
       list view {
         key name;
         ordered-by user;
         description "Define MIB views";
         leaf name {
           description "MIB view name";
           type string {
           }
         }
         uses apply-advanced;
         list oid {
           key name;
           ordered-by user;
           description "OID include/exclude list";
           leaf name {
             description "OID to include or exclude from view";
             type string {
             }
           }
           choice view-action {
             case case_1 {
               leaf include {
                 description "Include this OID in the view";
                 type empty;
               }
             }
             case case_2 {
               leaf exclude {
                 description "Exclude this OID from the view";
                 type empty;
               }
             }
           }
         }
       }
       list client-list {
         key name;
         ordered-by user;
         description "Client list";
         leaf name {
           description "The name for the client list";
           type string {
           }
         }
         uses apply-advanced;
         list client-address-list {
           key name;
           ordered-by user;
           description "Client address list";
           uses client-address-object;
         }
       }
       list community {
         key name;
         ordered-by user;
         description "Configure a community string";
         leaf name {
           description "Community name";
           type string;
         }
         uses apply-advanced;
         leaf view {
           description "View name";
           type string;
         }
         leaf authorization {
           description "Authorization type";
           type enumeration {
             enum "read-only" {
               description "Allow read-only access";
             }
             enum "read-write" {
               description "Allow read and write access";
             }
           }
         }
         choice clients_choice {
           case case_1 {
             leaf client-list-name {
               description "The name of client list or prefix list";
               type string {
               }
             }
           }
           case case_2 {
             list clients {
               key name;
               ordered-by user;
               description "List of source address prefix ranges to accept";
               leaf name {
                 description "Address or prefix";
                 type jt:ipprefix;
               }
               leaf restrict {
                 description "Deny access";
                 type empty;
               }
             }
           }
         }
         list routing-instances {
           key name;
           ordered-by user;
           description "Use logical-system/routing-instance for v1/v2c clients";
           status deprecated;
           leaf name {
             description "Routing instance of v1/v2c clients";
             type string {
             }
           }
           uses apply-advanced;
           choice clients_choice {
             case case_1 {
               leaf client-list-name {
                 description "The name of client list or prefix list";
                 type string {
                 }
               }
             }
             case case_2 {
               list clients {
                 key name;
                 ordered-by user;
                 description "List of source address prefix ranges to accept";
                 leaf name {
                   description "Address or prefix";
                   type jt:ipprefix;
                 }
                 leaf restrict {
                   description "Deny access";
                   type empty;
                 }
               }
             }
           }
         }
         list routing-instance {
           key name;
           ordered-by user;
           description "Use routing-instance name for v1/v2c clients";
           leaf name {
             description "Routing instance of v1/v2c clients";
             type string {
             }
           }
           uses apply-advanced;
           choice clients_choice {
             case case_1 {
               leaf client-list-name {
                 description "The name of client list or prefix list";
                 type string {
                 }
               }
             }
             case case_2 {
               list clients {
                 key name;
                 ordered-by user;
                 description "List of source address prefix ranges to accept";
                 leaf name {
                   description "Address or prefix";
                   type jt:ipprefix;
                 }
                 leaf restrict {
                   description "Deny access";
                   type empty;
                 }
               }
             }
           }
         }
         list logical-system {
           key name;
           ordered-by user;
           description "Use logical-system name for v1/v2c clients";
           leaf name {
             description "Use logical-system name for v1/v2c clients";
             type string {
             }
           }
           uses apply-advanced;
           list routing-instance {
             key name;
             ordered-by user;
             description "Use routing-instance name for v1/v2c clients";
             leaf name {
               description "Routing instance of v1/v2c clients";
               type string {
               }
             }
             uses apply-advanced;
             choice clients_choice {
               case case_1 {
                 leaf client-list-name {
                   description "The name of client list or prefix list";
                   type string {
                   }
                 }
               }
               case case_2 {
                 list clients {
                   key name;
                   ordered-by user;
                   description "List of source address prefix ranges to accept";
                   leaf name {
                     description "Address or prefix";
                     type jt:ipprefix;
                   }
                   leaf restrict {
                     description "Deny access";
                     type empty;
                   }
                 }
               }
             }
           }
         }
       }
       container trap-options {
         presence "enable trap-options";
         description "SNMP trap options";
         uses apply-advanced;
         container source-address {
           description "IPv4/IPv6 source address for trap PDUs";
           uses apply-advanced;
           choice address-choice {
             case case_1 {
               leaf lo0 {
                 description "Use lowest address on loopback interface";
                 type empty;
               }
             }
             case case_2 {
               leaf address {
                 description "Use specified address";
                 type jt:ipaddr;
               }
             }
           }
         }
         leaf enterprise-oid {
           description "Add snmpTrapEnterprise oid in varbind of all traps";
           type empty;
         }
         leaf context-oid {
           description "Add context oid in varbind of all traps at the end";
           type empty;
         }
         list routing-instances {
           key name;
           ordered-by user;
           description "Use routing-instance name for source-address";
           status deprecated;
           leaf name {
             description "Routing instance of trap destination";
             type string {
             }
           }
           uses apply-advanced;
           container source-address {
             description "IPv4/IPv6 source address for trap PDUs";
             uses apply-advanced;
             choice address-choice {
               case case_1 {
                 leaf lo0 {
                   description "Use lowest address on loopback interface";
                   type empty;
                 }
               }
               case case_2 {
                 leaf address {
                   description "Use specified address";
                   type jt:ipaddr;
                 }
               }
             }
           }
         }
         list routing-instance {
           key name;
           ordered-by user;
           description "Use routing-instance name for source-address";
           leaf name {
             description "Routing instance of trap destination";
             type string {
             }
           }
           uses apply-advanced;
           container source-address {
             description "IPv4/IPv6 source address for trap PDUs";
             uses apply-advanced;
             choice address-choice {
               case case_1 {
                 leaf lo0 {
                   description "Use lowest address on loopback interface";
                   type empty;
                 }
               }
               case case_2 {
                 leaf address {
                   description "Use specified address";
                   type jt:ipaddr;
                 }
               }
             }
           }
         }
         list logical-system {
           key name;
           ordered-by user;
           description "Use logical-system name for source-address";
           leaf name {
             description "Use logical-system name for source-address";
             type string {
             }
           }
           uses apply-advanced;
           list routing-instance {
             key name;
             ordered-by user;
             description "Use routing-instance name for source-address";
             leaf name {
               description "Routing instance of trap destination";
               type string {
               }
             }
             uses apply-advanced;
             container source-address {
               description "IPv4/IPv6 source address for trap PDUs";
               uses apply-advanced;
               choice address-choice {
                 case case_1 {
                   leaf lo0 {
                     description "Use lowest address on loopback interface";
                     type empty;
                   }
                 }
                 case case_2 {
                   leaf address {
                     description "Use specified address";
                     type jt:ipaddr;
                   }
                 }
               }
             }
           }
         }
         leaf agent-address {
           description "Agent address for v1 trap PDUs";
           type enumeration {
             enum "outgoing-interface" {
               description "Use address on outgoing interface";
             }
           }
         }
       }
       list trap-group {
         key name;
         ordered-by user;
         description "Configure traps and notifications";
         leaf name {
           description "Trap group name";
           type string;
         }
         uses apply-advanced;
         leaf version {
           description "SNMP version";
           type enumeration {
             enum "all" {
               description "Send SNMPv1 and SNMPv2 traps";
             }
             enum "v1" {
               description "Send SNMPv1 traps";
             }
             enum "v2" {
               description "Send SNMPv2 traps";
             }
           }
         }
         leaf destination-port {
           description "SNMP trap receiver port number";
           type union {
             type int32;
             type string {
               pattern "<.*>|$.*";
             }
           }
         }
         container categories {
           description "Trap categories";
           uses apply-advanced;
           leaf authentication {
             description "Authentication failures";
             type empty;
           }
           leaf chassis {
             description "Chassis or environment notifications";
             type empty;
           }
           leaf link {
             description "Link up-down transitions";
             type empty;
           }
           leaf remote-operations {
             description "Remote operations";
             type empty;
           }
           leaf routing {
             description "Routing protocol notifications";
             type empty;
           }
           leaf startup {
             description "System warm and cold starts";
             type empty;
           }
           leaf ggsn {
             description "GGSN notifications";
             type empty;
           }
           leaf rmon-alarm {
             description "RMON rising and falling alarms";
             type empty;
           }
           leaf vrrp-events {
             description "VRRP notifications";
             type empty;
           }
           leaf configuration {
             description "Configuration notifications";
             type empty;
           }
           leaf services {
             description "Services notifications";
             type empty;
           }
           leaf dot3oam-events {
             description "802.3ah notifications";
             type empty;
           }
           container sonet-alarms {
             presence "enable sonet-alarms";
             description "SONET alarm trap subcategories";
             uses apply-advanced;
             leaf loss-of-light {
               description "Loss of light alarm notification";
               type empty;
             }
             leaf pll-lock {
               description "PLL lock alarm notification";
               type empty;
             }
             leaf loss-of-frame {
               description "Loss of frame alarm notification";
               type empty;
             }
             leaf loss-of-signal {
               description "Loss of signal alarm notification";
               type empty;
             }
             leaf severely-errored-frame {
               description "Severely errored frame alarm notification";
               type empty;
             }
             leaf line-ais {
               description "Line AIS alarm notification";
               type empty;
             }
             leaf path-ais {
               description "Path AIS alarm notification";
               type empty;
             }
             leaf loss-of-pointer {
               description "Loss of pointer alarm notification";
               type empty;
             }
             leaf ber-defect {
               description "Sonet bit error rate alarm defect notification";
               type empty;
             }
             leaf ber-fault {
               description "Sonet bit error rate alarm fault notification";
               type empty;
             }
             leaf line-remote-defect-indication {
               description "Line Remote Defect Indication alarm notification";
               type empty;
             }
             leaf path-remote-defect-indication {
               description "Path Remote Defect Indication alarm notification";
               type empty;
             }
             leaf remote-error-indication {
               description "Remote Error Indication alarm notification";
               type empty;
             }
             leaf unequipped {
               description "Unequipped alarm notification";
               type empty;
             }
             leaf path-mismatch {
               description "Path mismatch alarm notification";
               type empty;
             }
             leaf loss-of-cell {
               description "Loss of Cell delineation alarm notification";
               type empty;
             }
             leaf vt-ais {
               description "VT AIS alarm notification";
               type empty;
             }
             leaf vt-loss-of-pointer {
               description "VT Loss Of Pointer alarm notification";
               type empty;
             }
             leaf vt-remote-defect-indication {
               description "VT Remote Defect Indication alarm notification";
               type empty;
             }
             leaf vt-unequipped {
               description "VT Unequipped alarm notification";
               type empty;
             }
             leaf vt-label-mismatch {
               description "VT label mismatch error notification";
               type empty;
             }
             leaf vt-loss-of-cell {
               description "VT Loss of Cell delineation notification";
               type empty;
             }
           }
           container otn-alarms {
             presence "enable otn-alarms";
             description "OTN alarm trap subcategories";
             uses apply-advanced;
             leaf oc-los {
               description "Loss of signal alarm notification";
               type empty;
             }
             leaf oc-lof {
               description "Loss of frame alarm notification";
               type empty;
             }
             leaf oc-lom {
               description "Loss of multiframe alarm notification";
               type empty;
             }
             leaf wavelength-lock {
               description "Wavelength lock alarm notification";
               type empty;
             }
             leaf otu-ais {
               description "OTU Alarm indication signal alarm notification";
               type empty;
             }
             leaf otu-bdi {
               description "OTU Backward defect indication alarm notification";
               type empty;
             }
             leaf otu-ttim {
               description "OTU Trace identification mismatch alarm notification";
               type empty;
             }
             leaf otu-iae {
               description "OTU Incoming alignment error alarm notification";
               type empty;
             }
             leaf otu-sd {
               description "OTU Signal degrade alarm notification";
               type empty;
             }
             leaf otu-sf {
               description "OTU Signal fail alarm notification";
               type empty;
             }
             leaf otu-fec-exe {
               description "OTU Fec excessive errors alarm notification";
               type empty;
             }
             leaf otu-fec-deg {
               description "OTU Fec degraded errors alarm notification";
               type empty;
             }
             leaf otu-bbe-threshold {
               description "OTU Background block error threshold alarm notification";
               type empty;
             }
             leaf otu-es-threshold {
               description "OTU Errored Second threshold alarm notification";
               type empty;
             }
             leaf otu-ses-threshold {
               description "OTU Severely Errored Second threshold alarm notification";
               type empty;
             }
             leaf otu-uas-threshold {
               description "OTU Unavailable Second threshold alarm notification";
               type empty;
             }
             leaf odu-ais {
               description "ODU Alarm indication signal alarm notification";
               type empty;
             }
             leaf odu-oci {
               description "ODU Open connection indicator alarm notification";
               type empty;
             }
             leaf odu-lck {
               description "ODU Locked alarm notification";
               type empty;
             }
             leaf odu-bdi {
               description "ODU Backward defect indication alarm notification";
               type empty;
             }
             leaf odu-ttim {
               description "ODU Trace identification mismatch alarm notification";
               type empty;
             }
             leaf odu-sd {
               description "ODU Signal degrade alarm notification";
               type empty;
             }
             leaf odu-sf {
               description "ODU Signal fail alarm notification";
               type empty;
             }
             leaf odu-rx-aps-change {
               description "ODU Receive APS change notification";
               type empty;
             }
             leaf odu-bbe-threshold {
               description "ODU Background block error threshold alarm notification";
               type empty;
             }
             leaf odu-es-threshold {
               description "ODU Errored Second threshold alarm notification";
               type empty;
             }
             leaf odu-ses-threshold {
               description "ODU Severely Errored Second threshold alarm notification";
               type empty;
             }
             leaf odu-uas-threshold {
               description "ODU Unavailable Second threshold alarm notification";
               type empty;
             }
             leaf opu-ptm {
               description "ODU Payload Type Mismatch alarm notification";
               type empty;
             }
           }
         }
         list targets {
           key name;
           ordered-by user;
           description "Targets for trap messages";
           leaf name {
             description "IP address";
             type jt:hostname;
           }
         }
         leaf routing-instance {
           description "Routing instance for trap destination";
           type string {
           }
         }
         leaf logical-system {
           description "Logical-system name for trap destination";
           type string {
           }
         }
       }
       container routing-instance-access {
         presence "enable routing-instance-access";
         description "SNMP routing-instance options";
         uses apply-advanced;
         list access-list {
           key name;
           description "Allow/Deny SNMP access to routing-instances";
           leaf name {
             description "Routing-instance in format <name>, <prefix>* or *";
             type string {
             }
           }
           leaf restrict {
             description "Deny access";
             type empty;
           }
         }
       }
       leaf logical-system-trap-filter {
         description "Allow only logical-system specific traps";
         type empty;
       }
       container traceoptions {
         description "Trace options for SNMP";
         uses apply-advanced;
         container memory-trace {
           presence "enable memory-trace";
           description "Memory tracing information";
           uses apply-advanced;
           leaf size {
             description "Memory size reserved for tracing ";
             default "5120";
             units "kilobytes";
             type union {
               type string {
                 pattern "<.*>|$.*";
               }
               type uint32 {
                 range "1250 .. 12500";
               }
             }
           }
         }
         leaf no-remote-trace {
           description "Disable remote tracing";
           type empty;
         }
         container file {
           description "Trace file information";
           leaf size {
             description "Maximum trace file size";
             units "bytes";
             type string;
           }
           leaf files {
             description "Maximum number of trace files";
             default "10";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "timer" {
                 description "Trace internal timer events";
               }
               enum "protocol-timeouts" {
                 description "Trace SNMP request timeouts";
               }
               enum "pdu" {
                 description "Dump SNMP request/response packets";
               }
               enum "varbind-error" {
                 description "Trace varbind errors";
               }
               enum "routing-socket" {
                 description "Trace routing socket calls";
               }
               enum "interface-stats" {
                 description "Trace interface statistics (logical and physical)";
               }
               enum "subagent" {
                 description "Trace master-agent interations with sub-agents";
               }
               enum "general" {
                 description "Trace general events";
               }
               enum "nonvolatile-sets" {
                 description "Nonvolatile SNMP set request handling";
               }
               enum "all" {
                 description "Trace everything";
               }
             }
           }
         }
       }
       container rmon {
         presence "enable rmon";
         description "Remote Monitoring configuration";
         uses apply-advanced;
         list history {
           key name;
           ordered-by user;
           description "RMON history entries";
           leaf name {
             description "RMON history identifier";
             type union {
               type string {
                 pattern "<.*>|$.*";
               }
               type uint32 {
                 range "1 .. 65535";
               }
             }
           }
           uses apply-advanced;
           leaf interface {
             description "Enable RMON on this interface";
             type union {
               type jt:interface-name;
               type string {
                 pattern "<.*>|$.*";
               }
             }
             mandatory true;
           }
           leaf bucket-size {
             description "Requested buckets for the interface";
             default "50";
             type union {
               type string {
                 pattern "<.*>|$.*";
               }
               type uint32 {
                 range "1 .. 65535";
               }
             }
           }
           leaf interval {
             description "Interval between samples";
             default "1800";
             units "seconds";
             type union {
               type string {
                 pattern "<.*>|$.*";
               }
               type uint32 {
                 range "1 .. 2147483647";
               }
             }
           }
           leaf owner {
             description "Owner name of the entry";
             type string {
             }
           }
         }
         list alarm {
           key name;
           ordered-by user;
           description "RMON alarm entries";
           leaf name {
             description "RMON alarm identifier";
             type union {
               type string {
                 pattern "<.*>|$.*";
               }
               type uint32 {
                 range "1 .. 65535";
               }
             }
           }
           uses apply-advanced;
           leaf description {
             description "General description of alarm (stored in alarmOwner)";
             type string {
             }
           }
           leaf interval {
             description "Interval between samples";
             default "60";
             units "seconds";
             type union {
               type string {
                 pattern "<.*>|$.*";
               }
               type uint32 {
                 range "1 .. 2147483647";
               }
             }
           }
           leaf falling-threshold-interval {
             description "Interval between samples during falling-threshold test";
             default "2147483647";
             units "seconds";
             type union {
               type string {
                 pattern "<.*>|$.*";
               }
               type uint32 {
                 range "1 .. 2147483647";
               }
             }
           }
           leaf variable {
             description "OID of MIB variable to be monitored";
             type string {
             }
             mandatory true;
           }
           leaf sample-type {
             description "Method of sampling the selected variable";
             type enumeration {
               enum "absolute-value" {
                 description "Absolute sample value is used";
               }
               enum "delta-value" {
                 description "Difference between sampled values is used";
               }
             }
             mandatory true;
           }
           leaf request-type {
             description "Type of SNMP request to issue for alarm";
             default "get-request";
             type enumeration {
               enum "get-request" {
                 description "Get request";
               }
               enum "get-next-request" {
                 description "Get-next request";
               }
               enum "walk-request" {
                 description "Walk request";
               }
             }
           }
           leaf startup-alarm {
             description "The alarm that may be sent upon entry startup";
             default "rising-or-falling-alarm";
             type enumeration {
               enum "rising-alarm" {
                 description "Rising alarm may be sent at startup";
               }
               enum "falling-alarm" {
                 description "Falling alarm may be sent at startup";
               }
               enum "rising-or-falling-alarm" {
                 description "Rising or falling alarm may be sent at startup";
               }
             }
           }
           leaf rising-threshold {
             description "The rising threshold";
             type union {
               type int32;
               type string {
                 pattern "<.*>|$.*";
               }
             }
             mandatory true;
           }
           leaf falling-threshold {
             description "The falling threshold";
             default "2147483647";
             type union {
               type int32;
               type string {
                 pattern "<.*>|$.*";
               }
             }
           }
           leaf rising-event-index {
             description "Event triggered after rising threshold is crossed";
             default "0";
             type union {
               type string {
                 pattern "<.*>|$.*";
               }
               type int32 {
                 range "0 .. 65535";
               }
             }
           }
           leaf falling-event-index {
             description "Event triggered after falling threshold is crossed";
             default "0";
             type union {
               type string {
                 pattern "<.*>|$.*";
               }
               type int32 {
                 range "0 .. 65535";
               }
             }
           }
           leaf syslog-subtag {
             description "Tag to be added to syslog messages";
             type string {
             }
           }
         }
         list event {
           key name;
           ordered-by user;
           description "RMON event entries";
           leaf name {
             description "RMON event identifier";
             type union {
               type string {
                 pattern "<.*>|$.*";
               }
               type uint32 {
                 range "1 .. 65535";
               }
             }
           }
           uses apply-advanced;
           leaf description {
             description "General description of event";
             type string {
             }
           }
           leaf type {
             description "The type of notification for this event";
             default "log-and-trap";
             type enumeration {
               enum "none" {
                 description "No notifications";
               }
               enum "log" {
                 description "Add entry to logTable";
               }
               enum "snmptrap" {
                 description "Send SNMP trap";
               }
               enum "log-and-trap" {
                 description "Send SNMP trap and make log entry";
               }
             }
           }
           leaf community {
             description "The community (trap group) for outgoing traps";
             type string {
             }
           }
         }
       }
       container health-monitor {
         presence "enable health-monitor";
         description "Health monitoring configuration";
         uses apply-advanced;
         leaf interval {
           description "Interval between samples";
           units "seconds";
           type union {
             type string {
               pattern "<.*>|$.*";
             }
             type uint32 {
               range "1 .. 2147483647";
             }
           }
         }
         leaf rising-threshold {
           description "Rising threshold applied to all monitored objects";
           units "percent";
           type union {
             type string {
               pattern "<.*>|$.*";
             }
             type uint32 {
               range "1 .. 100";
             }
           }
         }
         leaf falling-threshold {
           description "Falling threshold applied to all monitored objects";
           units "percent";
           type union {
             type string {
               pattern "<.*>|$.*";
             }
             type uint32 {
               range "0 .. 100";
             }
           }
         }
         container idp {
           presence "enable idp";
           description "IDP health monitor configuration";
           uses apply-advanced;
           leaf interval {
             description "Interval between samples";
             units "seconds";
             type union {
               type string {
                 pattern "<.*>|$.*";
               }
               type uint32 {
                 range "1 .. 2147483647";
               }
             }
           }
           leaf rising-threshold {
             description "Rising threshold applied to all monitored objects";
             units "percent";
             type union {
               type string {
                 pattern "<.*>|$.*";
               }
               type uint32 {
                 range "0 .. 100";
               }
             }
           }
           leaf falling-threshold {
             description "Falling threshold applied to all monitored objects";
             units "percent";
             type union {
               type string {
                 pattern "<.*>|$.*";
               }
               type uint32 {
                 range "0 .. 100";
               }
             }
           }
         }
       }
       container arp {
         presence "enable arp";
         description "JVision ARP settings";
         uses apply-advanced;
         leaf host-name-resolution {
           description "Enable host name resolution";
           type empty;
         }
       }
       container customization {
         description "Customize SNMP behaviour based on knob";
         uses apply-advanced;
         leaf ether-stats-ifd-only {
           description "To stop exposing IFLs as part of etherStatsTable";
           type empty;
         }
       }
     }
     container forwarding-options {
       description "Configure options to control packet forwarding";
       uses juniper-forwarding-options;
     }
     container event-options {
       description "Event processing configuration";
       uses apply-advanced;
       leaf max-policies {
         description "Number of policies that can be executed simultaneously";
         default "15";
         type union {
           type string {
             pattern "<.*>|$.*";
           }
           type uint32 {
             range "0 .. 20";
           }
         }
       }
       container flood-control {
         description "Flood control configuration";
         uses apply-advanced;
         list daemon-name {
           key name;
           ordered-by user;
           description "Per-daemon flood control configuration";
           leaf name {
             description "Specific daemon name to apply flood control";
             type string;
           }
           uses apply-advanced;
           leaf facility {
             description "Syslog facility for flood control filtering";
             type enumeration {
               enum "authorization" {
                 description "Authorization system";
               }
               enum "daemon" {
                 description "Various system processes";
               }
               enum "ftp" {
                 description "FTP process";
               }
               enum "ntp" {
                 description "NTP process";
               }
               enum "security" {
                 description "Security related";
               }
               enum "kernel" {
                 description "Kernel";
               }
               enum "user" {
                 description "User processes";
               }
               enum "dfc" {
                 description "Dynamic flow capture";
               }
               enum "external" {
                 description "Local external applications";
               }
               enum "firewall" {
                 description "Firewall filtering system";
               }
               enum "pfe" {
                 description "Packet Forwarding Engine";
               }
               enum "conflict-log" {
                 description "Configuration conflict log";
               }
               enum "change-log" {
                 description "Configuration change log";
               }
               enum "interactive-commands" {
                 description "Commands executed by the UI";
               }
             }
           }
           leaf threshold {
             description "Maximum number of events per second allowed from this daemon";
             default "20";
             type union {
               type string {
                 pattern "<.*>|$.*";
               }
               type uint32 {
                 range "1 .. 1000";
               }
             }
           }
           leaf priority-threshold {
             description "Priority threshold for flood control (0=emerg to 7=debug)";
             default "6";
             type union {
               type string {
                 pattern "<.*>|$.*";
               }
               type uint32 {
                 range "0 .. 7";
               }
             }
           }
         }
       }
       list generate-event {
         key name;
         ordered-by user;
         description "Generate an internal event";
         max-elements 10;
         leaf name {
           description "Name of the event to be generated";
           type string {
             length "1 .. 63";
           }
         }
         choice time_choice {
           case case_1 {
             leaf time-of-day {
               description "Time of day at which to generate event (hh:mm:ss)";
               type jt:time-of-day;
             }
           }
           case case_2 {
             leaf time-interval {
               description "Frequency for generating the event";
               units "seconds";
               type union {
                 type string {
                   pattern "<.*>|$.*";
                 }
                 type uint32 {
                   range "60 .. 2592000";
                 }
               }
             }
           }
         }
         leaf start-time {
           description "Start-time to generate event (yyyy-mm-dd.hh:mm)";
           type jt:time;
         }
         leaf no-drift {
           description "Avoid event generation delay propagating to next event";
           type empty;
         }
       }
       list policy {
         key name;
         ordered-by user;
         description "Event policy for event policy manager";
         leaf name {
           description "Name of policy";
           type string {
             length "1 .. 63";
           }
         }
         uses apply-advanced;
         leaf-list events {
           ordered-by user;
           description "List of events that trigger this policy";
           type string;
         }
         list within {
           key name;
           ordered-by user;
           description "List of events correlated with trigering events";
           leaf name {
             description "Time within which correlated events must occur (or not)";
             units "seconds";
             type union {
               type string {
                 pattern "<.*>|$.*";
               }
               type uint32 {
                 range "1 .. 604800";
               }
             }
           }
           uses apply-advanced;
           container trigger {
             description "Correlate events based on the number of occurrences";
             choice when {
               case case_1 {
                 leaf until {
                   description "Trigger when occurrences of triggering event < 'count'";
                   type empty;
                 }
               }
               case case_2 {
                 leaf on {
                   description "Trigger when occurrences of triggering event = 'count'";
                   type empty;
                 }
               }
               case case_3 {
                 leaf after {
                   description "Trigger when occurrences of triggering event > 'count'";
                   type empty;
                 }
               }
             }
             leaf count {
               description "Number of occurrences of triggering event";
               type union {
                 type uint32;
                 type string {
                   pattern "<.*>|$.*";
                 }
               }
               mandatory true;
             }
           }
           leaf-list events {
             ordered-by user;
             description "List of events that must occur within time interval";
             type string;
           }
           container not {
             description "Events must not occur within time interval";
             leaf-list events {
               ordered-by user;
               description "List of events that must not occur within time interval";
               type string;
             }
           }
         }
         list attributes-match {
           key "from-event-attribute condition to-event-attribute-value";
           ordered-by user;
           description "List of attributes to compare for two events";
           leaf from-event-attribute {
             description "First attribute to compare";
             type string {
             }
           }
           leaf condition {
             description "Relationship that must hold between attributes";
             type enumeration {
               enum "equals" {
                 description "Attributes match";
               }
               enum "starts-with" {
                 description "Second attribute starts with first attribute value";
               }
               enum "matches" {
                 description "Regular expression matching the first attribute value";
               }
             }
           }
           leaf to-event-attribute-value {
             description "Second attribute or value to compare";
             type string;
           }
         }
         container then {
           description "List of actions to perform when policy matches";
           uses apply-advanced;
           leaf ignore {
             description "Do not log event or perform any other action";
             type empty;
           }
           container priority-override {
             description "Change syslog priority value";
             uses apply-advanced;
             leaf facility {
               description "Facility type";
               type enumeration {
                 enum "authorization" {
                   description "Authorization system";
                 }
                 enum "daemon" {
                   description "Various system processes";
                 }
                 enum "ftp" {
                   description "FTP process";
                 }
                 enum "ntp" {
                   description "NTP process";
                 }
                 enum "security" {
                   description "Security related";
                 }
                 enum "kernel" {
                   description "Kernel";
                 }
                 enum "user" {
                   description "User processes";
                 }
                 enum "dfc" {
                   description "Dynamic flow capture";
                 }
                 enum "external" {
                   description "Local external applications";
                 }
                 enum "firewall" {
                   description "Firewall filtering system";
                 }
                 enum "pfe" {
                   description "Packet Forwarding Engine";
                 }
                 enum "conflict-log" {
                   description "Configuration conflict log";
                 }
                 enum "change-log" {
                   description "Configuration change log";
                 }
                 enum "interactive-commands" {
                   description "Commands executed by the UI";
                 }
               }
             }
             leaf severity {
               description "Severity type";
               type enumeration {
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
               }
             }
           }
           list upload {
             key "filename destination";
             ordered-by user;
             description "Upload file to specified destination";
             leaf filename {
               description "Name of file to upload";
               type string;
             }
             leaf destination {
               description "Location to which to output file";
               type string;
             }
             uses apply-advanced;
             leaf user-name {
               description "User under whose privileges upload action will execute";
               type string;
             }
             leaf transfer-delay {
               description "Delay before uploading file to the destination";
               units "seconds";
               type union {
                 type uint32;
                 type string {
                   pattern "<.*>|$.*";
                 }
               }
             }
             container retry-count {
               description "Upload output-filename retry attempt count";
               leaf retry {
                 description "Number of retry attempts";
                 type union {
                   type string {
                     pattern "<.*>|$.*";
                   }
                   type uint8 {
                     range "0 .. 10";
                   }
                 }
                 mandatory true;
               }
               leaf retry-interval {
                 description "Time interval between each retry";
                 units "seconds";
                 type union {
                   type uint32;
                   type string {
                     pattern "<.*>|$.*";
                   }
                 }
                 mandatory true;
               }
             }
           }
           container change-configuration {
             description "Change configuration";
             uses apply-advanced;
             container retry {
               description "Change configuration retry attempt count";
               leaf count {
                 description "Number of retry attempts";
                 type union {
                   type string {
                     pattern "<.*>|$.*";
                   }
                   type uint8 {
                     range "0 .. 10";
                   }
                 }
                 mandatory true;
               }
               leaf interval {
                 description "Time interval between each retry";
                 units "seconds";
                 type union {
                   type uint32;
                   type string {
                     pattern "<.*>|$.*";
                   }
                 }
                 mandatory true;
               }
             }
             list commands {
               key name;
               ordered-by user;
               description "List of configuration commands";
               leaf name {
                 description "Configuration command to issue";
                 type string;
               }
               uses apply-advanced;
             }
             leaf user-name {
               description "User under whose privileges configuration should be changed";
               type string;
             }
             container commit-options {
               description "List of commit options";
               uses apply-advanced;
               container check {
                 presence "enable check";
                 description "Check correctness of syntax; do not apply changes";
                 uses apply-advanced;
                 leaf synchronize {
                   description "Synchronize commit on both Routing Engines";
                   type empty;
                 }
               }
               leaf synchronize {
                 description "Synchronize commit on both Routing Engines";
                 type empty;
               }
               leaf force {
                 description "Force commit on other Routing Engine (ignore warnings)";
                 type empty;
               }
               leaf log {
                 description "Message to write to commit log";
                 type string {
                   length "1 .. 512";
                 }
               }
             }
           }
           container execute-commands {
             description "Issue one or more CLI commands";
             uses apply-advanced;
             list commands {
               key name;
               ordered-by user;
               description "List of CLI commands to issue";
               leaf name {
                 description "CLI command to issue";
                 type string;
               }
               uses apply-advanced;
             }
             leaf user-name {
               description "User under whose privileges command will execute";
               type string;
             }
             leaf output-filename {
               description "Name of file in which to write command output";
               type string {
               }
             }
             list destination {
               key name;
               ordered-by user;
               description "Location to which to upload command output";
               max-elements 1;
               leaf name {
                 description "Location to which to upload command output";
                 type string;
               }
               uses apply-advanced;
               leaf transfer-delay {
                 description "Delay before uploading file to the destination";
                 units "seconds";
                 type union {
                   type uint32;
                   type string {
                     pattern "<.*>|$.*";
                   }
                 }
               }
               container retry-count {
                 description "Upload output-filename retry attempt count";
                 leaf retry {
                   description "Number of retry attempts";
                   type union {
                     type string {
                       pattern "<.*>|$.*";
                     }
                     type uint8 {
                       range "0 .. 10";
                     }
                   }
                   mandatory true;
                 }
                 leaf retry-interval {
                   description "Time interval between each retry";
                   units "seconds";
                   type union {
                     type uint32;
                     type string {
                       pattern "<.*>|$.*";
                     }
                   }
                   mandatory true;
                 }
               }
             }
             leaf output-format {
               description "Format of output from CLI commands";
               default "xml";
               type enumeration {
                 enum "text" {
                   description "Formatted ASCII text";
                 }
                 enum "xml" {
                   description "JUNOS XML tags";
                 }
               }
             }
           }
           list event-script {
             key name;
             ordered-by user;
             description "Invoke event scripts";
             leaf name {
               description "Local filename of the script file";
               type string {
                 length "1 .. 254";
               }
             }
             uses apply-advanced;
             list arguments {
               key name;
               ordered-by user;
               description "Command line argument to the script";
               leaf name {
                 description "Name of the argument";
                 type string {
                   length "1 .. 254";
                 }
               }
               leaf value {
                 description "Value of the argument";
                 type string;
                 mandatory true;
               }
             }
             leaf user-name {
               description "User under whose privileges event script will execute";
               type string;
             }
             leaf output-filename {
               description "Name of file in which to write event script output";
               type string {
               }
             }
             list destination {
               key name;
               ordered-by user;
               description "Location to which to upload event script output";
               max-elements 1;
               leaf name {
                 description "Location to which to upload event script output";
                 type string;
               }
               uses apply-advanced;
               leaf transfer-delay {
                 description "Delay before uploading files";
                 units "seconds";
                 type union {
                   type uint32;
                   type string {
                     pattern "<.*>|$.*";
                   }
                 }
               }
               container retry-count {
                 description "Upload output-filename retry attempt count";
                 leaf retry {
                   description "Number of retry attempts";
                   type union {
                     type string {
                       pattern "<.*>|$.*";
                     }
                     type uint8 {
                       range "0 .. 10";
                     }
                   }
                   mandatory true;
                 }
                 leaf retry-interval {
                   description "Time interval between each retry";
                   units "seconds";
                   type union {
                     type uint32;
                     type string {
                       pattern "<.*>|$.*";
                     }
                   }
                   mandatory true;
                 }
               }
             }
             leaf output-format {
               description "Format of output from event-script";
               type enumeration {
                 enum "text" {
                   description "Formatted ASCII text";
                 }
                 enum "xml" {
                   description "JUNOS XML tags";
                 }
               }
             }
           }
           leaf raise-trap {
             description "Raise SNMP trap";
             type empty;
           }
         }
       }
       container event-script {
         description "Configure event-scripts";
         uses apply-advanced;
         leaf optional {
           description "Allow commit to succeed if the script is missing";
           type empty;
         }
         leaf max-datasize {
           description "Maximum data segment size for scripts execution";
           units "bytes";
           type string;
         }
         container dampen {
           presence "enable dampen";
           description "Run event scripts in dampen mode";
           uses apply-advanced;
           container dampen-options {
             description "Dampen options for event scripts";
             uses apply-advanced;
             leaf cpu-factor {
               description "CPU factor at which to pause";
               type union {
                 type string {
                   pattern "<.*>|$.*";
                 }
                 type uint32 {
                   range "1 .. 100";
                 }
               }
             }
             leaf line-interval {
               description "Line interval at which to pause";
               type union {
                 type string {
                   pattern "<.*>|$.*";
                 }
                 type uint32 {
                   range "1 .. 4294967295";
                 }
               }
             }
             leaf time-interval {
               description "Time to pause";
               units "microseconds";
               type union {
                 type string {
                   pattern "<.*>|$.*";
                 }
                 type uint32 {
                   range "1 .. 4294967295";
                 }
               }
             }
           }
         }
         container start {
           description "Start event scripts with start-criteria check";
           uses apply-advanced;
           container start-options {
             description "Start options for event scripts";
             uses apply-advanced;
             leaf mem-factor {
               description "Memory factor at which to start/stop";
               type union {
                 type string {
                   pattern "<.*>|$.*";
                 }
                 type uint32 {
                   range "1 .. 100";
                 }
               }
             }
           }
         }
         container traceoptions {
           description "Trace options for event scripts";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
           }
           list flag {
             key name;
             description "Tracing parameters";
             leaf name {
               type enumeration {
                 enum "events" {
                   description "Trace important events";
                 }
                 enum "input" {
                   description "Trace script input data";
                 }
                 enum "offline" {
                   description "Generate data for offline development";
                 }
                 enum "output" {
                   description "Trace script output data";
                 }
                 enum "rpc" {
                   description "Trace script RPCs";
                 }
                 enum "xslt" {
                   description "Trace the XSLT library";
                 }
                 enum "all" {
                   description "Trace all operations";
                 }
               }
             }
           }
         }
         list file {
           key name;
           ordered-by user;
           description "File name for event script";
           leaf name {
             description "Local filename of the script file";
             type string {
               length "1 .. 254";
             }
           }
           uses apply-advanced;
           leaf source {
             description "URL of source for this script";
             type string {
               length "1 .. 254";
             }
           }
           leaf cert-file {
             description "Specify the ca certificate file name";
             type string;
           }
           leaf python-script-user {
             description "Run the python event script with privileges of user";
             type string;
           }
           container dampen {
             presence "enable dampen";
             description "Run script in dampen mode";
             uses apply-advanced;
             container dampen-options {
               description "Dampen options for the script";
               uses apply-advanced;
               leaf cpu-factor {
                 description "CPU factor at which to pause";
                 type union {
                   type string {
                     pattern "<.*>|$.*";
                   }
                   type uint32 {
                     range "1 .. 100";
                   }
                 }
               }
               leaf line-interval {
                 description "Line interval at which to pause";
                 type union {
                   type string {
                     pattern "<.*>|$.*";
                   }
                   type uint32 {
                     range "1 .. 4294967295";
                   }
                 }
               }
               leaf time-interval {
                 description "Time to pause";
                 units "microseconds";
                 type union {
                   type string {
                     pattern "<.*>|$.*";
                   }
                   type uint32 {
                     range "1 .. 4294967295";
                   }
                 }
               }
             }
           }
           container start {
             description "Start script with start-criteria check";
             uses apply-advanced;
             container start-options {
               description "Start options for the event script";
               uses apply-advanced;
               leaf mem-factor {
                 description "Memory factor at which to start/stop";
                 type union {
                   type string {
                     pattern "<.*>|$.*";
                   }
                   type uint32 {
                     range "1 .. 100";
                   }
                 }
               }
             }
           }
           leaf routing-instance {
             description "Routing instance";
             type string {
             }
           }
           leaf refresh {
             description "Refresh all operation scripts from their source";
             type empty;
           }
           leaf refresh-from {
             description "Refresh all operation scripts from a given base URL";
             type string {
               length "1 .. 254";
             }
           }
           container checksum {
             description "Checksum of this script";
             uses apply-advanced;
             leaf sha-256 {
               description "SHA-256 checksum of this script";
               type string {
                 length "1 .. 254";
               }
             }
           }
           list remote-execution {
             key name;
             ordered-by user;
             description "Remote login username and password details for script";
             leaf name {
               description "Remote hostname";
               type string {
                 length "1 .. 255";
               }
             }
             uses apply-advanced;
             leaf username {
               description "SSH username for login into the remote host";
               type string {
               }
               mandatory true;
             }
             leaf passphrase {
               description "SSH passphrase for login into the remote host";
               type jt:unreadable;
               mandatory true;
             }
           }
         }
         leaf refresh {
           description "Refresh all operation scripts from their source";
           type empty;
         }
         leaf refresh-from {
           description "Refresh all operation scripts from a given base URL";
           type string {
             length "1 .. 254";
           }
         }
       }
       list destinations {
         key name;
         ordered-by user;
         description "List of destinations referred to in 'then' clause";
         leaf name {
           description "Destination name";
           type string;
         }
         uses apply-advanced;
         leaf transfer-delay {
           description "Delay before transferring files";
           default "0";
           units "seconds";
           type union {
             type uint32;
             type string {
               pattern "<.*>|$.*";
             }
           }
         }
         list archive-sites {
           key name;
           ordered-by user;
           description "List of archive destinations";
           leaf name {
             description "URL of destination for file";
             type string;
           }
           leaf password {
             description "Password for login into the archive site";
             type jt:unreadable;
           }
           leaf routing-instance {
             description "Routing instance";
             type string {
             }
           }
         }
       }
       container traceoptions {
         description "Trace options for the event processing daemon";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "List of event types to include in trace";
           leaf name {
             type enumeration {
               enum "server" {
                 description "Communication with processes that are generating events";
               }
               enum "configuration" {
                 description "Reading of configuration";
               }
               enum "events" {
                 description "Event processing";
               }
               enum "timer-events" {
                 description "Internally generated events";
               }
               enum "database" {
                 description "Events involving storage and retrieval in events database";
               }
               enum "policy" {
                 description "Policy processing";
               }
               enum "registration" {
                 description "Event registration";
               }
               enum "syslogd" {
                 description "Syslog related traces";
               }
               enum "all" {
                 description "Everything";
               }
             }
           }
         }
       }
     }
     container accounting-options {
       description "Accounting data configuration";
       uses juniper_accounting_options;
     }
     container policy-options {
       description "Policy option configuration";
       uses juniper-policy-options;
     }
     container class-of-service {
       description "Class-of-service configuration";
       uses juniper-class-of-service-options;
     }
     container firewall {
       description "Define a firewall configuration";
       uses apply-advanced;
       container family {
         description "Protocol family";
         container inet {
           description "Protocol family IPv4 for firewall filter";
           uses apply-advanced;
           list prefix-action {
             key name;
             ordered-by user;
             description "Define a prefix action";
             uses prefix_action;
           }
           list filter {
             key name;
             description "Define an IPv4 firewall filter";
             uses inet_filter;
           }
           list service-filter {
             key name;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list filter {
             key name;
             description "Define an IPv6 firewall filter";
             uses inet6_filter;
           }
           list service-filter {
             key name;
             description "One or more IPv6 service filters";
             uses inet6_service_filter;
           }
           list fast-update-filter {
             key name;
             ordered-by user;
             description "One or more fast update filters";
             uses inet6_fuf;
           }
         }
         container vpls {
           description "Protocol family VPLS for firewall filter";
           uses apply-advanced;
           list filter {
             key name;
             uses vpls_filter;
           }
         }
         container evpn {
           description "Protocol family EVPN for firewall filter";
           uses apply-advanced;
           list filter {
             key name;
             uses vpls_filter;
           }
         }
         container ccc {
           description "Protocol family CCC for firewall filter";
           uses apply-advanced;
           list filter {
             key name;
             uses ccc_filter;
           }
         }
         container any {
           description "Protocol-independent filter";
           uses apply-advanced;
           list filter {
             key name;
             description "Define a protocol independent filter";
             uses any_filter;
           }
         }
         container ethernet-switching {
           description "Protocol family Ethernet Switching for firewall filter";
           uses apply-advanced;
           list filter {
             key name;
             description "Define an Ethernet Switching firewall filter";
             uses es_filter;
           }
         }
       }
       list policer {
         key name;
         description "Policer template definition";
         uses firewall_policer;
       }
       list flexible-match {
         key name;
         description "Flexible packet match template definition";
         uses firewall_flexible_match;
       }
       list tunnel-end-point {
         key name;
         description "Tunnel end-point template definition";
         uses tunnel_end_point;
       }
       list hierarchical-policer {
         key name;
         description "Hierarchical policer template definition";
         uses firewall_hierpolicer;
       }
       leaf disable-arp-policers {
         description "Disables ARP policers";
         type empty;
       }
       list interface-set {
         key name;
         description "Interface set definition";
         uses interface_set_type;
       }
       list filter {
         key name;
         description "Define an IPv4 firewall filter";
         uses inet_filter;
       }
     }
     container unified-edge {
       uses apply-advanced;
       container cos-cac {
         description "Unified Edge COS configuration";
         status deprecated;
         uses juniper-unified-edge-cos-options;
       }
       list local-policies {
         key name;
         ordered-by user;
         description "Local policy profiles";
         status deprecated;
         max-elements 8001;
         leaf name {
           description "Local policy profile name";
           type string {
           }
         }
         uses apply-advanced;
         leaf description {
           description "Text description of local policy";
           type string;
         }
         leaf resource-threshold-profile {
           description "Resource threshold profile associated with the local policy";
           type string;
         }
         leaf classifier-profile {
           description "QoS class profile associated with the local policy";
           type string;
         }
         leaf cos-policy-profile {
           description "QoS policy profile associated with the local policy";
           type string;
         }
         leaf roamer-classifier-profile {
           description "QoS classifier profile for roamers";
           type string;
         }
         leaf roamer-cos-policy-profile {
           description "QoS policy profile for roamers";
           type string;
         }
         leaf visitor-classifier-profile {
           description "QoS classifier profile for visitor";
           type string;
         }
         leaf visitor-cos-policy-profile {
           description "QoS policy profile for visitor";
           type string;
         }
         leaf traffic-class-qci-mapping-profile {
           description "Traffic class to qci mapping profile";
           type string {
             length "1 .. 128";
           }
         }
         leaf ul-bandwidth-pool {
           description "Bandwidth pool associated with the local policy";
           type string;
         }
         leaf dl-bandwidth-pool {
           description "Bandwidth pool associated with the local policy";
           type string;
         }
       }
     }
     container jsrc {
       description "JSRC partition configuration";
       uses jsrc-options;
     }
     container vmhost {
       description "VM Host configurations";
       uses apply-advanced;
       leaf no-auto-recovery {
         description "Disable Guest auto recovery by the host";
         type empty;
       }
       container management-if {
         presence "enable management-if";
         description "Configuration for the host's side management interface";
         uses apply-advanced;
         leaf link-mode {
           description "Link operational mode";
           default "automatic";
           type enumeration {
             enum "automatic" {
               description "Automatically negotiate duplex";
             }
             enum "half-duplex" {
               description "Half-duplex operation";
             }
             enum "full-duplex" {
               description "Full-duplex operation";
             }
           }
         }
         leaf speed {
           description "Link speed";
           default "automatic";
           type enumeration {
             enum "automatic" {
               description "Automatically negotiate speed";
             }
             enum "10m" {
               description "10Mbps operation";
             }
             enum "100m" {
               description "100Mbps operation";
             }
             enum "1g" {
               description "1Gbps operation";
             }
           }
         }
         leaf disable {
           description "Administratively disable the management port";
           type empty;
         }
       }
       container resize {
         description "Resize the resource allocation of guest VM";
         uses apply-advanced;
         container vjunos {
           description "Vjunos/adminjunos VM";
           uses apply-advanced;
           leaf compact {
             description "Reduce the resource allocation of vjunos VM";
             type empty;
             mandatory true;
           }
         }
       }
       list interfaces {
         key name;
         ordered-by user;
         description "Interface configuration";
         leaf name {
           type enumeration {
             enum "management-if0" {
               description "Configuration for the host's side management interface0";
             }
             enum "management-if1" {
               description "Configuration for the host's side management interface1";
             }
           }
         }
         uses apply-advanced;
         container family {
           description "Protocol family";
           container inet {
             presence "enable inet";
             description "IPv4 parameters";
             uses apply-advanced;
             list address {
               key name;
               ordered-by user;
               description "Interface address/destination prefix";
               leaf name {
                 description "Interface address/destination prefix";
                 type jt:ipv4prefix;
               }
               uses apply-advanced;
               leaf master-only {
                 description "Master management IP address for host";
                 type empty;
               }
             }
             leaf gateway {
               description "Gateway IP address";
               type jt:ipv4addr;
               mandatory true;
             }
           }
           container inet6 {
             presence "enable inet6";
             description "IPv6 parameters";
             uses apply-advanced;
             list address {
               key name;
               ordered-by user;
               description "Interface address/destination prefix";
               leaf name {
                 description "Interface address/destination prefix";
                 type jt:ipv6prefix;
               }
               uses apply-advanced;
               leaf master-only {
                 description "Master management IP address for host";
                 type empty;
               }
             }
             leaf gateway {
               description "Gateway IP address";
               type jt:ipv6addr;
               mandatory true;
             }
           }
         }
       }
       container syslog {
         presence "enable syslog";
         description "VMhost logging facility";
         uses apply-advanced;
         list file {
           key name;
           description "File in which to log data";
           leaf name {
             description "Name of file in which to log data";
             type string {
               length "1 .. 1024";
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
         }
         list host {
           key name;
           ordered-by user;
           description "Host to be notified";
           leaf name {
             description "Host to be notified";
             type string {
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
           leaf transport {
             description "Transport type";
             default "udp";
             type enumeration {
               enum "tcp" {
                 description "TCP as transport of syslog";
               }
               enum "udp" {
                 description "UDP as transport of syslog";
               }
             }
           }
         }
       }
       container services {
         presence "enable services";
         description "System services";
         uses apply-advanced;
         container ssh {
           presence "enable ssh";
           description "Allow ssh access";
           uses apply-advanced;
           leaf root-login {
             description "Configure vmhost root access via ssh";
             type enumeration {
               enum "allow" {
                 description "Allow root access via ssh";
               }
               enum "deny" {
                 description "Do not allow root access via ssh";
               }
             }
           }
         }
       }
     }
     container applications {
       description "Define applications by protocol characteristics";
       uses apply-advanced;
       list application {
         key name;
         ordered-by user;
         description "Define an application";
         uses application_object;
       }
       list application-set {
         key name;
         ordered-by user;
         description "Define an application set";
         uses application_set_object;
       }
     }
     container diameter {
       presence "enable diameter";
       description "Diameter protocol layer";
       uses apply-advanced;
       container origin {
         presence "enable origin";
         description "Origin attributes of this diameter instance";
         uses apply-advanced;
         leaf realm {
           description "Origin realm of this diameter instance";
           type string {
             length "1 .. 255";
           }
           mandatory true;
         }
         leaf host {
           description "Origin host of this diameter instance";
           type string {
             length "1 .. 255";
           }
           mandatory true;
         }
       }
       list network-element {
         key name;
         ordered-by user;
         description "Network element of this diameter instance";
         leaf name {
           description "Name for this network element";
           type string {
             length "1 .. 255";
           }
         }
         uses apply-advanced;
         container dne-origin {
           presence "enable dne-origin";
           description "Optional origin filter of this networkd element";
           uses apply-advanced;
           leaf realm {
             description "Origin realm of this network element";
             type string {
               length "1 .. 255";
             }
             mandatory true;
           }
           leaf host {
             description "Optional origin host of this network element";
             type string {
               length "1 .. 255";
             }
           }
         }
         leaf-list function {
           ordered-by user;
           description "Diameter function associated with by this network element";
           type enumeration {
             enum "jsrc" {
               description "Function to use SRC application";
             }
             enum "gx-plus" {
               description "Function to use GX-PLUS application";
             }
             enum "sd-3gpp" {
               description "Function to use SD-3GPP application";
             }
             enum "nasreq" {
               description "Function to use NASREQ application";
             }
             enum "pcrf" {
               description "Function to use PCRF(GX) application";
             }
             enum "ocs" {
               description "Function to use OCS(GY) application";
             }
             enum "s6a" {
               description "Function to use S6A application";
             }
           }
           max-elements 8;
         }
         list peer {
           key name;
           ordered-by user;
           description "Peer associated with this network element";
           leaf name {
             description "Name of a peer associated with this network element";
             type string {
               length "1 .. 255";
             }
           }
           uses apply-advanced;
           leaf priority {
             description "Peer priority with this network element";
             type union {
               type string {
                 pattern "<.*>|$.*";
               }
               type uint32 {
                 range "1 .. 65535";
               }
             }
             mandatory true;
           }
         }
         container forwarding {
           description "Forwarding configuration for this network-element";
           uses apply-advanced;
           list route {
             key name;
             ordered-by user;
             description "Routes associated with this network-element";
             max-elements 256;
             leaf name {
               description "Name of a route associated with this network element";
               type string {
                 length "1 .. 255";
               }
             }
             uses apply-advanced;
             container function {
               description "Diameter function and partition associated with route";
               leaf function-name {
                 type enumeration {
                   enum "jsrc" {
                     description "Function to use SRC application";
                   }
                   enum "gx-plus" {
                     description "Function to use GX-PLUS application";
                   }
                   enum "sd-3gpp" {
                     description "Function to use SD-3GPP application";
                   }
                   enum "nasreq" {
                     description "Function to use NASREQ application";
                   }
                   enum "pcrf" {
                     description "Function to use PCRF(GX) application";
                   }
                   enum "ocs" {
                     description "Function to use OCS(GY) application";
                   }
                   enum "s6a" {
                     description "Function to use S6A application";
                   }
                 }
                 mandatory true;
               }
               leaf partition {
                 description "Diameter function partition name";
                 type string {
                   length "1 .. 255";
                 }
               }
             }
             container destination {
               description "Destination for this route";
               leaf realm {
                 description "Diameter destination realm";
                 type string {
                   length "1 .. 255";
                 }
                 mandatory true;
               }
               leaf host {
                 description "Diameter destination host";
                 type string {
                   length "1 .. 255";
                 }
               }
             }
             leaf metric {
               description "Metric for this route";
               type union {
                 type string {
                   pattern "<.*>|$.*";
                 }
                 type uint32 {
                   range "0 .. 255";
                 }
               }
               mandatory true;
             }
           }
         }
       }
       list transport {
         key name;
         ordered-by user;
         description "Diameter transport configuration";
         max-elements 31;
         leaf name {
           description "Name for this transport definition";
           type string {
             length "1 .. 255";
           }
         }
         uses apply-advanced;
         leaf address {
           description "Source IP address for a peer";
           type jt:ipaddr;
           mandatory true;
         }
         choice instance {
           case case_1 {
             container logical-system {
               description "Logical system to be used by transport";
               leaf logical-system-name {
                 description "Name of logical system";
                 type string {
                 }
                 mandatory true;
               }
               leaf routing-instance {
                 description "Routing instance to be used by transport";
                 type union {
                   type string {
                     pattern "default";
                   }
                   type string {
                   }
                 }
               }
             }
           }
           case case_2 {
             leaf routing-instance {
               description "Routing instance of server to which to forward";
               type union {
                 type string {
                   pattern "default";
                 }
                 type string {
                 }
               }
             }
           }
         }
       }
       list peer {
         key name;
         ordered-by user;
         description "Diameter peer configuration";
         max-elements 31;
         leaf name {
           description "Name for this Diameter peer";
           type string {
             length "1 .. 255";
           }
         }
         uses apply-advanced;
         leaf address {
           description "IP Address of Diameter peer";
           type jt:ipaddr;
           mandatory true;
         }
         leaf send-origin-state-id {
           description "Include origin-state-id in peer messages";
           type empty;
         }
         choice instance {
           case case_1 {
             container logical-system {
               description "Logical system to be used by transport";
               leaf logical-system-name {
                 description "Name of logical system";
                 type string {
                 }
                 mandatory true;
               }
               leaf routing-instance {
                 description "Routing instance to be used by transport";
                 type union {
                   type string {
                     pattern "default";
                   }
                   type string {
                   }
                 }
               }
             }
           }
           case case_2 {
             leaf routing-instance {
               description "Routing instance of server to which to forward";
               type union {
                 type string {
                   pattern "default";
                 }
                 type string {
                 }
               }
             }
           }
         }
         container connect-actively {
           presence "enable connect-actively";
           uses apply-advanced;
           leaf transport {
             description "Name of transport";
             type string {
               length "1 .. 255";
             }
           }
           leaf port {
             description "Peer port";
             default "3868";
             type union {
               type string {
                 pattern "<.*>|$.*";
               }
               type uint16 {
                 range "1 .. 65535";
               }
             }
           }
         }
         container peer-origin {
           presence "enable peer-origin";
           description "Optional origin attributes of this diameter peer";
           uses apply-advanced;
           leaf realm {
             description "Origin realm of this diameter peer";
             type string {
               length "1 .. 255";
             }
             mandatory true;
           }
           leaf host {
             description "Origin host of this diameter peer";
             type string {
               length "1 .. 255";
             }
             mandatory true;
           }
         }
       }
       leaf product-name {
         description "Product name to advertise in capability-exchange";
         type string {
           length "1 .. 255";
         }
       }
     }
     list dynamic-profiles {
       key name;
       ordered-by user;
       description "Dynamic profiles configuration";
       uses juniper-dynamic-profile-object;
     }
     container routing-options {
       description "Protocol-independent routing option configuration";
       uses juniper-routing-options;
     }
     container protocols {
       description "Routing protocol configuration";
       uses juniper-protocols;
     }
     container switch-options {
       description "Options for default routing-instance of type virtual-switch";
       uses juniper-def-rtb-switch-options;
     }
     container poe {
       description "Power over Ethernet options";
       uses apply-advanced;
       leaf management {
         description "Power management mode for Power over Ethernet";
         default "class";
         type enumeration {
           enum "static" {
             description "Static power allocation method";
           }
           enum "class" {
             description "Class based power allocation method";
           }
           enum "high-power" {
             description "High power allocation method";
           }
         }
       }
       leaf guard-band {
         description "Guard band for Power over Ethernet";
         default "0";
         units "watts";
         type union {
           type string {
             pattern "<.*>|$.*";
           }
           type uint32 {
             range "0 .. 19";
           }
         }
       }
       container notification-control {
         description "Notification control for Power over Ethernet traps";
         uses apply-advanced;
         list fpc {
           key name;
           ordered-by user;
           description "FPC slot number";
           leaf name {
             description "FPC slot number";
             type union {
               type string {
                 pattern "<.*>|$.*";
               }
               type uint32;
             }
           }
           uses apply-advanced;
           leaf disable {
             description "Disable Power over Ethernet notification";
             type empty;
           }
         }
       }
       leaf lldp-priority {
         description "PoE controller LLDP priority";
         type empty;
       }
       list interface {
         key name;
         ordered-by user;
         description "Interface configuration for Power over Ethernet";
         leaf name {
           description "Name of interface";
           type string;
         }
         uses apply-advanced;
         leaf disable {
           description "Disable interface";
           type empty;
         }
         leaf priority {
           description "Priority options";
           default "low";
           type enumeration {
             enum "low" {
               description "Low priority";
             }
             enum "high" {
               description "High priority";
             }
           }
         }
         leaf maximum-power {
           description "Maximum power";
           default "15.4";
           units "watts";
           type decimal64 {
             fraction-digits 9;
           }
         }
         container telemetries {
           presence "enable telemetries";
           description "Telemetries settings";
           uses apply-advanced;
           leaf disable {
             description "Disable telemetries";
             type empty;
           }
           leaf interval {
             description "Interval at which data should be recorded";
             default "5";
             units "minutes";
             type union {
               type string {
                 pattern "<.*>|$.*";
               }
               type uint32 {
                 range "1 .. 30";
               }
             }
           }
           leaf duration {
             description "Duration to continue recording of data";
             default "1";
             units "hours";
             type union {
               type string {
                 pattern "<.*>|$.*";
               }
               type uint32 {
                 range "1 .. 24";
               }
             }
           }
         }
         leaf af-mode {
           description "Enable 802.3af";
           type empty;
         }
         leaf high-power {
           description "Enable high power on interface ";
           type empty;
         }
         leaf ultrahigh-power {
           description "Enable ultra high power on interface";
           type empty;
         }
         leaf legacy-pd {
           description "Enable legacy pd support on interface";
           type empty;
         }
       }
       list fpc {
         key name;
         ordered-by user;
         description "FPC slot number";
         leaf name {
           description "FPC slot number";
           type string;
         }
         uses apply-advanced;
         leaf management {
           description "PoE management mode";
           default "class";
           type enumeration {
             enum "static" {
               description "Static power allocation method";
             }
             enum "class" {
               description "Power allocation class";
             }
           }
         }
         leaf guard-band {
           description "Guard band for PoE";
           default "0";
           units "watts";
           type union {
             type string {
               pattern "<.*>|$.*";
             }
             type uint32 {
               range "0 .. 15";
             }
           }
         }
         leaf maximum-power {
           description "Maximum FPC power limit";
           units "watts";
           type union {
             type uint32;
             type string {
               pattern "<.*>|$.*";
             }
           }
         }
         leaf lldp-priority {
           description "PoE controller LLDP priority";
           type empty;
         }
       }
     }
     container vlans {
       description "VLAN configuration";
       uses apply-advanced;
       list vlan {
         key name;
         description "Virtual LAN";
         uses vlan-types;
       }
       container vlan-groups {
         description "802.1x VLAN group configuration";
         uses apply-advanced;
         list vlan-group {
           key name;
           description "802.1x Vlan group";
           max-elements 4096;
           uses vlan-group-types;
         }
       }
     }
   }
   grouping aggregate-load-balance {
     description "Load balancing parameters";
     uses apply-advanced;
     choice adaptive_option {
       case case_1 {
       }
       case case_2 {
       }
       case case_3 {
       }
     }
   }
   grouping any_filter {
     leaf name {
       description "Filter name";
       type string {
       }
     }
     uses apply-advanced;
     leaf micro-segmentation {
       description "Indicates GBP tagging filter";
       type empty;
     }
     leaf no-longest-prefix-match {
       description "Disable longest prefix match for GBP filters";
       type empty;
     }
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object_oam;
         }
         list interface-set {
           key name;
           ordered-by user;
           description "Match interface in set";
           uses match_interface_set_object;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
           case case_3 {
           }
           case case_4 {
           }
         }
         choice loss-priority_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice learn-vlan-1p-priority_choice {
           case case_1 {
           }
           case case_2 {
           }
         }
         choice user-vlan-1p-priority_choice {
           case case_1 {
           }
           case case_2 {
           }
         }
         choice user-vlan-id_choice {
           case case_1 {
           }
           case case_2 {
           }
         }
         choice learn-vlan-id_choice {
           case case_1 {
           }
           case case_2 {
           }
         }
         choice ether-type_choice {
           case case_1 {
           }
           case case_2 {
           }
         }
         leaf mpls-bottom-of-stack {
           description "Match MPLS BottomOfStack bit";
           type empty;
         }
         choice slice_choice {
           case case_1 {
           }
           case case_2 {
           }
         }
         choice interface-group_choice {
           case case_1 {
           }
           case case_2 {
           }
         }
         list egress-interface {
           key name;
           ordered-by user;
           description "Match egress interface name";
           uses match_interface_object;
         }
         list mac-address {
           key name;
           ordered-by user;
           description "GBP MAC address";
           uses firewall_mac_addr_object;
         }
         choice vlan-id_choice {
           case case_1 {
             leaf-list vlan-id {
               ordered-by user;
               description "Vlan-id range (0..4095)";
               type string {
               }
             }
           }
           case case_2 {
             leaf-list vlan-id-except {
               ordered-by user;
               description "Vlan-id range (0..4095)";
               type string {
               }
             }
           }
         }
         choice gbp-src-tag_choice {
           case case_1 {
             leaf-list gbp-src-tag {
               ordered-by user;
               description "GBP Tag Range (0..65535)";
               type string {
               }
             }
           }
         }
         choice gbp-dst-tag_choice {
           case case_1 {
             leaf-list gbp-dst-tag {
               ordered-by user;
               description "GBP Tag Range (0..65535)";
               type string {
               }
             }
           }
         }
       }
       container then {
         description "Action to take if the 'from' condition is matched";
         uses apply-advanced;
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
           case case_5 {
           }
         }
         leaf gbp-tag {
           description "GBP tag to be assigned";
           type union {
             type string {
               pattern "<.*>|$.*";
             }
             type uint32 {
               range "1 .. 65535";
             }
           }
         }
         container next-ip {
           description "Packets are directed to the specified ipv4 address";
           leaf address {
             description "Address to route";
             type jt:ipv4prefix;
             mandatory true;
           }
           container routing-instance {
             description "Packets are directed to specified routing instance";
             leaf routing-instance-name {
               description "Name of routing instance";
               type string {
               }
               mandatory true;
             }
             leaf topology {
               description "Packets are directed to specified topology";
               type string {
               }
             }
           }
         }
         container next-ip6 {
           description "Packets are directed to the specified ipv6 address";
           leaf address {
             description "Address to route";
             type jt:ipv6prefix;
             mandatory true;
           }
           container routing-instance {
             description "Packets are directed to specified routing instance";
             leaf routing-instance-name {
               description "Name of routing instance";
               type string {
               }
               mandatory true;
             }
             leaf topology {
               description "Packets are directed to specified topology";
               type string {
               }
             }
           }
         }
       }
     }
   }
   grouping application_object {
     leaf name {
       description "Application name";
       type string {
         length "1 .. 63";
       }
     }
     uses apply-advanced;
     leaf application-protocol {
       description "Application protocol type";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
         enum "pop3" {
           description "Post Office Protocol 3 Protocol";
         }
         enum "smtps" {
           description "Simple Mail Transfer Protocol Over TLS";
         }
         enum "imaps" {
           description "Internet Mail Access Protocol Over TLS";
         }
         enum "pop3s" {
           description "Post Office Protocol 3 Protocol Over TLS";
         }
       }
     }
     leaf protocol {
       description "Match IP protocol type";
       type string;
     }
     leaf source-port {
       description "Match TCP/UDP source port";
       type string;
     }
     leaf destination-port {
       description "Match TCP/UDP destination port";
       type string;
     }
     leaf snmp-command {
       description "Match SNMP command";
       type enumeration {
         enum "get" {
           description "Get request";
         }
         enum "get-next" {
           description "Get-next request";
         }
         enum "get-response" {
           description "Get response";
         }
         enum "set" {
           description "Set request";
         }
         enum "trap" {
           description "Trap";
         }
       }
     }
     leaf icmp-type {
       description "Match ICMP message type";
       type string;
     }
     leaf icmp-code {
       description "Match ICMP message code";
       type string;
     }
     leaf ttl-threshold {
       description "Traceroute TTL threshold";
       type union {
         type uint8;
         type string {
           pattern "<.*>|$.*";
         }
       }
     }
     leaf rpc-program-number {
       description "Match range of RPC program numbers";
       type string {
       }
     }
     leaf uuid {
       description "Match universal unique identifier for DCE RPC objects";
       type string {
       }
     }
     leaf inactivity-timeout {
       description "Application-specific inactivity timeout";
       units "seconds";
       type string;
     }
     leaf gate-timeout {
       description "Application-specific gate timeout";
       units "seconds";
       type union {
         type string {
           pattern "<.*>|$.*";
         }
         type uint32 {
           range "5 .. 21600";
         }
       }
     }
     leaf child-inactivity-timeout {
       description "Application-specific child session inactivity timeout";
       units "seconds";
       type union {
         type string {
           pattern "<.*>|$.*";
         }
         type uint32 {
           range "4 .. 86400";
         }
       }
     }
     choice dns-choice {
       case case_1 {
         leaf do-not-translate-AAAA-query-to-A-query {
           description "Knob to control the translation of AAAA query to A query";
           type empty;
         }
       }
       case case_2 {
         leaf do-not-translate-A-query-to-AAAA-query {
           description "Knob to control the translation of A query to AAAA query";
           type empty;
         }
       }
     }
   }
   grouping application_set_object {
     leaf name {
       description "Application set name";
       type string {
         length "1 .. 63";
       }
     }
     uses apply-advanced;
     leaf description {
       description "Text description of application set";
       type string {
         length "1 .. 900";
       }
     }
     list application {
       key name;
       ordered-by user;
       description "Application to be included in the set";
       leaf name {
         description "Application name";
         type string {
           length "1 .. 63";
         }
       }
       uses apply-advanced;
     }
     list application-set {
       key name;
       ordered-by user;
       description "Define an application-set";
       leaf name {
         description "Define an application-set name";
         type string {
           length "1 .. 63";
         }
       }
       uses apply-advanced;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping aps_type {
     uses apply-advanced;
     choice aps_mode {
       case case_1 {
         leaf working-circuit {
           description "Working circuit group name";
           type string;
         }
       }
       case case_2 {
         leaf protect-circuit {
           description "Protect circuit group name";
           type string;
         }
       }
     }
     leaf annex-b {
       description "Annex-b mode";
       type empty;
     }
     leaf wait-to-restore-time {
       description "Circuit wait-to-restore time for annex-b";
       units "seconds";
       type union {
         type string {
           pattern "<.*>|$.*";
         }
         type uint32 {
           range "1 .. 4294967295";
         }
       }
     }
     leaf preserve-interface {
       description "Preserve interface state for fast failover";
       type empty;
     }
     leaf neighbor {
       description "Neighbor address";
       type jt:ipv4addr;
     }
     leaf paired-group {
       description "Name of paired APS group";
       type string;
     }
     container authentication-key {
       presence "enable authentication-key";
       description "Authentication parameters";
       leaf auth_key {
         description "Authentication key";
         type jt:unreadable;
         mandatory true;
       }
     }
     leaf switching-mode {
       description "APS switching mode";
       type enumeration {
         enum "bidirectional" {
           description "Bidirectional";
         }
         enum "unidirectional" {
           description "Unidirectional";
         }
       }
     }
     leaf advertise-interval {
       description "Advertise interval";
       units "milliseconds";
       type union {
         type string {
           pattern "<.*>|$.*";
         }
         type uint32 {
           range "1 .. 65534";
         }
       }
     }
     leaf hold-time {
       description "Hold time";
       units "milliseconds";
       type union {
         type string {
           pattern "<.*>|$.*";
         }
         type uint32 {
           range "1 .. 65534";
         }
       }
     }
     leaf revert-time {
       description "Circuit revert time";
       units "seconds";
       type union {
         type string {
           pattern "<.*>|$.*";
         }
         type uint32 {
           range "0 .. 65534";
         }
       }
     }
     choice break-before-make-choice {
       leaf break-before-make {
         description "Ensure only one interface is active at a time";
         type empty;
       }
       leaf no-break-before-make {
         description "Don't ensure only one interface is active at a time";
         type empty;
       }
     }
     choice manual_mode {
       case case_1 {
         leaf request {
           description "Request circuit state";
           type enumeration {
             enum "protect" {
               description "Request protect circuit";
             }
             enum "working" {
               description "Request working circuit";
             }
           }
         }
       }
       case case_2 {
         leaf force {
           description "Force circuit state";
           type enumeration {
             enum "protect" {
               description "Force protect circuit";
             }
             enum "working" {
               description "Force working circuit";
             }
           }
         }
       }
       case case_3 {
         leaf lockout {
           description "Lockout protection";
           type empty;
         }
       }
     }
     leaf fast-aps-switch {
       description "Fast aps switch";
       type empty;
     }
   }
   grouping ccc_filter {
     description "Define a CCC firewall filter";
     leaf name {
       description "Filter name";
       type string {
       }
     }
     uses apply-advanced;
     leaf-list accounting-profile {
       ordered-by user;
       description "Accounting profile name";
       type string;
     }
     leaf interface-specific {
       description "Any counters defined will be interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
           }
         }
         choice packet-length_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
           case case_3 {
           }
           case case_4 {
           }
         }
         choice loss-priority_choice {
           case case_1 {
           }
           case case_2 {
           }
         }
         choice learn-vlan-1p-priority_choice {
           case case_1 {
           }
           case case_2 {
           }
         }
         choice user-vlan-1p-priority_choice {
           case case_1 {
           }
           case case_2 {
           }
         }
         choice dscp_choice {
           case case_1 {
           }
           case case_2 {
           }
         }
         choice ip-precedence_choice {
           case case_1 {
           }
           case case_2 {
           }
         }
         choice ip-protocol_choice {
           case case_1 {
           }
           case case_2 {
           }
         }
         choice icmp-type_choice {
           case case_1 {
           }
           case case_2 {
           }
         }
         choice icmp-code_choice {
           case case_1 {
           }
           case case_2 {
           }
         }
         choice source-port_choice {
           case case_1 {
           }
           case case_2 {
           }
         }
         choice destination-port_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice user-vlan-id_choice {
           case case_1 {
           }
           case case_2 {
           }
         }
         choice ether-type_choice {
           case case_1 {
           }
           case case_2 {
           }
         }
         choice learn-vlan-id_choice {
           case case_1 {
           }
           case case_2 {
           }
         }
         leaf mpls-bottom-of-stack {
           description "Match MPLS BottomOfStack bit";
           type empty;
         }
       }
       container then {
         description "Action to take if the 'from' condition is matched";
         uses apply-advanced;
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to the specified instance";
           type string {
           }
         }
         leaf port-mirror {
           description "Port-mirror the packet";
           type empty;
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping certificate-object {
     leaf name {
       description "Simple name to identify this certificate";
       type string;
     }
     uses apply-advanced;
     leaf certificate {
       description "Certificate and private key string";
       type string;
     }
   }
   grouping chassis_type {
     uses apply-advanced;
     container nssu {
       presence "enable nssu";
       description "Nonstop Software Upgrade settings";
       uses apply-advanced;
       list upgrade-group {
         key name;
         ordered-by user;
         description "Nonstop Software Upgrade group";
         leaf name {
           type string {
             length "1 .. 254";
           }
         }
         uses apply-advanced;
         leaf-list fpcs {
           description "FPCs associated with update-group";
           type union {
             type string {
               pattern "<.*>|$.*";
             }
             type uint32;
           }
           max-elements 16;
         }
         list member {
           key name;
           description "Member of virtual chassis configuration";
           uses upgrade-group-fpcs;
         }
       }
       leaf rcp-count {
         description "Parallel rcp count";
         type union {
           type string {
             pattern "<.*>|$.*";
           }
           type int32 {
             range "1 .. 8";
           }
         }
       }
       leaf lc-reboot-delay {
         description "Delay between linecard reboot during NSSU";
         type union {
           type string {
             pattern "<.*>|$.*";
           }
           type int32 {
             range "0 .. 600";
           }
         }
       }
     }
     leaf no-psu-redundancy {
       description "Disable N+1 Redundancy for PSUs";
       type empty;
     }
     leaf no-power-budget {
       description "Disable Chassis Power Budget";
       type empty;
     }
     container psu {
       description "Power Supply Unit redundancy configuration";
       uses apply-advanced;
       container redundancy {
         description "PSU Redundancy settings";
         uses apply-advanced;
         leaf n-plus-n {
           description "PSU redundancy: N+N configuration";
           type empty;
         }
       }
     }
     container optics {
       presence "enable optics";
       description "Optics specific config";
       uses apply-advanced;
       leaf display-3po-pn {
         description "To display third party optics part number";
         type empty;
       }
       container pm {
         presence "enable pm";
         description "Optics Performance Monitoring";
         uses apply-advanced;
         leaf interval-length {
           description "Interval bin length";
           type enumeration {
             enum "10s" {
               description "10 seconds";
             }
             enum "30s" {
               description "30 seconds";
             }
             enum "1min" {
               description "1 minute";
             }
             enum "5min" {
               description "5 minutes";
             }
             enum "15min" {
               description "15 minutes";
             }
           }
         }
       }
     }
     choice source-route-choice {
       leaf source-route {
         description "Enable IP source-route processing";
         status deprecated;
         type empty;
       }
       leaf no-source-route {
         description "Don't enable IP source-route processing";
         status deprecated;
         type empty;
       }
     }
     leaf vrf-mtu-check {
       description "Enable Internet Processor II-based MTU check";
       type empty;
     }
     container icmp {
       description "ICMP protocol";
       uses apply-advanced;
     }
     container icmp6 {
       description "ICMP version 6 protocol";
       uses apply-advanced;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container redundancy {
       description "Redundancy settings";
       uses chassis_redundancy_type;
     }
     container routing-engine {
       description "Routing Engine settings";
       uses chassis_routing_engine_type;
     }
     container port-extender {
       presence "enable port-extender";
       description "Port extender settings";
       uses apply-advanced;
       list fpc-slot {
         key name;
         ordered-by user;
         description "Virtual FPC settings";
         leaf name {
           description "Virtual slot of the satellite device";
           type union {
             type string {
               pattern "<.*>|$.*";
             }
             type uint8 {
               range "65 .. 254";
             }
           }
           mandatory true;
         }
         uses apply-advanced;
         leaf desc {
           description "Description of the satellite device";
           type string;
           mandatory true;
         }
         leaf device {
           description "Model of the satellite device";
           type enumeration {
             enum "ex4400-48p" {
               description "Select EX4400-48P as the satellite";
             }
             enum "ex4400-48t" {
               description "Select EX4400-48T as the satellite";
             }
             enum "qfx5120-48t-6c" {
               description "Select QFX5120-48T-CHAS as the satellite";
             }
             enum "qfx5120-48y-8c" {
               description "Select JNP48Y8C-CHAS as the satellite";
             }
           }
           mandatory true;
         }
         leaf satellite-mgmt-ip {
           description "Management IP of the satellite device";
           type jt:ipv4addr;
         }
         list cascade-port {
           key name;
           ordered-by user;
           description "List of cascade ports";
           leaf name {
             description "AE interface name";
             type string {
             }
             mandatory true;
           }
           uses apply-advanced;
         }
         leaf target-mode {
           description "Enable EP targeting";
           type empty;
         }
         list pic-slot {
           key name;
           ordered-by user;
           description "PIC slot";
           leaf name {
             description "PIC slot number";
             type union {
               type string {
                 pattern "<.*>|$.*";
               }
               type uint8 {
                 range 0;
               }
             }
           }
           uses apply-advanced;
           list port {
             key name;
             ordered-by user;
             description "Port settings";
             leaf name {
               description "Port number";
               type union {
                 type string {
                   pattern "<.*>|$.*";
                 }
                 type uint16 {
                   range "0 .. 47";
                 }
               }
             }
             uses apply-advanced;
             leaf speed {
               description "Port speed";
               type enumeration {
                 enum "speed-100mbps" {
                   description "Sets the interface speed to 100Mbps";
                 }
                 enum "speed-1gbps" {
                   description "Sets the interface speed to 1Gbps";
                 }
                 enum "speed-10gbps" {
                   description "Sets the interface speed to 10Gbps";
                 }
                 enum "speed-25gbps" {
                   description "Sets the interface speed to 25Gbps";
                 }
               }
             }
           }
         }
       }
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
             mandatory true;
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container provider-instance-devices {
       description "Provider instance devices configuration";
       uses chassisd_provider_instance_type;
     }
     container fabric {
       description "Switch fabric settings";
       uses chassis_fabric_type;
     }
     list fpc {
       key name;
       description "Flexible PIC Concentrator parameters";
       uses chassis_fpc_type;
     }
     leaf node-id {
       description "Chassis identifier";
       status deprecated;
       type union {
         type string {
           pattern "<.*>|$.*";
         }
         type uint64 {
           range "1 .. 18446744073709551615";
         }
       }
     }
     container p4rt {
       presence "enable p4rt";
       description "Chassis p4rt";
       uses apply-advanced;
       leaf node-id {
         description "Chassis identifier";
         type union {
           type string {
             pattern "<.*>|$.*";
           }
           type uint64 {
             range "1 .. 18446744073709551615";
           }
         }
       }
     }
     list cb {
       key name;
       description "Control Board parameters";
       uses chassis_cb_type;
     }
     container sib {
       description "Switch Interface Board parameters";
       uses chassis_sib_type;
     }
     container fabric-card {
       description "Fabric card parameters";
       presence "enable fabric-card";
       uses chassis_fabric_cards_type;
     }
     container alarm {
       description "Global alarm settings";
       uses chassis_alarm_type;
     }
     leaf slow-pfe-alarm {
       description "Enable slow (potential) PFE alarm";
       type empty;
     }
     container usb {
       description "USB control flags";
       uses apply-advanced;
       container storage {
         description "USB storage flags";
         uses apply-advanced;
         leaf disable {
           description "Disable USB storage";
           type empty;
         }
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         uses chassis_fpc_type;
       }
       choice state {
         case case_1 {
           leaf online-expected {
             description "LCC is expected to be online";
             type empty;
           }
         }
         case case_2 {
           leaf offline {
             description "LCC is expected to be offline";
             type empty;
           }
         }
       }
     }
     container lcd {
       description "Chassis LCD";
       status deprecated;
       uses apply-advanced;
       list fpc {
         key name;
         ordered-by user;
         leaf name {
           description "FPC slot number";
           type union {
             type string {
               pattern "<.*>|$.*";
             }
             type uint32;
           }
         }
         choice menu-item {
           case case_1 {
             leaf maintenance-menu {
               description "LCD maintenance menu";
               type empty;
             }
           }
         }
         choice enable-disable {
           case case_1 {
             leaf disable {
               description "Disable maintenance-menu";
               type empty;
             }
           }
         }
       }
       choice menu-item {
         case case_1 {
           leaf maintenance-menu {
             description "LCD maintenance menu";
             type empty;
           }
         }
       }
       choice enable-disable {
         case case_1 {
           leaf disable {
             description "Disable maintenance-menu";
             type empty;
           }
         }
       }
     }
     leaf loopback-firewallv6-optimization {
       description "Increase ACL scale for loopback IPv6 filters; restarts PFE";
       type empty;
     }
     leaf ipv6linklocal-sourcechecking {
       description "Enable ipv6 linklocal source checking. This will restart PFE";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       type empty;
     }
     leaf loopback-firewall-optimization {
       description "Optimal TCAM use,reboot(VC);restarts PFE(IP rsrved mcast dest&ttl=0/1,config explicitly)";
       type empty;
     }
     leaf loopback-firewall-per-vrf {
       description "Enable per vrf control, needs reboot for VC; restarts PFE if standalone";
       type empty;
     }
     leaf epacl-firewall-optimization {
       description "Maximizes Egress Port ACLs TCAM use and restarts PFE";
       type empty;
     }
     leaf per-logical-interface-firewall {
       description "Ingress port firewall can be supported per logical interface, restarts PFE";
       type empty;
     }
     container lcd-menu {
       description "Chassis LCD menu";
       uses apply-advanced;
       list fpc {
         key name;
         ordered-by user;
         leaf name {
           description "FPC slot number";
           type union {
             type string {
               pattern "<.*>|$.*";
             }
             type uint32;
           }
         }
         uses apply-advanced;
         list menu-item {
           key name;
           ordered-by user;
           description "LCD menu item";
           leaf name {
             description "LCD menu name";
             type string;
           }
           leaf disable {
             description "Disable LCD menu";
             type empty;
           }
         }
       }
       list menu-item {
         key name;
         ordered-by user;
         description "LCD menu item";
         leaf name {
           description "LCD menu name";
           type string;
         }
         leaf disable {
           description "Disable LCD menu";
           type empty;
         }
       }
     }
     leaf fpc-empolicy-profile {
       description "FPC EM Policy Profile";
       type enumeration {
         enum "low-power-mode" {
           description "Set low power mode";
         }
       }
     }
     leaf auto-image-upgrade {
       description "Auto image upgrade using DHCP";
       type empty;
     }
     container multicast-loadbalance {
       description "Multicast load balancing settings";
       presence "enable multicast-loadbalance";
       uses chassis_ae_lb_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
         mandatory true;
       }
       leaf satellite-name {
         description "Satellite name";
         type string;
       }
       leaf device-group {
         description "Satellite device group";
         type string;
       }
       list device-group-map {
         key name;
         ordered-by user;
         description "Common groups mapping to device groups";
         leaf name {
           description "Satellite Device Group";
           type string;
         }
         uses apply-advanced;
         leaf-list include-groups {
           ordered-by user;
           description "Common groups list";
           type string;
         }
       }
       list satellite {
         key name;
         ordered-by user;
         description "List of satellites";
         leaf name {
           description "Satellite name";
           type string;
         }
         uses apply-advanced;
         leaf device-group {
           description "Satellite Device Group";
           type string;
         }
         leaf model {
           description "Satellite model";
           type string;
           mandatory true;
         }
         leaf version {
           description "Satellite version";
           type string {
           }
           mandatory true;
         }
       }
       leaf user {
         description "Satellite User Name";
         type string;
       }
       leaf-list controller {
         ordered-by user;
         description "Controller Name";
         type string;
       }
       leaf other-controller {
         description "Dual controller Name";
         type string;
       }
       leaf authentication {
         description "Authentication string";
         type jt:unreadable;
       }
     }
     list satellite {
       key name;
       ordered-by user;
       description "List of available satellite configurations";
       leaf name {
         description "Satellite name";
         type string;
       }
       uses apply-advanced;
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_ae_lb_type {
     uses apply-advanced;
     leaf disable {
       description "Disable Multicast load balancing";
       type empty;
     }
     leaf hash-mode {
       description "PFE hash mode";
       type enumeration {
         enum "crc-sgip" {
           description "CRC of Source IP and Group IP";
         }
         enum "crc-gip" {
           description "CRC of Group IP only";
         }
         enum "crc-sip" {
           description "CRC of Source IP only";
         }
         enum "simple-sgip" {
           description "Simple hash of Source IP and Group IP";
         }
         enum "simple-gip" {
           description "Simple hash of Group IP";
         }
         enum "simple-sip" {
           description "Simple hash of Source IP";
         }
         enum "balanced" {
           description "Round-Robin balancing";
         }
       }
     }
   }
   grouping chassis_agg_dev_type {
     uses apply-advanced;
     container ethernet {
       description "Aggregated device options for Ethernet";
       uses chassisd_agg_enet_type;
     }
     container sonet {
       description "Aggregated device options for SONET";
       uses chassisd_agg_pos_type;
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
     leaf ignore-fan-speed-check {
       description "Ignore the Fan speed check alarms";
       type empty;
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       type union {
         type string {
           pattern "<.*>|$.*";
         }
         type uint32;
       }
     }
     uses apply-advanced;
     container temperature-threshold {
       description "CB temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_cards_type {
     uses apply-advanced;
     leaf reset-count {
       description "Number of times sib can be reset by cmerror";
       type union {
         type string {
           pattern "<.*>|$.*";
         }
         type uint32 {
           range "1 .. 10";
         }
       }
     }
   }
   grouping chassis_fabric_type {
     uses apply-advanced;
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
             }
           }
         }
         container actions {
           description "Reachability fault actions";
           uses apply-advanced;
           container recovery-failure {
             description "Recovery failure action to be taken for FHP";
             uses apply-advanced;
           }
         }
       }
     }
     container oam {
       description "Fabric OAM configuration";
       uses apply-advanced;
     }
   }
   grouping chassis_fpc_type {
     leaf name {
       description "FPC slot number";
       type union {
         type string {
           pattern "<.*>|$.*";
         }
         type uint32;
       }
     }
     uses apply-advanced;
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
       leaf software-based {
         description "Override linkscan mode to software based";
         type empty;
       }
     }
     list pic {
       key name;
       description "Physical Interface Card number";
       uses chassis_pic_type;
     }
     list mic {
       key name;
       description "Modular Interface Card number";
       uses chassis_mic_type;
     }
     leaf power {
       description "Power FPCs on or off";
       type enumeration {
         enum "off" {
           description "Do not provide power to FPCs";
         }
         enum "on" {
           description "Provide power to FPCs";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf cfp-to-et {
       description "Enable ET interface and remove CFP client";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     list port-mirror-instance {
       key name;
       ordered-by user;
       max-elements 2;
       leaf name {
         description "Associate a port mirroring instance with the FPC";
         type string {
           length "1 .. 64";
         }
       }
       uses apply-advanced;
     }
     list sampling-instance {
       key name;
       ordered-by user;
       max-elements 1;
       leaf name {
         description "Associate a sampling instance with the FPC";
         type string {
           length "1 .. 64";
         }
       }
       uses apply-advanced;
     }
     list pfe {
       key name;
       description "Packet forwarding engine parameters";
       uses chassis_pfe_type;
     }
   }
   grouping chassis_fpc_type_slot {
     leaf name {
       description "FPC slot number";
       type string;
     }
     uses apply-advanced;
     list pem {
       key name;
       ordered-by user;
       description "Power Supply Module slot";
       uses chassis_pem_type_slot;
     }
   }
   grouping chassis_mic_type {
     leaf name {
       description "MIC slot number";
       type union {
         type string {
           pattern "<.*>|$.*";
         }
         type uint32;
       }
     }
     uses apply-advanced;
     leaf power {
       description "Power off MIC";
       type enumeration {
         enum "off" {
           description "Do not provide power to MIC";
         }
       }
     }
   }
   grouping chassis_pem_type_slot {
     leaf name {
       description "PEM slot number";
       type string;
     }
     uses apply-advanced;
   }
   grouping chassis_pfe_type {
     description "PFE(Packet forwarding engine)";
     leaf name {
       description "PFE(Packet forwarding engine) identifier";
       type union {
         type string {
           pattern "<.*>|$.*";
         }
         type uint32;
       }
     }
     uses apply-advanced;
     leaf node {
       description "PFE(Packet forwarding engine) global identifier";
       type union {
         type string {
           pattern "<.*>|$.*";
         }
         type uint64 {
           range "1 .. 18446744073709551615";
         }
       }
     }
     leaf tunnel-services {
       description "Tunnel services configuration";
       type empty;
     }
   }
   grouping chassis_pic_type {
     leaf name {
       description "PIC slot number";
       type union {
         type string {
           pattern "<.*>|$.*";
         }
         type uint32;
       }
     }
     uses apply-advanced;
     list tunnel-port {
       key name;
       description "Tunnel port number";
       uses chassis_port_type;
     }
     container tunnel-services {
       presence "enable tunnel-services";
       description "Tunnel services configuration";
       uses apply-advanced;
       leaf bandwidth {
         description "Amount of bandwidth reserved for tunnel service";
         type string;
       }
       leaf tunnel-only {
         description "Support only tunnel traffic";
         type empty;
       }
       list tunnel-port {
         key name;
         ordered-by user;
         description "Tunnel port number";
         leaf name {
           description "Port number";
           type union {
             type string {
               pattern "<.*>|$.*";
             }
             type uint32;
           }
         }
         uses apply-advanced;
         leaf bandwidth {
           description "Amount of bandwidth reserved for tunnel service";
           type string;
           mandatory true;
         }
       }
     }
     choice adaptive-or-monitoring {
       case case_1 {
       }
       case case_2 {
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf aggregate-ports {
       description "Aggregate multiple ports on a PIC as a single port";
       type empty;
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     list port-mirror-instance {
       key name;
       ordered-by user;
       max-elements 2;
       leaf name {
         description "Associate a port mirroring instance with the PIC";
         type string {
           length "1 .. 64";
         }
       }
       uses apply-advanced;
     }
     list port {
       key name;
       description "Port number";
       uses chassis_pic_port_framing;
     }
     list qsfp-port {
       key name;
       description "Qsfp port to configure";
       leaf name {
         description "Port-group 0:'0-3' 1:'4-7'";
         type union {
           type string {
             pattern "<.*>|$.*";
           }
           type uint32 {
             range "0 .. 1";
           }
         }
       }
       uses apply-advanced;
       leaf port-mode {
         description "Select mode for port-group";
         type enumeration {
           enum "40g" {
             description "40G mode";
           }
           enum "10g" {
             description "10G mode";
           }
         }
       }
     }
     container sfpplus {
       description "Sfpplus configuration option";
       uses apply-advanced;
       leaf pic-mode {
         description "PIC mode";
         type enumeration {
           enum "1g" {
             description "1G SFP mode";
           }
           enum "10g" {
             description "10G SFP+ mode";
           }
         }
       }
     }
     list port-group {
       key name;
       description "Port group number";
       leaf name {
         description "Port group number";
         type union {
           type string {
             pattern "<.*>|$.*";
           }
           type uint32 {
             range "0 .. 3";
           }
         }
       }
       uses apply-advanced;
       leaf speed-group {
         description "Specify speed group";
         type enumeration {
           enum "high" {
             description "High speed group";
           }
           enum "low" {
             description "Low speed group";
           }
           enum "10g" {
             description "Supporting 10G/40G/4x10G with common speeds";
           }
         }
       }
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_pic_port_framing {
     leaf name {
       description "Port number";
       type union {
         type string {
           pattern "<.*>|$.*";
         }
         type uint32;
       }
     }
     uses apply-advanced;
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf speed {
       description "Port speed";
       type enumeration {
         enum "oc3-stm1" {
           description "OC3 or STM1";
         }
         enum "oc12-stm4" {
           description "OC12 or STM4";
         }
         enum "oc48-stm16" {
           description "OC48 or STM16";
         }
         enum "1g" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
   }
   grouping chassis_port_type {
     leaf name {
       description "Port number for tunnel services";
       type union {
         type string {
           pattern "<.*>|$.*";
         }
         type uint32 {
           range "0 .. 47";
         }
       }
     }
     uses apply-advanced;
     leaf tunnel-services {
       description "Tunnel services configuration";
       type empty;
     }
   }
   grouping chassis_redundancy_type {
     uses apply-advanced;
     list routing-engine {
       key name;
       description "Redundancy options for Routing Engines";
       uses chassis_rdd_re_type;
     }
     container failover {
       description "Failover to other Routing Engine";
       presence "enable failover";
       uses chassis_rdd_failover_type;
     }
     leaf keepalive-time {
       description "Time before Routing Engine failover";
       units "seconds";
       type union {
         type string {
           pattern "<.*>|$.*";
         }
         type uint32 {
           range "2 .. 10000";
         }
       }
     }
     container graceful-switchover {
       description "Enable graceful switchover on supported hardware";
       presence "enable graceful-switchover";
       uses chassis_non_stop_forwarding_type;
     }
   }
   grouping chassis_non_stop_forwarding_type {
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_failover_type {
     uses apply-advanced;
     container category {
       description "Failover category";
       presence "enable category";
       uses chassis_rdd_fail_cat_type;
     }
     leaf on-loss-of-keepalives {
       description "Failover on loss of keepalives";
       type empty;
     }
     leaf on-disk-failure {
       description "Failover on disk failure";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-mcontrol-slip {
       description "Failover on mastership control thread slip";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       uses chassis_re_on_disk_failure;
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           type string {
             length "1 .. 40";
           }
         }
         uses apply-advanced;
         list id {
           key name;
           ordered-by user;
           description "Attribute ids to monitor of this series type";
           max-elements 30;
           leaf name {
             description "SSD smart attribute id";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
             mandatory true;
           }
           leaf id-value {
             description "SSD attribute value";
             type enumeration {
               enum "raw" {
                 description "Raw value to be used for this smart id";
               }
               enum "norm" {
                 description "Normalised value to be used for this smart id";
               }
             }
             mandatory true;
           }
           leaf id-flag {
             description "SSD attribute flag";
             type enumeration {
               enum "low" {
                 description "Check if value is less than smart threshold";
               }
               enum "high" {
                 description "Check if value is greater than smart threshold";
               }
             }
             mandatory true;
           }
         }
       }
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
   }
   grouping chassis_sib_type {
     uses apply-advanced;
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping chassisd_provider_instance_type {
     uses apply-advanced;
     leaf device-count {
       description "Number of provider instance port devices";
       type union {
         type string {
           pattern "<.*>|$.*";
         }
         type uint32 {
           range "1 .. 16";
         }
       }
     }
   }
   grouping client-address-object {
     description "Client address";
     leaf name {
       description "Address or prefix";
       type jt:ipprefix;
     }
     uses apply-advanced;
     leaf restrict {
       description "Deny access";
       type empty;
     }
   }
   grouping comm-object {
     description "Specify snmp-community name";
     uses apply-advanced;
     leaf snmp-community {
       description "Specify community name";
       type string {
         length "1 .. 32";
       }
       mandatory true;
     }
     leaf no-default-comm-to-v3-config {
       description "No default snmp-community and v3 configuration";
       type empty;
     }
   }
   grouping cos_policer {
     description "Define a CoS based policer";
     leaf name {
       description "Policer name";
       type string {
       }
     }
     uses apply-advanced;
     container premium {
       description "Policer to apply to premium traffic";
       presence "enable premium";
       uses ethernet_policer;
     }
     container aggregate {
       description "Policer to apply to aggregate traffic";
       presence "enable aggregate";
       uses ethernet_policer;
     }
   }
   grouping cos_policer_input_priority_map {
     description "Input policer priority map";
     uses apply-advanced;
     container ieee-802.1p {
       description "Use IEEE 802.1p to determine policer priority map";
       uses apply-advanced;
       leaf-list premium {
         ordered-by user;
         description "Input traffic's IEEE 802.1p value to which premium policer is applied";
         type union {
           type string {
             pattern "<.*>|$.*";
           }
           type uint32 {
             range "0 .. 7";
           }
         }
       }
     }
   }
   grouping cos_policer_output_priority_map {
     description "Output policer priority map";
     uses apply-advanced;
     container classifier {
       description "Use classifier as policer priority map";
       uses apply-advanced;
       container premium {
         description "Output traffic classifier to which premium policer is applied";
         uses apply-advanced;
         list forwarding-class {
           key name;
           ordered-by user;
           description "Select a classification for this priority map";
           leaf name {
             description "Forwarding class name";
             type string {
             }
           }
           uses apply-advanced;
           list loss-priority {
             key name;
             ordered-by user;
             description "Select a loss priority";
             leaf name {
               type enumeration {
                 enum "low" {
                   description "Select low loss priority as premium policer";
                 }
                 enum "high" {
                   description "Select high loss priority as premium policer";
                 }
               }
             }
           }
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping dcd_rx_bucket_config {
     uses apply-advanced;
     leaf overflow {
       description "Overflow behavior";
       type enumeration {
         enum "tag" {
           description "Tag and count overflow packets";
         }
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dcd_shaping_config {
     description "Traffic-shaping profile";
     uses apply-advanced;
     choice useless_shaping_choice {
       case case_1 {
         container cbr {
           presence "enable cbr";
           description "Constant bandwidth utilization";
           leaf cbr-value {
             description "Constant bandwidth utilization";
             type string;
             mandatory true;
           }
         }
       }
       case case_2 {
         container vbr {
           description "Variable bandwidth utilization";
           leaf peak {
             description "Peak rate";
             type string;
             mandatory true;
           }
           leaf sustained {
             description "Sustained rate";
             type string;
             mandatory true;
           }
           leaf burst {
             description "Burst size";
             type string;
             mandatory true;
           }
         }
       }
       case case_3 {
         container rtvbr {
           description "ATM2 real-time variable bandwidth utilization";
           leaf peak {
             description "Peak rate";
             type string;
             mandatory true;
           }
           leaf sustained {
             description "Sustained rate";
             type string;
             mandatory true;
           }
           leaf burst {
             description "Burst size";
             type string;
             mandatory true;
           }
         }
       }
     }
     leaf queue-length {
       description "Queue length";
       type union {
         type string {
           pattern "<.*>|$.*";
         }
         type uint32 {
           range "1 .. 16383";
         }
       }
     }
   }
   grouping dcd_tx_bucket_config {
     uses apply-advanced;
     leaf overflow {
       description "Overflow behavior";
       type enumeration {
         enum "discard" {
           description "Discard overflow packets";
         }
       }
     }
     leaf rate {
       description "Bucket rate";
       type union {
         type string {
           pattern "<.*>|$.*";
         }
         type uint32 {
           range "0 .. 100";
         }
       }
     }
     leaf threshold {
       description "Bucket threshold";
       type union {
         type string {
           pattern "<.*>|$.*";
         }
         type uint32 {
           range "0 .. 65535";
         }
       }
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
             }
           }
         }
       }
       container user-id {
         description "Add user id to client-id option ";
         choice user-id-choice {
           case case_1 {
             leaf ascii {
               description "Client identifier as an ASCII string";
               type string;
             }
           }
           case case_2 {
             leaf hexadecimal {
               description "Client identifier as a hexadecimal string";
               type string {
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
       leaf hardware-type {
         description "Hardware type";
         default "0";
         type union {
           type string {
             pattern "<.*>|$.*";
           }
           type uint8 {
             range "0 .. 255";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 50000";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     leaf request-unicast-replies {
       description "Set broadcast bit to 0 in the DHCP discover and request packets";
       type empty;
     }
     container options {
       description "DHCP options";
       uses apply-advanced;
       list number {
         key name;
         description "DHCP option code";
         leaf name {
           description "DHCP option identifier code";
           type union {
             type string {
               pattern "<.*>|$.*";
             }
             type uint32 {
               range "1 .. 254";
             }
           }
         }
         choice option-type-choice {
           case case_1 {
             leaf hex-string {
               description "Hexadecimal string";
               type string {
                 length "1 .. 510";
               }
             }
           }
         }
       }
       leaf no-hostname {
         description "Do not carry hostname (RFC option code is 12) in packet";
         type empty;
       }
     }
     list requested-options {
       key name;
       description "DHCP options";
       leaf name {
         description "DHCP option identifier code";
         type union {
           type string {
             pattern "<.*>|$.*";
           }
           type uint32 {
             range "1 .. 254";
           }
         }
       }
     }
   }
   grouping dnsf-multitenant-hash-object {
     uses apply-advanced;
     container file-hash-key {
       description "Define web-filter global file key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
       mandatory true;
     }
   }
   grouping dynamic_ipv4_type {
     description "Packet triggered subscribers";
     uses apply-advanced;
     container address-ranges {
       description "Packet triggered subscribers configuration";
       uses apply-advanced;
       list dynamic-profile {
         key name;
         ordered-by user;
         description "Attach dynamic-profile to packet triggered subscriber ranges";
         max-elements 16;
         leaf name {
           description "Profile name";
           type string;
         }
         uses apply-advanced;
         list network {
           key name;
           ordered-by user;
           description "IPv4 Network address";
           max-elements 16;
           leaf name {
             description "Specify the network address";
             type jt:ipv4prefix;
           }
           uses apply-advanced;
           list range {
             key name;
             ordered-by user;
             description "Configure demux interface based on source IP address range";
             max-elements 16;
             leaf name {
               description "Name of range";
               type string;
             }
             uses apply-advanced;
             leaf low {
               description "Lower limit of address range";
               type jt:ipv4prefix;
               mandatory true;
             }
             leaf high {
               description "Upper limit of address range";
               type jt:ipv4prefix;
               mandatory true;
             }
           }
         }
       }
       container authentication {
         description "Auto-configure packet triggered subscriber authentication";
         uses dynamic_ip_authentication_type;
       }
       leaf session-timeout {
         description "Self destruct or auto clear timeout in seconds";
         type union {
           type string {
             pattern "<.*>|$.*";
           }
           type uint32 {
             range "600 .. 6000";
           }
         }
       }
     }
   }
   grouping dynamic_ip_authentication_type {
     description "Autoconf packet trigger subscriber authentication";
     uses apply-advanced;
     leaf password {
       description "Username password";
       type string {
         length "1 .. 64";
       }
     }
     container username-include {
       description "Username options";
       uses apply-advanced;
       leaf delimiter {
         description "Delimiter/separator character";
         type string {
           length 1;
         }
       }
       leaf domain-name {
         description "Domain name";
         type string {
           length "1 .. 64";
         }
       }
       leaf user-prefix {
         description "User defined prefix";
         type string {
           length "1 .. 64";
         }
       }
       leaf auth-server-realm {
         description "Authentication server realm name";
         type string {
           length "1 .. 64";
         }
       }
       leaf interface-name {
         description "Interface name";
         type empty;
       }
       leaf source-address {
         description "Source address";
         type empty;
       }
     }
   }
   grouping epd_threshold_config {
     uses apply-advanced;
     leaf epd-threshold-plp0 {
       description "Early packet discard threshold value";
       units "cells";
       type string;
       mandatory true;
     }
     leaf plp1 {
       description "Early packet drop threshold value for PLP 1";
       units "cells";
       type string;
     }
   }
   grouping es_filter {
     leaf name {
       description "Filter name";
       type string {
       }
     }
     uses apply-advanced;
     leaf interface-specific {
       description "Defined counters are interface specific";
       type empty;
     }
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object;
         }
         list source-mac-address {
           key name;
           ordered-by user;
           description "Match MAC source address";
           uses firewall_mac_addr_object;
         }
         list destination-mac-address {
           key name;
           ordered-by user;
           description "Match MAC destination address";
           uses firewall_mac_addr_object;
         }
         choice ether-type_choice {
           case case_1 {
             leaf-list ether-type {
               ordered-by user;
               type string;
             }
           }
           case case_2 {
             leaf-list ether-type-except {
               ordered-by user;
               type string;
             }
           }
         }
         choice l2-encap-type_choice {
           case case_1 {
             leaf-list l2-encap-type {
               ordered-by user;
               type string;
             }
           }
           case case_2 {
           }
         }
         choice vlan_choice {
           case case_1 {
             leaf-list vlan {
               ordered-by user;
               description "VLAN name or ID";
               type string;
             }
           }
           case case_2 {
             leaf-list vlan-except {
               ordered-by user;
               description "VLAN name or ID";
               type string;
             }
           }
         }
         choice dot1q-tag_choice {
           case case_1 {
             leaf-list dot1q-tag {
               ordered-by user;
               description "Range of values";
               type string {
               }
             }
           }
           case case_2 {
             leaf-list dot1q-tag-except {
               ordered-by user;
               description "Range of values";
               type string {
               }
             }
           }
         }
         choice dot1q-user-priority_choice {
           case case_1 {
             leaf-list dot1q-user-priority {
               ordered-by user;
               type string;
             }
           }
           case case_2 {
             leaf-list dot1q-user-priority-except {
               ordered-by user;
               type string;
             }
           }
         }
         list source-address {
           key name;
           ordered-by user;
           description "Match IP source address";
           uses firewall_addr_object;
         }
         list destination-address {
           key name;
           ordered-by user;
           description "Match IP destination address";
           uses firewall_addr_object;
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
             leaf-list precedence-except {
               ordered-by user;
               type string;
             }
           }
         }
         choice ip-options_choice {
           case case_1 {
           }
           case case_2 {
           }
         }
         leaf fragment-flags {
           description "Match fragment flags (in symbolic or hex formats) - (Ingress only)";
           type string {
           }
         }
         leaf is-fragment {
           description "Match if packet is a fragment";
           type empty;
         }
         choice protocol_choice {
           case case_1 {
             leaf-list protocol {
               ordered-by user;
               type string;
             }
           }
           case case_2 {
             leaf-list protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags (in symbolic or hex formats)";
           type string;
         }
         leaf tcp-initial {
           description "Match initial packet of a TCP connection";
           type empty;
         }
         leaf tcp-established {
           description "Match packet of an established TCP connection";
           type empty;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice interface-group_choice {
           case case_1 {
             leaf-list interface-group {
               ordered-by user;
               description "Range of values";
               type string;
             }
           }
           case case_2 {
             leaf-list interface-group-except {
               ordered-by user;
               description "Range of values";
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
           }
           case case_2 {
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-address {
           key name;
           ordered-by user;
           description "Match IP source or destination address";
           uses firewall_addr_object;
         }
         list interface-set {
           key name;
           ordered-by user;
           description "Match interface in set";
           uses match_interface_set_object;
         }
         list prefix-list {
           key name;
           ordered-by user;
           description "Match IP source or destination prefixes in named list";
           uses firewall_prefix_list;
         }
         choice isid_choice {
           case case_1 {
             leaf-list isid {
               ordered-by user;
               description "Range of values";
               type string;
             }
           }
           case case_2 {
             leaf-list isid-except {
               ordered-by user;
               description "Range of values";
               type string;
             }
           }
         }
         choice isid-priority-code-point_choice {
           case case_1 {
             leaf-list isid-priority-code-point {
               ordered-by user;
               description "802.1p priority value 0-7";
               type union {
                 type string {
                   pattern "<.*>|$.*";
                 }
                 type uint32 {
                   range "0 .. 7";
                 }
               }
             }
           }
           case case_2 {
             leaf-list isid-priority-code-point-except {
               ordered-by user;
               description "802.1p priority value 0-7";
               type union {
                 type string {
                   pattern "<.*>|$.*";
                 }
                 type uint32 {
                   range "0 .. 7";
                 }
               }
             }
           }
         }
         choice isid-dei_choice {
           case case_1 {
             leaf-list isid-dei {
               ordered-by user;
               description "DEI value 0-1";
               type union {
                 type string {
                   pattern "<.*>|$.*";
                 }
                 type uint32 {
                   range "0 .. 1";
                 }
               }
             }
           }
           case case_2 {
             leaf-list isid-dei-except {
               ordered-by user;
               description "DEI value 0-1";
               type union {
                 type string {
                   pattern "<.*>|$.*";
                 }
                 type uint32 {
                   range "0 .. 1";
                 }
               }
             }
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice arp-type_choice {
           case case_1 {
           }
         }
         list arp-sender-address {
           key name;
           ordered-by user;
           description "Match Arp header Sender IPv4 address";
           uses firewall_addr_object;
         }
         list arp-target-address {
           key name;
           ordered-by user;
           description "Match Arp header Target IPv4 address";
           uses firewall_addr_object;
         }
         container ip-version {
           description "Define IP version";
           uses apply-advanced;
           container ipv4 {
             description "Define L3/L4 match items to match IPv4 packets";
             uses apply-advanced;
             list source-address {
               key name;
               ordered-by user;
               description "Match IP source address";
               uses firewall_addr_object;
             }
             list destination-address {
               key name;
               ordered-by user;
               description "Match IP destination address";
               uses firewall_addr_object;
             }
             choice dscp_choice {
               case case_1 {
                 leaf-list dscp {
                   ordered-by user;
                   type string;
                 }
               }
               case case_2 {
                 leaf-list dscp-except {
                   ordered-by user;
                   type string;
                 }
               }
             }
             choice precedence_choice {
               case case_1 {
                 leaf-list precedence {
                   ordered-by user;
                   type string;
                 }
               }
               case case_2 {
                 leaf-list precedence-except {
                   ordered-by user;
                   type string;
                 }
               }
             }
             choice ip-options_choice {
               case case_1 {
               }
               case case_2 {
               }
             }
             leaf fragment-flags {
               description "Match fragment flags (in symbolic or hex formats) - (Ingress only)";
               type string;
             }
             leaf is-fragment {
               description "Match if packet is a fragment";
               type empty;
             }
             choice protocol_choice {
               case case_1 {
                 leaf-list protocol {
                   ordered-by user;
                   type string;
                 }
               }
               case case_2 {
                 leaf-list protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
               }
               case case_2 {
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip-source-address {
               key name;
               ordered-by user;
               description "Match IP source address";
               uses firewall_addr_object;
             }
             list ip-destination-address {
               key name;
               ordered-by user;
               description "Match IP destination address";
               uses firewall_addr_object;
             }
             choice ip-protocol_choice {
               case case_1 {
                 leaf-list ip-protocol {
                   ordered-by user;
                   type string;
                 }
               }
               case case_2 {
                 leaf-list ip-protocol-except {
                   ordered-by user;
                   type string;
                 }
               }
             }
             choice ip-precedence_choice {
               case case_1 {
                 leaf-list ip-precedence {
                   ordered-by user;
                   type string;
                 }
               }
               case case_2 {
                 leaf-list ip-precedence-except {
                   ordered-by user;
                   type string;
                 }
               }
             }
           }
           container ipv6 {
             description "Define L3/L4 match items to match IPv6 packets";
             uses apply-advanced;
             list source-address {
               key name;
               ordered-by user;
               description "Match source address";
               uses firewall_addr6_object;
             }
             list destination-address {
               key name;
               ordered-by user;
               description "Match destination address";
               uses firewall_addr6_object;
             }
             choice traffic-class_choice {
               case case_1 {
                 leaf-list traffic-class {
                   ordered-by user;
                   type string;
                 }
               }
               case case_2 {
                 leaf-list traffic-class-except {
                   ordered-by user;
                   type string;
                 }
               }
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
               }
               case case_2 {
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
               }
               case case_2 {
               }
             }
             choice extension-header_choice {
               case case_1 {
               }
               case case_2 {
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip6-source-address {
               key name;
               ordered-by user;
               description "Match source address";
               uses firewall_addr6_object;
             }
             list ip6-destination-address {
               key name;
               ordered-by user;
               description "Match destination address";
               uses firewall_addr6_object;
             }
           }
         }
         choice packet-length_choice {
           case case_1 {
           }
           case case_2 {
           }
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         choice policy-map-choice {
           case case_1 {
           }
           case case_2 {
           }
         }
         leaf syslog {
           description "System log (syslog) information about the packet";
           type empty;
         }
         leaf packet-capture {
           description "Enable packet capture for telemetry";
           type empty;
         }
         leaf forwarding-class {
           description "Classify packet to forwarding class";
           type string {
           }
         }
         leaf analyzer {
           description "Name of analyzer - (Ingress only)";
           type string {
           }
         }
         leaf port-mirror-instance {
           description "Port-mirror the packet to specified instance";
           type string {
           }
         }
         leaf port-mirror {
           description "Port-mirror the packet";
           type empty;
         }
         leaf inband-flow-telemetry-init {
           description "Initiate inband telemetry for a flow";
           type string;
         }
         leaf inband-flow-telemetry-terminate {
           description "Terminate inband telemetry for a flow";
           type string;
         }
         leaf next-hop-group {
           description "Use specified next-hop group";
           type string;
         }
         leaf sampling {
           description "Sample the packets";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf count {
           description "Count the packet in the named counter";
           type string {
           }
         }
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         leaf vlan {
           description "Name of VLAN - (Ingress only)";
           type string;
         }
         leaf interface {
           description "Switch traffic to the specified interface by-passing switching lookup - (Ingress only)";
           type union {
             type jt:interface-unit;
             type string {
               pattern "<.*>|$.*";
             }
           }
         }
       }
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
         }
         enum "trunk" {
           description "Interface mode is trunk";
         }
       }
     }
     leaf inter-switch-link {
       description "PVLAN inter switch link";
       type empty;
     }
     leaf reflective-relay {
       description "Reflective-relay mode for this interface";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           type jt:vlan-range;
         }
       }
     }
     leaf vlan-auto-sense {
       description "Enable VLAN auto sense on this interface";
       type empty;
     }
     leaf bridge-domain-type {
       description "Bridge domain type";
       type enumeration {
         enum "svlan" {
           description "Bridge domain type SVLAN";
         }
         enum "bvlan" {
           description "Bridge domain type BVLAN";
         }
       }
     }
     container vlan-rewrite {
       description "Specify VLAN translation";
       uses apply-advanced;
       list translate {
         key name;
         ordered-by user;
         description "Translate incoming VLAN tag";
         leaf name {
           description "Specify the incoming VLAN tag";
           type union {
             type string {
               pattern "<.*>|$.*";
             }
             type uint32 {
               range "1 .. 4094";
             }
           }
           mandatory true;
         }
         leaf to-vlan-id {
           description "Specify the bridge-domain VLAN-ID";
           type union {
             type string {
               pattern "<.*>|$.*";
             }
             type uint32 {
               range "1 .. 4094";
             }
           }
           mandatory true;
         }
       }
     }
     leaf native-vlan-id {
       description "Untagged packets on a trunk/tagged-access interface belong to this vlan";
       type string {
       }
     }
     choice isid_list {
       case case_1 {
         leaf isid-list {
           description "Specify the ISID list";
           type enumeration {
             enum "all-service-groups" {
               description "Map all ISIDs specified under the service-groups";
             }
             enum "all" {
               description "Map all ISIDs";
             }
           }
         }
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container storm-control {
       description "Storm control profile name to bind";
       uses apply-advanced;
       leaf profile-name {
         description "Profile name";
         type string;
         mandatory true;
       }
     }
     container recovery-timeout {
       description "Recovery timeout for this interface";
       leaf time-in-seconds {
         units "seconds";
         type union {
           type string {
             pattern "<.*>|$.*";
           }
           type uint32 {
             range "10 .. 3600";
           }
         }
       }
     }
   }
   grouping ethernet_policer {
     description "Define a policer";
     uses apply-advanced;
     choice bandwidth {
       case case_1 {
         leaf bandwidth-limit {
           description "Bandwidth limit";
           units "bits per second";
           type string;
         }
       }
     }
     leaf burst-size-limit {
       description "Burst size limit";
       units "bytes";
       type string;
       mandatory true;
     }
   }
   grouping ett-attributes {
     description "Transport ethernet configuration attributes";
     uses apply-advanced;
     leaf rate {
       description "Ethernet client signal rate";
       type enumeration {
         enum "100ge" {
           description "100 gigabit ethernet";
         }
       }
     }
   }
   grouping firewall_addr6_object {
     leaf name {
       description "Prefix to match";
       type jt:ipv6prefix;
     }
     leaf except {
       description "Match address not in this prefix";
       type empty;
     }
   }
   grouping firewall_addr_object {
     leaf name {
       description "Prefix to match";
       type jt:ipv4prefix;
     }
     leaf except {
       description "Match address not in this prefix";
       type empty;
     }
   }
   grouping firewall_flexible_match {
     description "Define a flexible match";
     leaf name {
       description "Flex match template name";
       type string {
       }
     }
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
       mandatory true;
     }
     leaf byte-offset {
       description "Byte offset after the match start point";
       type union {
         type string {
           pattern "<.*>|$.*";
         }
         type uint32 {
           range "0 .. 255";
         }
       }
     }
     leaf bit-offset {
       description "Bit offset after the (match-start + byte) offset";
       type union {
         type string {
           pattern "<.*>|$.*";
         }
         type uint32 {
           range "0 .. 7";
         }
       }
     }
     leaf bit-length {
       description "Length of integer input (1..32 bits), Optional length of string input (1..128 bits)";
       type union {
         type uint32;
         type string {
           pattern "<.*>|$.*";
         }
       }
       mandatory true;
     }
   }
   grouping firewall_hierpolicer {
     description "Define a hierarchical policer";
     leaf name {
       description "Hierarchical Policer name";
       type string {
       }
     }
     choice sharing {
       case case_1 {
         leaf logical-interface-policer {
           description "Hierarchical policer is a logical interface policer";
           type empty;
         }
       }
       case case_2 {
         leaf physical-interface-policer {
           description "Hierarchical policer is a physical interface policer";
           type empty;
         }
       }
     }
     leaf shared-bandwidth-policer {
       description "Share policer bandwidth among bundle links";
       type empty;
     }
     leaf filter-specific {
       description "Hierarchical policer is filter-specific";
       type empty;
     }
     container aggregate {
       description "Aggregate definition";
       presence "enable aggregate";
       uses hierarchical-policer-aggregate-bucket;
     }
     container premium {
       description "Premium definition";
       presence "enable premium";
       uses hierarchical-policer-premium-bucket;
     }
   }
   grouping firewall_mac_addr_object {
     leaf name {
       description "MAC address to match";
       type jt:mac-addr-prefix;
     }
     leaf except {
       description "Match MAC address not in this range";
       type empty;
     }
   }
   grouping firewall_policer {
     description "Define a policer";
     leaf name {
       description "Policer name";
       type string {
       }
     }
     uses apply-advanced;
     leaf logical-interface-policer {
       description "Policer is logical interface policer";
       type empty;
     }
     leaf physical-interface-policer {
       description "Policer is physical interface policer";
       type empty;
     }
     leaf logical-bandwidth-policer {
       description "Policer uses logical interface bandwidth";
       type empty;
     }
     leaf shared-bandwidth-policer {
       description "Share policer bandwidth among bundle links";
       type empty;
     }
     choice exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
             case case_2 {
               leaf bandwidth-percent {
                 description "Bandwidth limit in percentage";
                 units "percent";
                 type union {
                   type string {
                     pattern "<.*>|$.*";
                   }
                   type uint32 {
                     range "1 .. 100";
                   }
                 }
               }
             }
           }
           leaf burst-size-limit {
             description "Burst size limit";
             units "bytes";
             type string;
             mandatory true;
           }
         }
       }
       case case_2 {
       }
     }
     container counter {
       description "Define policer counter configuration";
       uses apply-advanced;
       leaf counter-id {
         description "Counter Index";
         type union {
           type string {
             pattern "<.*>|$.*";
           }
           type uint32 {
             range "0 .. 2";
           }
         }
         mandatory true;
       }
     }
     container then {
       description "Action to take if the rate limits are exceeded";
       uses apply-advanced;
       leaf discard {
         description "Discard the packet";
         type empty;
       }
       leaf loss-priority {
         description "Packet's loss priority";
         type enumeration {
           enum "low" {
             description "Loss priority low";
           }
           enum "high" {
             description "Loss priority high";
           }
           enum "medium-low" {
             description "Loss priority medium-low";
           }
           enum "medium-high" {
             description "Loss priority medium-high";
           }
         }
       }
       leaf forwarding-class {
         description "Classify packet to forwarding class";
         type string {
         }
       }
     }
   }
   grouping firewall_prefix_list {
     leaf name {
       description "Prefix list to match";
       type string;
     }
     leaf except {
       description "Match addresses not in this prefix list";
       type empty;
     }
   }
   grouping hierarchical-policer-aggregate-bucket {
     uses apply-advanced;
     choice hp-aggregate-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
             mandatory true;
           }
         }
       }
       case case_2 {
       }
     }
     container then {
       description "Action to take if the rate limits are exceeded";
       uses apply-advanced;
       choice hierarchical-policer-action {
         case case_1 {
           leaf discard {
             description "Discard the packet";
             type empty;
           }
         }
         case case_2 {
         }
         case case_3 {
         }
       }
     }
   }
   grouping hierarchical-policer-premium-bucket {
     uses apply-advanced;
     choice hp-premium-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
             mandatory true;
           }
         }
       }
       case case_2 {
       }
     }
     container then {
       description "Action to take if the rate limits are exceeded";
       uses apply-advanced;
       choice hierarchical-policer-action {
         case case_1 {
           leaf discard {
             description "Discard the packet";
             type empty;
           }
         }
       }
     }
   }
   grouping inband-telemetry-profile-type {
     description "Inband Telemetry Profile";
     leaf name {
       description "Profile Name";
       type string {
         length "1 .. 32";
       }
     }
     uses apply-advanced;
     leaf sample-rate {
       description "Ratio of packets to be sampled (1 out of N)";
       type union {
         type string {
           pattern "<.*>|$.*";
         }
         type uint32 {
           range "1 .. 16777215";
         }
       }
     }
     container collector {
       description "Profile options";
       uses apply-advanced;
       leaf source-address {
         description "Source IP Address";
         type jt:ipv4addr;
       }
       leaf destination-address {
         description "Destination IP Address";
         type jt:ipv4addr;
       }
       leaf destination-port {
         description "Destionation Port";
         type union {
           type string {
             pattern "<.*>|$.*";
           }
           type uint32 {
             range "1 .. 65535";
           }
         }
       }
       leaf maximum-clip-length {
         description "Maximum data packet length for export";
         default "256";
         type union {
           type string {
             pattern "<.*>|$.*";
           }
           type uint32 {
             range "64 .. 9000";
           }
         }
       }
       leaf mtu {
         description "Maximum size of export packet";
         default "9000";
         type union {
           type string {
             pattern "<.*>|$.*";
           }
           type uint32 {
             range "256 .. 9000";
           }
         }
       }
     }
   }
   grouping inet6_filter {
     description "Define an IPv6 firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf enhanced-mode {
       description "Define filter for chassis network-services enhanced mode";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
           }
           case case_2 {
           }
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice traffic-class_choice {
           case case_1 {
             leaf-list traffic-class {
               ordered-by user;
               type string;
             }
           }
           case case_2 {
             leaf-list traffic-class-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice ecn_choice {
           case case_1 {
             leaf-list ecn {
               ordered-by user;
               description "ECN value 0-3";
               type union {
                 type string {
                   pattern "<.*>|$.*";
                 }
                 type uint32 {
                   range "0 .. 3";
                 }
               }
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         list interface {
           key name;
           ordered-by user;
           description "Match interface name";
           uses match_interface_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice hop-limit_choice {
           case case_1 {
             leaf-list hop-limit {
               ordered-by user;
               description "Range of values";
               type string {
               }
             }
           }
           case case_2 {
             leaf-list hop-limit-except {
               ordered-by user;
               description "Range of values";
               type string {
               }
             }
           }
         }
         choice gre-key_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice slice_choice {
           case case_1 {
           }
           case case_2 {
           }
         }
       }
       container then {
         description "Action to take if the 'from' condition is matched";
         uses apply-advanced;
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         choice inet6cnt {
           case case_1 {
           }
           case case_2 {
             leaf count {
               description "Count the packet in the named counter";
               type string {
               }
             }
           }
         }
         leaf service-accounting {
           description "Count the packets for service accounting";
           type empty;
         }
         leaf log {
           description "Log the packet";
           type empty;
         }
         leaf syslog {
           description "System log (syslog) information about the packet";
           type empty;
         }
         leaf packet-capture {
           description "Enable packet capture for telemetry";
           type empty;
         }
         leaf port-mirror-instance {
           description "Port-mirror the packet to specified instance";
           type string {
           }
         }
         leaf port-mirror {
           description "Port-mirror the packet";
           type empty;
         }
         leaf sampling {
           description "Sample the packets";
           type empty;
         }
         leaf inband-flow-telemetry-init {
           description "Initiate inband telemetry for a flow";
           type string;
         }
         leaf inband-flow-telemetry-terminate {
           description "Terminate inband telemetry for a flow";
           type string;
         }
         leaf analyzer {
           description "Name of analyzer";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf traffic-class {
           description "Set traffic-class code point";
           type string;
         }
         leaf skip-services {
           description "Skip the services";
           type empty;
         }
         leaf service-filter-hit {
           description "Marked when packet processing by the current type of chained filters is done, the packet is directed to the next type of filters";
           type empty;
         }
         choice designation {
           case case_1 {
           }
           case case_2 {
           }
           case case_3 {
             leaf accept {
               description "Accept the packet";
               type empty;
             }
           }
           case case_4 {
             leaf discard {
               description "Discard the packet";
               type empty;
             }
           }
           case case_5 {
             leaf next {
               description "Continue to next term in a filter";
               type enumeration {
                 enum "term" {
                   description "Continue to next term in a filter";
                 }
               }
             }
           }
           case case_6 {
           }
           case case_7 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                   mandatory true;
                 }
                 leaf topology {
                   description "Packets are directed to specified topology";
                   type string {
                   }
                 }
               }
               leaf topology {
                 description "Packets are directed to specified topology";
                 type string {
                 }
               }
             }
           }
           case case_8 {
           }
           case case_9 {
             container routing-instance {
               description "Packets are directed to specified routing instance";
               leaf routing-instance-name {
                 description "Name of routing instance";
                 type string {
                 }
                 mandatory true;
               }
               leaf topology {
                 description "Packets are directed to specified topology";
                 type string {
                 }
               }
             }
           }
           case case_10 {
             leaf topology {
               description "Packets are directed to specified topology";
               type string {
               }
             }
           }
           case case_11 {
           }
           case case_12 {
           }
           case case_13 {
             container reject {
               presence "enable reject";
               description "Reject the packet";
               choice style {
                 case case_1 {
                   leaf no-route {
                     description "Send ICMPv6 No Route message";
                     type empty;
                   }
                 }
                 case case_2 {
                   leaf administratively-prohibited {
                     description "Send ICMPv6 Administratively Prohibited message";
                     type empty;
                   }
                 }
                 case case_3 {
                   leaf beyond-scope {
                     description "Send ICMPv6 Beyond Scope of Source Address message";
                     type empty;
                   }
                 }
                 case case_4 {
                   leaf address-unreachable {
                     description "Send ICMPv6 Address Unreachable message";
                     type empty;
                   }
                 }
                 case case_5 {
                   leaf port-unreachable {
                     description "Send ICMPv6 Port Unreachable message";
                     type empty;
                   }
                 }
                 case case_6 {
                   leaf policy-failed {
                     description "Source address failed ingress/egress policy";
                     type empty;
                   }
                 }
                 case case_7 {
                   leaf reject-route {
                     description "Reject route to destination";
                     type empty;
                   }
                 }
                 case case_8 {
                   leaf tcp-reset {
                     description "Send TCP Reset message";
                     type empty;
                   }
                 }
                 case case_9 {
                   leaf network-unreachable {
                     description "Send ICMPv4 Network Unreachable message";
                     status deprecated;
                     type empty;
                   }
                 }
                 case case_10 {
                   leaf host-unreachable {
                     description "Send ICMPv4 Host Unreachable message";
                     status deprecated;
                     type empty;
                   }
                 }
                 case case_11 {
                   leaf protocol-unreachable {
                     description "Send ICMPv4 Protocol Unreachable message";
                     status deprecated;
                     type empty;
                   }
                 }
                 case case_12 {
                   leaf source-route-failed {
                     description "Send ICMPv4 Source Route Failed message";
                     status deprecated;
                     type empty;
                   }
                 }
                 case case_13 {
                   leaf network-unknown {
                     description "Send ICMPv4 Network Unknown message";
                     status deprecated;
                     type empty;
                   }
                 }
                 case case_14 {
                   leaf host-unknown {
                     description "Send ICMPv4 Host Unknown message";
                     status deprecated;
                     type empty;
                   }
                 }
                 case case_15 {
                   leaf source-host-isolated {
                     description "Send ICMPv4 Source Host Isolated message";
                     status deprecated;
                     type empty;
                   }
                 }
                 case case_16 {
                   leaf network-prohibited {
                     description "Send ICMPv4 Network Prohibited message";
                     status deprecated;
                     type empty;
                   }
                 }
                 case case_17 {
                   leaf host-prohibited {
                     description "Send ICMPv4 Host Prohibited message";
                     status deprecated;
                     type empty;
                   }
                 }
                 case case_18 {
                   leaf bad-network-tos {
                     description "Send ICMPv4 Bad Network ToS message";
                     status deprecated;
                     type empty;
                   }
                 }
                 case case_19 {
                   leaf bad-host-tos {
                     description "Send ICMPv4 Bad Host ToS message";
                     status deprecated;
                     type empty;
                   }
                 }
                 case case_20 {
                   leaf precedence-violation {
                     description "Send ICMPv4 Precedence Violation message";
                     status deprecated;
                     type empty;
                   }
                 }
                 case case_21 {
                   leaf precedence-cutoff {
                     description "Send ICMPv4 Precedence Cutoff message";
                     status deprecated;
                     type empty;
                   }
                 }
               }
             }
           }
         }
       }
     }
   }
   grouping inet6_fuf {
     leaf name {
       description "Name of fast update filter";
       type string {
       }
     }
     uses apply-advanced;
     leaf interface-specific {
       description "Defined counters are interface specific";
       type empty;
       mandatory true;
     }
     leaf-list match-order {
       ordered-by user;
       type enumeration {
         enum "next-header" {
           description "Include next header protocol in match set";
         }
         enum "payload-protocol" {
           description "Include payload protocol in match set";
         }
         enum "source-address" {
           description "Include source-address in match set";
         }
         enum "destination-address" {
           description "Include destination-address in match set";
         }
         enum "source-port" {
           description "Include source-port in match set";
         }
         enum "destination-port" {
           description "Include destination-port in match set";
         }
         enum "traffic-class" {
           description "Include traffic-class (DSCP) in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr6_simple_object;
         }
         container destination-address {
           description "Match destination IP address";
           uses firewall_addr6_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice next-header_choice {
           case case_1 {
             container next-header {
               description "Match next header protocol type";
               uses match_simple_protocol_value;
             }
           }
         }
         choice traffic-class_choice {
           case case_1 {
             container traffic-class {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
                 mandatory true;
               }
               leaf topology {
                 description "Packets are directed to specified topology";
                 type string {
                 }
               }
             }
           }
         }
       }
     }
   }
   grouping firewall_addr6_simple_object {
     uses apply-advanced;
     leaf address {
       description "Prefix to match";
       type jt:ipv6prefix;
     }
   }
   grouping inet6_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
           }
           case case_2 {
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
         leaf tcp-flags {
           description "Match TCP flags (in symbolic or hex formats)";
           type string;
         }
         choice loss-priority_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
       }
       container then {
         description "Action to take if the 'from' condition is matched";
         uses apply-advanced;
         leaf count {
           description "Count the packet in the named counter";
           type string {
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
           }
         }
       }
     }
   }
   grouping inet_filter {
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     leaf enhanced-mode {
       description "Define filter for chassis network-services enhanced mode";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
           }
           case case_2 {
           }
         }
         list source-address {
           key name;
           ordered-by user;
           description "Match IP source address";
           uses firewall_addr_object;
         }
         list destination-address {
           key name;
           ordered-by user;
           description "Match IP destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         choice packet-length_choice {
           case case_1 {
             leaf-list packet-length {
               ordered-by user;
               description "Range of values";
               type string {
               }
             }
           }
           case case_2 {
           }
         }
         choice dscp_choice {
           case case_1 {
             leaf-list dscp {
               ordered-by user;
               type string;
             }
           }
           case case_2 {
             leaf-list dscp-except {
               ordered-by user;
               type string;
             }
           }
         }
         choice ecn_choice {
           case case_1 {
             leaf-list ecn {
               ordered-by user;
               description "ECN value 0-3";
               type union {
                 type string {
                   pattern "<.*>|$.*";
                 }
                 type uint32 {
                   range "0 .. 3";
                 }
               }
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags (in symbolic or hex formats) - (Ingress only)";
           type string {
           }
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
           }
           case case_2 {
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
           }
           case case_2 {
           }
         }
         choice ah-spi_choice {
           case case_1 {
           }
           case case_2 {
           }
         }
         list interface {
           key name;
           ordered-by user;
           description "Match interface name";
           uses match_interface_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice rat-type_choice {
           case case_1 {
             leaf-list rat-type {
               ordered-by user;
               type string;
             }
           }
           case case_2 {
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
           }
         }
         choice gre-key_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice slice_choice {
           case case_1 {
           }
           case case_2 {
           }
         }
       }
       container then {
         description "Action to take if the 'from' condition is matched";
         uses apply-advanced;
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         choice inetcnt {
           case case_1 {
           }
           case case_2 {
             leaf count {
               description "Count the packet in the named counter";
               type string {
               }
             }
           }
         }
         leaf service-accounting {
           description "Count the packets for service accounting";
           type empty;
         }
         leaf skip-services {
           description "Skip the services";
           type empty;
         }
         leaf log {
           description "Log the packet";
           type empty;
         }
         leaf syslog {
           description "System log (syslog) information about the packet";
           type empty;
         }
         leaf packet-capture {
           description "Enable packet capture for telemetry";
           type empty;
         }
         leaf port-mirror-instance {
           description "Port-mirror the packet to specified instance";
           type string {
           }
         }
         leaf port-mirror {
           description "Port-mirror the packet";
           type empty;
         }
         leaf sampling {
           description "Sample the packets";
           type empty;
         }
         leaf inband-flow-telemetry-init {
           description "Initiate inband telemetry for a flow";
           type string;
         }
         leaf inband-flow-telemetry-terminate {
           description "Terminate inband telemetry for a flow";
           type string;
         }
         leaf analyzer {
           description "Name of analyzer - (Ingress only)";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf service-filter-hit {
           description "Marked when packet processing by the current type of chained filters is done, the packet is directed to the next type of filters";
           type empty;
         }
         choice designation {
           case case_1 {
             leaf accept {
               description "Accept the packet";
               type empty;
             }
           }
           case case_2 {
             container discard {
               presence "enable discard";
               description "Discard the packet";
               uses apply-advanced;
               leaf accounting {
                 description "Named discard collector for packet";
                 type string;
               }
             }
           }
           case case_3 {
             leaf next {
               description "Continue to next term in a filter";
               type enumeration {
                 enum "term" {
                   description "Continue to next term in a filter";
                 }
               }
             }
           }
           case case_4 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                   mandatory true;
                 }
                 leaf topology {
                   description "Packets are directed to specified topology";
                   type string {
                   }
                 }
               }
               leaf topology {
                 description "Packets are directed to specified topology";
                 type string {
                 }
               }
             }
           }
           case case_5 {
           }
           case case_6 {
             container routing-instance {
               description "Packets are directed to specified routing instance";
               leaf routing-instance-name {
                 description "Name of routing instance";
                 type string {
                 }
                 mandatory true;
               }
               leaf topology {
                 description "Packets are directed to specified topology";
                 type string {
                 }
               }
             }
           }
           case case_7 {
             leaf topology {
               description "Packets are directed to specified topology";
               type string {
               }
             }
           }
           case case_8 {
           }
           case case_9 {
           }
           case case_10 {
             leaf ipsec-sa {
               description "Use specified IPSec security association";
               type string;
             }
           }
           case case_11 {
             leaf next-hop-group {
               description "Use specified next-hop group";
               type string;
             }
           }
           case case_12 {
           }
           case case_13 {
           }
           case case_14 {
             container reject {
               presence "enable reject";
               description "Reject the packet";
               choice style {
                 case case_1 {
                   leaf network-unreachable {
                     description "Send ICMP Network Unreachable message";
                     type empty;
                   }
                 }
                 case case_2 {
                   leaf host-unreachable {
                     description "Send ICMP Host Unreachable message";
                     type empty;
                   }
                 }
                 case case_3 {
                   leaf protocol-unreachable {
                     description "Send ICMP Protocol Unreachable message";
                     type empty;
                   }
                 }
                 case case_4 {
                   leaf port-unreachable {
                     description "Send ICMP Port Unreachable message";
                     type empty;
                   }
                 }
                 case case_5 {
                   leaf fragmentation-needed {
                     description "Send ICMP Fragmentation Needed message";
                     type empty;
                   }
                 }
                 case case_6 {
                   leaf source-route-failed {
                     description "Send ICMP Source Route Failed message";
                     type empty;
                   }
                 }
                 case case_7 {
                   leaf network-unknown {
                     description "Send ICMP Network Unknown message";
                     type empty;
                   }
                 }
                 case case_8 {
                   leaf host-unknown {
                     description "Send ICMP Host Unknown message";
                     type empty;
                   }
                 }
                 case case_9 {
                   leaf source-host-isolated {
                     description "Send ICMP Source Host Isolated message";
                     type empty;
                   }
                 }
                 case case_10 {
                   leaf network-prohibited {
                     description "Send ICMP Network Prohibited message";
                     type empty;
                   }
                 }
                 case case_11 {
                   leaf host-prohibited {
                     description "Send ICMP Host Prohibited message";
                     type empty;
                   }
                 }
                 case case_12 {
                   leaf bad-network-tos {
                     description "Send ICMP Bad Network ToS message";
                     type empty;
                   }
                 }
                 case case_13 {
                   leaf bad-host-tos {
                     description "Send ICMP Bad Host ToS message";
                     type empty;
                   }
                 }
                 case case_14 {
                   leaf administratively-prohibited {
                     description "Send ICMP Administratively Prohibited message";
                     type empty;
                   }
                 }
                 case case_15 {
                   leaf precedence-violation {
                     description "Send ICMP Precedence Violation message";
                     type empty;
                   }
                 }
                 case case_16 {
                   leaf precedence-cutoff {
                     description "Send ICMP Precedence Cutoff message";
                     type empty;
                   }
                 }
                 case case_17 {
                   leaf tcp-reset {
                     description "Send TCP Reset message";
                     type empty;
                   }
                 }
               }
             }
           }
           case case_15 {
           }
         }
         leaf dscp {
           description "Set Differentiated Services (DiffServ) code point";
           type string;
         }
         leaf outer-dscp {
           description "Set differentiated services code point for outer header";
           type string;
         }
         leaf qfi {
           description "Set QFI for N3 interface";
           type string;
         }
         leaf nat-translated-sip {
           description "IPv4 source address used for Static NAT";
           type jt:ipv4addr;
         }
         leaf nat-translated-srcport {
           description "UDP/TCP source port used for Static NAT";
           type union {
             type string {
               pattern "<.*>|$.*";
             }
             type uint16 {
               range "0 .. 65535";
             }
           }
         }
         leaf nat-translated-dip {
           description "IPv4 destination address used for Static NAT";
           type jt:ipv4addr;
         }
         leaf nat-translated-dstport {
           description "UDP/TCP destination port used for Static NAT";
           type union {
             type string {
               pattern "<.*>|$.*";
             }
             type uint16 {
               range "0 .. 65535";
             }
           }
         }
         leaf prefix-action {
           description "Police or count packets using named prefix action";
           type string {
           }
         }
       }
     }
   }
   grouping inet_fuf {
     leaf name {
       description "Name of fast update filter";
       type string {
       }
     }
     uses apply-advanced;
     leaf interface-specific {
       description "Defined counters are interface specific";
       type empty;
       mandatory true;
     }
     leaf-list match-order {
       ordered-by user;
       type enumeration {
         enum "protocol" {
           description "Include IP protocol in match set";
         }
         enum "source-address" {
           description "Include source-address in match set";
         }
         enum "destination-address" {
           description "Include destination-address in match set";
         }
         enum "source-port" {
           description "Include source-port in match set";
         }
         enum "destination-port" {
           description "Include destination-port in match set";
         }
         enum "dscp" {
           description "Include Differentiated Services (DiffServ) code point in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr_simple_object;
         }
         container destination-address {
           description "Match destination IP address";
           uses firewall_addr_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice protocol_choice {
           case case_1 {
             container protocol {
               description "Match IP protocol type";
               uses match_simple_protocol_value;
             }
           }
         }
         choice dscp_choice {
           case case_1 {
             container dscp {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
                 mandatory true;
               }
               leaf topology {
                 description "Packets are directed to specified topology";
                 type string {
                 }
               }
             }
           }
         }
       }
     }
   }
   grouping firewall_addr_simple_object {
     uses apply-advanced;
     leaf address {
       description "Prefix to match";
       type jt:ipv4prefix;
     }
   }
   grouping inet_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice protocol_choice {
           case case_1 {
             leaf-list protocol {
               ordered-by user;
               type string;
             }
           }
           case case_2 {
             leaf-list protocol-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
           }
         }
         choice esp-spi_choice {
           case case_1 {
             leaf-list esp-spi {
               ordered-by user;
               description "Range of values";
               type string;
             }
           }
           case case_2 {
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
               }
             }
           }
           case case_2 {
           }
         }
         leaf fragment-flags {
           description "Match fragment flags";
           type string;
         }
         leaf tcp-flags {
           description "Match TCP flags (in symbolic or hex formats)";
           type string;
         }
         choice ah-spi_choice {
           case case_1 {
           }
           case case_2 {
           }
         }
         choice loss-priority_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
       }
       container then {
         description "Action to take if the 'from' condition is matched";
         uses apply-advanced;
         leaf count {
           description "Count the packet in the named counter";
           type string {
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
           }
         }
       }
     }
   }
   grouping interface_set_type {
     leaf name {
       description "Interface set name";
       type string {
       }
     }
     uses apply-advanced;
     list interface-list {
       key name;
       ordered-by user;
       description "Interface list";
       leaf name {
         description "Interface name";
         type union {
           type jt:interface-wildcard;
           type string {
             pattern "<.*>|$.*";
           }
         }
       }
       uses apply-advanced;
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping interfaces_type {
     description "Physical interface";
     leaf name {
       type string;
     }
     uses apply-advanced;
     leaf description {
       description "Text description of interface";
       type string;
     }
     leaf external-model-name {
       description "Name for interface as configured using 3rd-party model";
       type string;
     }
     container management-ethernet-redundancy {
       presence "enable management-ethernet-redundancy";
       description "Management Interface Redundancy";
       uses apply-advanced;
       choice enable_choice {
         case case_1 {
           leaf redundancy-enable {
             description "Enable Managment Ethernet Redundancy";
             type empty;
           }
         }
         case case_2 {
           leaf redundancy-disable {
             description "Disable  Managment Ethernet Redundancy";
             type empty;
           }
         }
       }
       leaf connectivity-test-interval {
         description "Connectivity test interval";
         default "5";
         units "seconds";
         type union {
           type string {
             pattern "<.*>|$.*";
           }
           type uint32 {
             range "1 .. 10";
           }
         }
       }
       leaf connectivity-test-response-interval {
         description "Connectivity test response wait time";
         default "5";
         units "seconds";
         type union {
           type string {
             pattern "<.*>|$.*";
           }
           type uint32 {
             range "1 .. 10";
           }
         }
       }
       leaf remote-ipv4-address {
         description "Destination IPV4 address to reach remote ";
         default "nil";
         type jt:ipv4addr;
       }
       leaf remote-ipv6-address {
         description "Destination IPV6 address to reach remote";
         default "nil";
         type jt:ipv6addr;
       }
       leaf number-of-connectivity-retries {
         description "Number of Connectivity retries ";
         default "2";
         type union {
           type string {
             pattern "<.*>|$.*";
           }
           type uint32 {
             range "1 .. 8";
           }
         }
       }
     }
     choice enable-disable {
       case case_1 {
         leaf disable {
           description "Disable this interface";
           type empty;
         }
       }
     }
     container traceoptions {
       presence "enable traceoptions";
       description "Interface trace options";
       uses apply-advanced;
       list flag {
         key name;
         ordered-by user;
         description "Tracing parameters";
         leaf name {
           type enumeration {
             enum "ipc" {
               description "Trace interface IPC messages";
             }
             enum "event" {
               description "Trace interface events";
             }
             enum "media" {
               description "Trace interface media changes";
             }
             enum "all" {
               description "Enable all interface trace flags";
             }
           }
         }
       }
     }
     leaf passive-monitor-mode {
       description "Use interface to tap packets from another router";
       type empty;
     }
     choice keepalive_choices {
       case case_1 {
         container keepalives {
           description "Send or demand keepalive messages";
           presence "enable keepalives";
           uses keepalives_type;
         }
       }
       case case_2 {
         leaf no-keepalives {
           description "Do not send keepalive messages";
           type empty;
         }
       }
     }
     choice traps-choice {
       leaf traps {
         description "Enable SNMP notifications on state changes";
         type empty;
       }
       leaf no-traps {
         description "Don't enable SNMP notifications on state changes";
         type empty;
       }
     }
     choice interface-mib-choice {
       leaf interface-mib {
         description "Enable interface-related MIBs";
         type empty;
       }
       leaf no-interface-mib {
         description "Don't enable interface-related MIBs";
         type empty;
       }
     }
     leaf accounting-profile {
       description "Accounting profile name";
       type string;
     }
     choice scheduler_type {
       case case_1 {
         choice per-unit-scheduler-choice {
           leaf per-unit-scheduler {
             description "Enable subunit queuing on Frame Relay or VLAN IQ interface";
             type empty;
           }
           leaf no-per-unit-scheduler {
             description "Don't enable subunit queuing on Frame Relay or VLAN IQ interface";
             type empty;
           }
         }
       }
       case case_2 {
         leaf shared-scheduler {
           description "Enabled shared queuing on an IQ2 interface";
           type empty;
         }
       }
       case case_3 {
         container hierarchical-scheduler {
           presence "enable hierarchical-scheduler";
           description "Enable hierarchical scheduling";
           leaf maximum-hierarchy-levels {
             description "Maximum hierarchy levels";
             type union {
               type string {
                 pattern "<.*>|$.*";
               }
               type uint32;
             }
           }
           leaf implicit-hierarchy {
             description "Implicit hierarchy (follows interface hierarchy)";
             type empty;
           }
         }
       }
     }
     leaf l2tp-maximum-session {
       description "Maximum L2TP session";
       type union {
         type string {
           pattern "<.*>|$.*";
         }
         type uint32 {
           range "0 .. 64000";
         }
       }
     }
     leaf schedulers {
       description "Number of schedulers to allocate for interface";
       type union {
         type uint32;
         type string {
           pattern "<.*>|$.*";
         }
       }
     }
     leaf port-extender-cascade-port {
       description "NGPE Cascade port";
       type empty;
     }
     leaf dce {
       description "Respond to Frame Relay status enquiry messages";
       type empty;
     }
     choice vlan_tag_mode {
       case case_1 {
         leaf vlan-tagging {
           description "802.1q VLAN tagging support";
           type empty;
         }
       }
       case case_2 {
         leaf stacked-vlan-tagging {
           description "Stacked 802.1q VLAN tagging support";
           type empty;
         }
       }
       case case_3 {
       }
       case case_4 {
       }
     }
     leaf number-of-sub-ports {
       description "Number of channels to create for a port";
       type union {
         type string {
           pattern "<.*>|$.*";
         }
         type uint32 {
           range "1 .. 8";
         }
       }
     }
     leaf speed {
       description "Link speed";
       type enumeration {
         enum "auto" {
           description "Enable auto negotiation of interface speed";
         }
         enum "auto-10m-100m" {
           description "Enable auto negotiation of limiting interface speed to 10m/100m";
         }
         enum "10m" {
         }
         enum "100m" {
         }
         enum "1g" {
         }
         enum "2.5g" {
         }
         enum "5g" {
         }
         enum "10g" {
         }
         enum "25g" {
         }
         enum "40g" {
         }
         enum "50g" {
         }
         enum "100g" {
         }
         enum "200g" {
         }
         enum "400g" {
         }
         enum "800g" {
         }
         enum "oc3" {
         }
         enum "oc12" {
         }
         enum "oc48" {
         }
         enum "1.6t" {
         }
       }
     }
     leaf mtu {
       description "Maximum transmit packet size";
       type union {
         type string {
           pattern "<.*>|$.*";
         }
         type uint32;
       }
     }
     container hold-time {
       description "Hold time for link up and link down";
       leaf up {
         description "Link up hold time";
         units "milliseconds";
         type union {
           type uint32;
           type string {
             pattern "<.*>|$.*";
           }
         }
         mandatory true;
       }
       leaf down {
         description "Link down hold time";
         units "milliseconds";
         type union {
           type uint32;
           type string {
             pattern "<.*>|$.*";
           }
         }
         mandatory true;
       }
     }
     container port-extender {
       description "Tunnel binding information for the extended port";
       uses apply-advanced;
       container vxlan {
         presence "enable vxlan";
         description "VXLAN binding information for the extended port";
         uses apply-advanced;
         leaf end-point {
           description "Satellite loopback IP address";
           type jt:ipaddr;
           mandatory true;
         }
         leaf vni {
           description "VNI of the satellite extended-port";
           type union {
             type string {
               pattern "<.*>|$.*";
             }
             type uint32 {
               range "0 .. 16777214";
             }
           }
           mandatory true;
         }
       }
     }
     container link-degrade-monitor {
       presence "enable link-degrade-monitor";
       description "Enable link degrade monitoring";
       uses apply-advanced;
       choice enable_choice {
         case case_1 {
           leaf link-degrade-monitor-enable {
             description "Enable Link Degrade Monitoring";
             type empty;
           }
         }
         case case_2 {
           leaf no-link-degrade-monitor-enable {
             description "Disable Link Degrade Monitoring";
             type empty;
           }
         }
       }
       container actions {
         description "Action upon link degrade event";
         uses apply-advanced;
         choice action_choice {
           case case_1 {
             leaf media-based {
               description "Media based";
               type empty;
             }
           }
         }
       }
       container recovery {
         description "Link degrade recovery mechanism";
         uses apply-advanced;
         leaf timer {
           description "Auto recovery timer in seconds";
           default "1800";
           type union {
             type uint32;
             type string {
               pattern "<.*>|$.*";
             }
           }
         }
         choice receovery_choice {
           case case_1 {
             leaf auto {
               description "Automatic recovery";
               type empty;
             }
           }
           case case_2 {
             leaf manual {
               description "Manual recovery";
               type empty;
             }
           }
         }
       }
       container thresholds {
         description "Link degrade threshold parameters";
         uses apply-advanced;
         leaf set {
           description "BER at which link considered degraded(1..16)";
           default "1e-7";
           type string {
           }
         }
         leaf clear {
           description "BER at which link considered improved(1..16)";
           default "1e-12";
           type string {
           }
         }
         leaf warning-set {
           description "BER at which link degrade warning raised(1..16)";
           default "1e-9";
           type string {
           }
         }
         leaf warning-clear {
           description "BER at which link degrade warning cleared(1..16)";
           default "1e-11";
           type string {
           }
         }
         leaf interval {
           description "Consecutive link degrade events";
           default "10";
           type union {
             type string {
               pattern "<.*>|$.*";
             }
             type uint32 {
               range "1 .. 256";
             }
           }
         }
       }
     }
     container satop-options {
       description "Structure-Agnostic TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container cesopsn-options {
       description "Structure-Aware TDM over Packet protocol options";
       uses apply-advanced;
       leaf idle-pattern {
         description "An 8-bit hexadecimal pattern to replace TDM data in a lost packet";
         type union {
           type string {
             pattern "<.*>|$.*";
           }
           type uint32 {
             range "0 .. 255";
           }
         }
       }
       leaf packetization-latency {
         description "Number of microseconds to create packets";
         units "microseconds";
         type union {
           type string {
             pattern "<.*>|$.*";
           }
           type uint32 {
             range "1000 .. 8000";
           }
         }
       }
       leaf payload-size {
         description "Number of payload bytes per packet";
         type union {
           type string {
             pattern "<.*>|$.*";
           }
           type uint32 {
             range "64 .. 1024";
           }
         }
       }
       container excessive-packet-loss-rate {
         description "Packet loss options";
         uses apply-advanced;
         leaf threshold {
           description "Percentile designating the threshold of excessive packet loss rate";
           type union {
             type string {
               pattern "<.*>|$.*";
             }
             type uint8 {
               range "1 .. 100";
             }
           }
         }
         leaf sample-period {
           description "Number of milliseconds over which excessive packet loss rate is calculated";
           type union {
             type string {
               pattern "<.*>|$.*";
             }
             type uint32 {
               range "1000 .. 65535";
             }
           }
         }
       }
       choice jitter-buffer-size {
         case case_1 {
           leaf jitter-buffer-packets {
             description "Number of packets in jitter buffer before packet data is played out in the line";
             type union {
               type string {
                 pattern "<.*>|$.*";
               }
               type uint32 {
                 range "1 .. 64";
               }
             }
           }
         }
         case case_2 {
           leaf jitter-buffer-latency {
             description "Number of milliseconds delay in jitter buffer before packet data is played out in the line";
             units "milliseconds";
             type union {
               type string {
                 pattern "<.*>|$.*";
               }
               type uint32 {
                 range "1 .. 1000";
               }
             }
           }
         }
         case case_3 {
           leaf jitter-buffer-auto-adjust {
             description "Automatically adjust jitter buffer";
             type empty;
           }
         }
       }
       leaf bit-rate {
         description "In multiples of DS0";
         type union {
           type string {
             pattern "<.*>|$.*";
           }
           type uint32 {
             range "1 .. 10240";
           }
         }
       }
     }
     container clocking {
       description "Interface clock source";
       choice clocking_choices {
         case case_1 {
           leaf internal {
             description "Clocking provided by local system";
             type empty;
           }
         }
         case case_2 {
           container external {
             presence "enable external";
             description "Clocking provided by DCE (loop timing)";
           }
         }
       }
     }
     leaf link-mode {
       description "Link operational mode";
       type enumeration {
         enum "automatic" {
           description "Automatically negotiate duplex";
         }
         enum "half-duplex" {
           description "Half-duplex operation";
         }
         enum "full-duplex" {
           description "Full-duplex operation";
         }
       }
     }
     leaf media-type {
       description "Interface media type (copper or fiber)";
       type enumeration {
         enum "copper" {
           description "Copper as media";
         }
         enum "fiber" {
           description "Fiber as media";
         }
       }
     }
     leaf encapsulation {
       description "Physical link-layer encapsulation";
       type enumeration {
         enum "ethernet" {
           description "Ethernet physical media";
         }
         enum "fddi" {
           description "FDDI physical media";
         }
         enum "token-ring" {
           description "Token Ring physical media";
         }
         enum "ppp" {
           description "Serial PPP device";
         }
         enum "ppp-ccc" {
           description "Serial PPP device for a cross-connect";
         }
         enum "ppp-tcc" {
           description "Serial PPP device for a translational cross-connect";
         }
         enum "ether-vpls-ppp" {
           description "Ethernet VPLS over PPP (bridging) device";
         }
         enum "frame-relay" {
           description "Frame Relay encapsulation";
         }
         enum "frame-relay-ccc" {
           description "Frame Relay for cross-connect";
         }
         enum "frame-relay-tcc" {
           description "Frame Relay for translational cross-connect";
         }
         enum "extended-frame-relay-ccc" {
           description "Any Frame Relay DLCI for cross-connect";
         }
         enum "extended-frame-relay-tcc" {
           description "Any Frame Relay DLCI for translational cross-connect";
         }
         enum "flexible-frame-relay" {
           description "Multiple Frame Relay encapsulations";
         }
         enum "frame-relay-port-ccc" {
           description "Frame Relay port encapsulation for a cross-connect";
         }
         enum "frame-relay-ether-type" {
           description "Cisco-compatible Frame Relay encapsulation";
         }
         enum "frame-relay-ether-type-tcc" {
           description "Cisco-compatible Frame Relay encapsulation for translational cross-connect";
         }
         enum "extended-frame-relay-ether-type-tcc" {
           description "Cisco-compatible Frame Relay encapsulation any DLCI for translational cross-connect";
         }
         enum "cisco-hdlc" {
           description "Cisco-compatible HDLC framing";
         }
         enum "cisco-hdlc-ccc" {
           description "Cisco-compatible HDLC framing for a cross-connect";
         }
         enum "cisco-hdlc-tcc" {
           description "Cisco-compatible HDLC framing for a translational cross-connect";
         }
         enum "vlan-ccc" {
           description "802.1q tagging for a cross-connect";
         }
         enum "extended-vlan-ccc" {
           description "Nonstandard TPID tagging for a cross-connect";
         }
         enum "ethernet-ccc" {
           description "Ethernet cross-connect";
         }
         enum "flexible-ethernet-services" {
           description "Allows per-unit Ethernet encapsulation configuration";
         }
         enum "smds-dxi" {
           description "SMDS DXI framing";
         }
         enum "atm-pvc" {
           description "ATM permanent virtual circuits";
         }
         enum "atm-ccc-cell-relay" {
           description "ATM cell relay encapsulation for cross-connect";
         }
         enum "ethernet-over-atm" {
           description "Ethernet over ATM encapsulation";
         }
         enum "ethernet-tcc" {
           description "Ethernet translational cross-connect";
         }
         enum "extended-vlan-tcc" {
           description "802.1q tagging for a translational cross-connect";
         }
         enum "multilink-frame-relay-uni-nni" {
           description "Multilink Frame Relay UNI NNI (FRF.16) encapsulation";
         }
         enum "satop" {
           description "Structure-Agnostic TDM over Packet encapsulation";
         }
         enum "cesopsn" {
           description "Structure-Agnostic TDM over Packet encapsulation";
         }
         enum "ima" {
           description "Inverse Multiplexing for ATM";
         }
         enum "ethernet-vpls" {
           description "Ethernet virtual private LAN service";
         }
         enum "ethernet-bridge" {
           description "Ethernet layer-2 bridging";
         }
         enum "vlan-vpls" {
           description "VLAN virtual private LAN service";
         }
         enum "vlan-vci-ccc" {
           description "CCC for VLAN Q-in-Q and ATM VPI/VCI interworking";
         }
         enum "extended-vlan-vpls" {
           description "Extended VLAN virtual private LAN service";
         }
         enum "extended-vlan-bridge" {
           description "VLAN layer-2 bridging";
         }
         enum "multilink-ppp" {
           description "Multilink PPP";
         }
         enum "generic-services" {
           description "Generic services";
         }
       }
     }
     leaf network-isolation-profile {
       description "Attach a network isolation profile on this interface";
       type string;
     }
     container framing {
       description "Frame type";
       uses apply-advanced;
       choice frame {
         case case_1 {
           leaf lan-phy {
             description "802.3ae 10-Gbps LAN-mode interface";
             type empty;
           }
         }
         case case_2 {
           leaf wan-phy {
             description "802.3ae 10-Gbps WAN-mode interface";
             type empty;
           }
         }
         case case_3 {
           leaf sonet {
             description "SONET framing";
             type empty;
           }
         }
         case case_4 {
           leaf sdh {
             description "SDH framing";
             type empty;
           }
         }
       }
     }
     container lmi {
       description "Local Management Interface settings";
       uses apply-advanced;
       leaf n391dte {
         description "DTE full status polling interval";
         type union {
           type string {
             pattern "<.*>|$.*";
           }
           type uint16 {
             range "1 .. 255";
           }
         }
       }
       leaf n392dce {
         description "DCE error threshold";
         type union {
           type string {
             pattern "<.*>|$.*";
           }
           type uint16 {
             range "1 .. 10";
           }
         }
       }
       leaf n392dte {
         description "DTE error threshold";
         type union {
           type string {
             pattern "<.*>|$.*";
           }
           type uint16 {
             range "1 .. 10";
           }
         }
       }
       leaf n393dce {
         description "DCE monitored event count";
         type union {
           type string {
             pattern "<.*>|$.*";
           }
           type uint16 {
             range "1 .. 10";
           }
         }
       }
       leaf n393dte {
         description "DTE monitored event count";
         type union {
           type string {
             pattern "<.*>|$.*";
           }
           type uint16 {
             range "1 .. 10";
           }
         }
       }
       leaf t391dte {
         description "DTE polling timer";
         units "seconds";
         type union {
           type string {
             pattern "<.*>|$.*";
           }
           type uint16 {
             range "5 .. 30";
           }
         }
       }
       leaf t392dce {
         description "DCE polling verification timer";
         units "seconds";
         type union {
           type string {
             pattern "<.*>|$.*";
           }
           type uint16 {
             range "5 .. 30";
           }
         }
       }
       leaf lmi-type {
         description "Specify the Frame Relay LMI type";
         type enumeration {
           enum "ansi" {
             description "Use ANSI Annex D LMI";
           }
           enum "itu" {
             description "Use ITU Q933a Annex A LMI";
           }
           enum "c-lmi" {
             description "Use Consortium LMI";
           }
         }
       }
     }
     container mlfr-uni-nni-bundle-options {
       description "Multilink Frame Relay UNI NNI (FRF.16) management settings";
       uses apply-advanced;
       container cisco-interoperability {
         description "FRF.16 Cisco interoperability settings";
         uses apply-advanced;
         leaf send-lip-remove-link-for-link-reject {
           description "Send Link Integrity Protocol remove link on receiving add-link rejection";
           type empty;
         }
       }
       leaf mrru {
         description "Maximum received reconstructed unit";
         units "bytes";
         type union {
           type string {
             pattern "<.*>|$.*";
           }
           type uint16 {
             range "1500 .. 4500";
           }
         }
       }
       leaf yellow-differential-delay {
         description "Yellow differential delay among bundle links to give warning";
         units "milliseconds";
         type union {
           type string {
             pattern "<.*>|$.*";
           }
           type uint16 {
             range "3 .. 2000";
           }
         }
       }
       leaf red-differential-delay {
         description "Red differential delay among bundle links to take action";
         units "milliseconds";
         type union {
           type string {
             pattern "<.*>|$.*";
           }
           type uint16 {
             range "5 .. 2000";
           }
         }
       }
       leaf action-red-differential-delay {
         description "Type of actions when differential delay exceeds red limit";
         type enumeration {
           enum "remove-link" {
             description "Remove bundle link from service when exceeding red limit";
           }
           enum "disable-tx" {
             description "Disable transfer of bundle link when exceeding red limit";
           }
         }
       }
       leaf fragment-threshold {
         description "Fragmentation threshold";
         units "bytes";
         type union {
           type string {
             pattern "<.*>|$.*";
           }
           type uint32 {
             range "64 .. 16320";
           }
         }
       }
       leaf drop-timeout {
         description "Drop timeout";
         units "milliseconds";
         type union {
           type string {
             pattern "<.*>|$.*";
           }
           type uint16 {
             range "0 .. 2000";
           }
         }
       }
       leaf link-layer-overhead {
         description "Link layer bit stuffing overhead (0.0 .. 50.0 percent)";
         type jt:unsigned-float;
       }
       leaf lmi-type {
         description "Specify the multilink Frame Relay UNI NNI LMI type";
         type enumeration {
           enum "ansi" {
             description "Use ANSI Annex D LMI";
           }
           enum "itu" {
             description "Use ITU Q933a Annex A LMI";
           }
           enum "c-lmi" {
             description "Use Consortium LMI";
           }
         }
       }
       leaf minimum-links {
         description "Minimum number of links to sustain the bundle";
         type union {
           type string {
             pattern "<.*>|$.*";
           }
           type uint16 {
             range "1 .. 8";
           }
         }
       }
       leaf hello-timer {
         description "LIP hello timer";
         type union {
           type string {
             pattern "<.*>|$.*";
           }
           type uint16 {
             range "5 .. 180";
           }
         }
       }
       leaf acknowledge-timer {
         description "LIP ack timer";
         type union {
           type string {
             pattern "<.*>|$.*";
           }
           type uint16 {
             range "1 .. 10";
           }
         }
       }
       leaf acknowledge-retries {
         description "LIP ack retry times";
         type union {
           type string {
             pattern "<.*>|$.*";
           }
           type uint16 {
             range "1 .. 5";
           }
         }
       }
       leaf n391 {
         description "Multilink Frame Relay UNI NNI full status polling counter";
         type union {
           type string {
             pattern "<.*>|$.*";
           }
           type uint16 {
             range "1 .. 255";
           }
         }
       }
       leaf n392 {
         description "Multilink Frame Relay UNI NNI LMI error threshold";
         type union {
           type string {
             pattern "<.*>|$.*";
           }
           type uint16 {
             range "1 .. 10";
           }
         }
       }
       leaf n393 {
         description "Multilink Frame Relay UNI NNI LMI monitored event count";
         type union {
           type string {
             pattern "<.*>|$.*";
           }
           type uint16 {
             range "1 .. 10";
           }
         }
       }
       leaf t391 {
         description "Multilink Frame Relay UNI NNI link integrity verify polling timer";
         type union {
           type string {
             pattern "<.*>|$.*";
           }
           type uint16 {
             range "5 .. 30";
           }
         }
       }
       leaf t392 {
         description "Multilink Frame Relay UNI NNI polling verification timer";
         type union {
           type string {
             pattern "<.*>|$.*";
           }
           type uint16 {
             range "5 .. 30";
           }
         }
       }
     }
     leaf mac {
       description "Hardware MAC address";
       type jt:mac-unicast;
     }
     container receive-bucket {
       description "Set receive bucket parameters";
       uses dcd_rx_bucket_config;
     }
     container transmit-bucket {
       description "Set transmit bucket parameters";
       uses dcd_tx_bucket_config;
     }
     leaf shared-interface {
       description "Enable shared interface on the interface";
       type empty;
     }
     container sonet-options {
       description "SONET interface-specific options";
       uses sonet_options_type;
     }
     container logical-tunnel-options {
       description "Logical Tunnel interface-specific options";
       uses apply-advanced;
       container link-protection {
         presence "enable link-protection";
         description "Enable link protection mode";
         uses apply-advanced;
         leaf revertive {
           description "Revert back (Default mode) from active backup link to primary, if primary is UP";
           type empty;
         }
         leaf non-revertive {
           description "Do not revert back from active backup link to primary, if primary is UP";
           type empty;
         }
       }
       leaf per-unit-mac-disable {
         description "Disable the creation of per unit mac address on LT IFLs for VPLS/CCC encaps";
         type empty;
       }
     }
     container aggregated-sonet-options {
       description "Aggregated SONET interface-specific options";
       uses apply-advanced;
       leaf minimum-links {
         description "Minimum number of aggregated links";
         type union {
           type string {
             pattern "<.*>|$.*";
           }
           type uint16;
         }
       }
       leaf link-speed {
         description "Aggregated links speed";
         type enumeration {
           enum "oc3" {
             description "Links are OC-3c or STM-1c";
           }
           enum "oc12" {
             description "Links are OC-12c or STM-4c";
           }
           enum "oc48" {
             description "Links are OC-48c or STM-16c";
           }
           enum "oc192" {
             description "Links are OC-192c or STM-64c";
           }
           enum "oc768" {
             description "Links are OC-768c or STM-256c";
           }
           enum "mixed" {
             description "Links are various speeds";
           }
         }
       }
       leaf minimum-bandwidth {
         description "Minimum bandwidth necessary to sustain bundle";
         units "bps";
         type union {
           type string {
             pattern "<.*>|$.*";
           }
           type uint64 {
             range "0 .. 159232000000";
           }
         }
       }
     }
     container atm-options {
       description "ATM interface-specific options";
       uses apply-advanced;
       leaf pic-type {
         description "Type of ATM PIC (ATM I, ATM II or ATM CE)";
         type enumeration {
           enum "atm-ce" {
             description "CE PIC";
           }
           enum "atm2" {
             description "ATM II IQ PIC";
           }
           enum "atm1" {
             description "ATM I PIC";
           }
         }
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf use-null-cw {
         description "Always insert/strip null control words with cell-relay";
         type empty;
       }
       container promiscuous-mode {
         presence "enable promiscuous-mode";
         description "Set ATM interface to promiscuous mode";
         uses apply-advanced;
         list vpi {
           key name;
           ordered-by user;
           description "Open this VPI in promiscuous mode";
           leaf name {
             description "Virtual path index";
             type union {
               type string {
                 pattern "<.*>|$.*";
               }
               type uint32 {
                 range "0 .. 255";
               }
             }
           }
         }
       }
       list vpi {
         key name;
         ordered-by user;
         description "Define a virtual path";
         leaf name {
           description "Virtual path index";
           type union {
             type string {
               pattern "<.*>|$.*";
             }
             type uint32 {
               range "0 .. 255";
             }
           }
         }
         uses apply-advanced;
         leaf maximum-vcs {
           description "Maximum number of virtual circuits on this VP";
           type union {
             type uint32;
             type string {
               pattern "<.*>|$.*";
             }
           }
         }
         container shaping {
           description "Virtual path traffic-shaping options";
           uses dcd_shaping_config;
         }
         container oam-period {
           description "F4 OAM cell period";
           choice oam_period_choices {
             case case_1 {
               leaf oam-period {
                 description "F4 OAM cell period";
                 units "seconds";
                 type union {
                   type string {
                     pattern "<.*>|$.*";
                   }
                   type uint32 {
                     range "1 .. 900";
                   }
                 }
               }
             }
             case case_2 {
               container disable {
                 presence "enable disable";
                 description "Disable F4 OAM loopback";
               }
             }
           }
         }
         container oam-liveness {
           description "F4 OAM virtual path liveness parameters";
           uses apply-advanced;
           leaf up-count {
             description "Number of F4 OAM cells to consider VP up";
             type union {
               type string {
                 pattern "<.*>|$.*";
               }
               type uint32 {
                 range "1 .. 255";
               }
             }
           }
           leaf down-count {
             description "Number of F4 OAM cells to consider VP down";
             type union {
               type string {
                 pattern "<.*>|$.*";
               }
               type uint32 {
                 range "1 .. 255";
               }
             }
           }
         }
       }
       container ilmi {
         presence "enable ilmi";
         description "Enable Interim Local Management Interface";
         uses apply-advanced;
       }
       list linear-red-profiles {
         key name;
         ordered-by user;
         description "ATM2 CoS virtual circuit drop profiles";
         leaf name {
           description "Linear RED profile name";
           type string {
           }
         }
         leaf queue-depth {
           description "Maximum queue depth";
           units "cells";
           type string;
           mandatory true;
         }
         leaf high-plp-threshold {
           description "Fill level percentage when linear RED is applied for high PLP";
           type union {
             type string {
               pattern "<.*>|$.*";
             }
             type uint32 {
               range "0 .. 100";
             }
           }
           mandatory true;
         }
         leaf low-plp-threshold {
           description "Fill level percentage when linear RED is applied for low PLP";
           type union {
             type string {
               pattern "<.*>|$.*";
             }
             type uint32 {
               range "0 .. 100";
             }
           }
           mandatory true;
         }
         leaf high-plp-max-threshold {
           description "Fill level percentage with 100 percent packet drop for high PLP";
           type union {
             type string {
               pattern "<.*>|$.*";
             }
             type uint32 {
               range "0 .. 100";
             }
           }
         }
         leaf low-plp-max-threshold {
           description "Fill level percentage with 100 percent packet drop for low PLP";
           type union {
             type string {
               pattern "<.*>|$.*";
             }
             type uint32 {
               range "0 .. 100";
             }
           }
         }
       }
       list scheduler-maps {
         key name;
         ordered-by user;
         description "ATM2 CoS parameters assigned to forwarding classes";
         leaf name {
           description "ATM2 CoS scheduler map name";
           type string {
           }
         }
         uses apply-advanced;
         leaf vc-cos-mode {
           description "ATM2 virtual circuit CoS mode";
           type enumeration {
             enum "strict" {
               description "Always schedule high priority queue first";
             }
             enum "alternate" {
               description "Every other packet from high priority queue (default)";
             }
           }
         }
         list forwarding-class {
           key name;
           ordered-by user;
           description "Scheduling parameters associated with forwarding class";
           leaf name {
             description "Forwarding class name";
             type string {
             }
           }
           uses apply-advanced;
           leaf priority {
             description "Queuing priority assigned to forwarding class";
             type enumeration {
               enum "low" {
                 description "Low priority queuing";
               }
               enum "high" {
                 description "High priority queuing";
               }
             }
           }
           container transmit-weight {
             description "Transmit weight";
             choice weight-method {
               case case_1 {
                 leaf percent {
                   description "Transmit weight as percentage";
                   type union {
                     type string {
                       pattern "<.*>|$.*";
                     }
                     type uint32 {
                       range "5 .. 100";
                     }
                   }
                 }
               }
               case case_2 {
                 leaf cells {
                   description "Transmit weight by cells count";
                   type string;
                 }
               }
             }
           }
           choice drop-profile-method {
             case case_1 {
               container epd-threshold {
                 description "Early packet discard threshold for ATM2";
                 uses epd_threshold_config;
               }
             }
             case case_2 {
               leaf linear-red-profile {
                 description "Linear RED profile profile name";
                 type string;
               }
             }
           }
         }
       }
       container mpls {
         description "MPLS options";
         uses mpls_ifd_options;
       }
       choice payload-scrambler-choice {
         leaf payload-scrambler {
           description "Enable payload scrambling";
           type empty;
         }
         leaf no-payload-scrambler {
           description "Don't enable payload scrambling";
           type empty;
         }
       }
     }
     container multiservice-options {
       description "Multiservice interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
       choice dump-on-flow-control-choice {
         leaf dump-on-flow-control {
           description "Enable dumping for this interface on prolonged flow-control";
           status deprecated;
           type empty;
         }
         leaf no-dump-on-flow-control {
           description "Don't enable dumping for this interface on prolonged flow-control";
           status deprecated;
           type empty;
         }
       }
       choice reset-on-flow-control-choice {
         leaf reset-on-flow-control {
           description "Enable resetting this interface on prolonged flow-control";
           status deprecated;
           type empty;
         }
         leaf no-reset-on-flow-control {
           description "Don't enable resetting this interface on prolonged flow-control";
           status deprecated;
           type empty;
         }
       }
       container flow-control-options {
         description "Flow control configuration";
         uses apply-advanced;
         leaf dump-on-flow-control {
           description "Cause core dump during prolonged flow-control";
           type empty;
         }
         leaf reset-on-flow-control {
           description "Reset interface during prolonged flow-control";
           type empty;
         }
         leaf down-on-flow-control {
           description "Bring interface down during prolonged flow-control";
           type empty;
         }
         leaf up-on-flow-control {
           description "Keep interface up during prolonged flow-control";
           type empty;
         }
       }
     }
     container ggsn-options {
       description "GGSN interface-specific options";
       uses apply-advanced;
       choice syslog-choice {
         leaf syslog {
           description "Enable system logging on this interface";
           type empty;
         }
         leaf no-syslog {
           description "Don't enable system logging on this interface";
           type empty;
         }
       }
       choice core-dump-choice {
         leaf core-dump {
           description "Enable core dumping on this interface";
           type empty;
         }
         leaf no-core-dump {
           description "Don't enable core dumping on this interface";
           type empty;
         }
       }
     }
     container ppp-options {
       description "Point-to-Point Protocol (PPP) interface-specific options";
       uses ppp_options_type;
     }
     container lsq-failure-options {
       description "Link services queuing failure options";
       uses apply-advanced;
       list trigger-link-failure {
         key name;
         ordered-by user;
         description "Link on which to trigger failure";
         leaf name {
           description "Interface name";
           type union {
             type jt:interface-device;
             type string {
               pattern "<.*>|$.*";
             }
           }
         }
         uses apply-advanced;
       }
       choice no-termination-request-choice {
         leaf no-termination-request {
           description "Do not send PPP termination requests";
           type empty;
         }
         leaf no-no-termination-request {
           description "Don't do not send PPP termination requests";
           type empty;
         }
       }
     }
     container services-options {
       description "Services interface-specific options";
       uses apply-advanced;
       container syslog {
         description "Define system log parameters";
         uses log-object;
       }
       container jflow-log {
         description "Define Jflow-log parameters.";
         uses apply-advanced;
         leaf message-rate-limit {
           description "Maximum jflow-log NAT error events allowed per second from this interface";
           units "messages per second";
           type union {
             type string {
               pattern "<.*>|$.*";
             }
             type uint32 {
               range "1 .. 2147483647";
             }
           }
         }
       }
       container deterministic-nat-configuration-log-interval {
         presence "enable deterministic-nat-configuration-log-interval";
         description "Define Deterministic NAT parameters";
         uses apply-advanced;
         leaf interval {
           description "Interval in which deterministic NAT logs are generated";
           units "seconds";
           type union {
             type string {
               pattern "<.*>|$.*";
             }
             type uint32 {
               range "1800 .. 86400";
             }
           }
         }
       }
       leaf open-timeout {
         description "Timeout period for TCP session establishment";
         units "seconds";
         type union {
           type string {
             pattern "<.*>|$.*";
           }
           type uint32 {
             range "4 .. 300";
           }
         }
       }
       leaf close-timeout {
         description "Timeout period for TCP session tear-down";
         units "seconds";
         type union {
           type string {
             pattern "<.*>|$.*";
           }
           type uint32 {
             range "2 .. 300";
           }
         }
       }
       leaf inactivity-timeout {
         description "Inactivity timeout period for established sessions (4..86400)";
         units "seconds";
         type union {
           type uint32;
           type string {
             pattern "<.*>|$.*";
           }
         }
       }
       leaf inactivity-tcp-timeout {
         description "Inactivity timeout period for TCP established sessions";
         units "seconds";
         type union {
           type string {
             pattern "<.*>|$.*";
           }
           type uint32 {
             range "4 .. 86400";
           }
         }
       }
       leaf inactivity-asymm-tcp-timeout {
         description "Inactivity timeout period for asymmetric TCP established sessions";
         units "seconds";
         type union {
           type string {
             pattern "<.*>|$.*";
           }
           type uint32 {
             range "4 .. 86400";
           }
         }
       }
       leaf inactivity-non-tcp-timeout {
         description "Inactivity timeout period for non-TCP established sessions";
         units "seconds";
         type union {
           type string {
             pattern "<.*>|$.*";
           }
           type uint32 {
             range "4 .. 86400";
           }
         }
       }
       leaf session-timeout {
         description "Session timeout period for established sessions";
         units "seconds";
         type union {
           type string {
             pattern "<.*>|$.*";
           }
           type uint32 {
             range "4 .. 86400";
           }
         }
       }
       leaf disable-global-timeout-override {
         description "Disallow overriding  global inactivity or session timeout";
         type empty;
       }
       leaf tcp-tickles {
         description "Number of TCP keep-alive packets to be sent for bi-directional TCP flows";
         default "4";
         type union {
           type string {
             pattern "<.*>|$.*";
           }
           type uint8 {
             range "0 .. 30";
           }
         }
       }
       leaf fragment-limit {
         description "Maximum number of fragments allowed for a packet";
         default "64";
         type union {
           type string {
             pattern "<.*>|$.*";
           }
           type uint8 {
             range "1 .. 250";
           }
         }
       }
       leaf reassembly-timeout {
         description "Re-assembly timeout (seconds) for fragments of a packet";
         default "4";
         units "seconds";
         type union {
           type string {
             pattern "<.*>|$.*";
           }
           type uint8 {
             range "1 .. 60";
           }
         }
       }
       leaf cgn-pic {
         description "PIC will be used for Carrier Grade NAT configuration only";
         type empty;
       }
       leaf pba-interim-logging-interval {
         description "Interim logging interval in seconds";
         default "0";
         units "seconds";
         type union {
           type string {
             pattern "<.*>|$.*";
           }
           type uint32 {
             range "0 .. 86400";
           }
         }
       }
       container session-limit {
         presence "enable session-limit";
         description "Session limit";
         uses apply-advanced;
         leaf maximum {
           description "Maximum number of sessions allowed simultaneously";
           type string;
         }
         leaf rate {
           description "Maximum number of new sessions allowed per second";
           type string;
         }
         leaf cpu-load-threshold {
           description "CPU limit in percentage for auto-tuning of session rate";
           units "percent";
           type union {
             type string {
               pattern "<.*>|$.*";
             }
             type uint8 {
               range "1 .. 100";
             }
           }
         }
       }
       leaf enable-subscriber-analysis {
         description "Enable subscriber analysis on the interface";
         type empty;
       }
       leaf disable-subscriber-analysis {
         description "Disable subscriber analysis on the interface";
         type empty;
       }
       leaf disable-usp-tracing {
         description "Disable usp tracing on this pic";
         type empty;
       }
       leaf disable-drop-flows {
         description "Disable drop flows on this pic";
         type empty;
       }
       container ignore-errors {
         presence "enable ignore-errors";
         description "Ignore anomalies or errors";
         leaf tcp {
           description "TCP protocol errors";
           type empty;
         }
         leaf alg {
           description "ALG anomalies or errors";
           type empty;
         }
       }
       container capture {
         description "Packet capture for SFW and NAT on the Services PIC";
         uses apply-advanced;
         leaf capture-size {
           description "The number of packets to store";
           type union {
             type string {
               pattern "<.*>|$.*";
             }
             type uint32 {
               range "1 .. 344000";
             }
           }
         }
         leaf pkt-size {
           description "Number of bytes to be saved from each packet";
           type union {
             type string {
               pattern "<.*>|$.*";
             }
             type uint16 {
               range "64 .. 15000";
             }
           }
         }
         leaf logs-per-packet {
           description "The number of trace messages stored for each packet";
           type union {
             type string {
               pattern "<.*>|$.*";
             }
             type uint16 {
               range "0 .. 500";
             }
           }
         }
         leaf max-log-line-size {
           description "The maximum length of a stored trace message";
           type union {
             type uint8;
             type string {
               pattern "<.*>|$.*";
             }
           }
         }
         container filter {
           presence "enable filter";
           description "Filtering options for the packet capture";
           uses apply-advanced;
           container source-ip {
             description "Filter based on source-ip (and wildcard)";
             leaf ip {
               description "Source IP";
               type jt:ipaddr;
               mandatory true;
             }
             leaf wildcard {
               description "Source IP wildcard";
               type jt:ipaddr;
             }
           }
           container dest-ip {
             description "Filter based on dest-ip (and wildcard)";
             leaf ip {
               description "Dest IP";
               type jt:ipaddr;
               mandatory true;
             }
             leaf wildcard {
               description "Dest IP wildcard";
               type jt:ipaddr;
             }
           }
           container sw-sip {
             description "Filter based on source softwire ip (and wildcard)";
             leaf ip {
               description "Source softwire IP";
               type jt:ipv6addr;
               mandatory true;
             }
             leaf wildcard {
               description "Source IP wildcard";
               type jt:ipv6addr;
             }
           }
           container sw-dip {
             description "Filter based on destination softwire ip (and wildcard)";
             leaf ip {
               description "Destination softwire IP";
               type jt:ipaddr;
               mandatory true;
             }
             leaf wildcard {
               description "Destination IP wildcard";
               type jt:ipaddr;
             }
           }
           container sport-range {
             description "Filter based on source port";
             leaf low {
               description "Source port range start";
               type union {
                 type uint16;
                 type string {
                   pattern "<.*>|$.*";
                 }
               }
               mandatory true;
             }
             leaf high {
               description "Source port range end";
               type union {
                 type uint16;
                 type string {
                   pattern "<.*>|$.*";
                 }
               }
               mandatory true;
             }
           }
           container dport-range {
             description "Filter based on destination port";
             leaf low {
               description "Destination port range start";
               type union {
                 type uint16;
                 type string {
                   pattern "<.*>|$.*";
                 }
               }
               mandatory true;
             }
             leaf high {
               description "Destination port range end";
               type union {
                 type uint16;
                 type string {
                   pattern "<.*>|$.*";
                 }
               }
               mandatory true;
             }
           }
           leaf proto {
             description "Filter based on L4 protocol";
             type enumeration {
               enum "icmp" {
               }
               enum "tcp" {
               }
               enum "udp" {
               }
             }
           }
         }
       }
       container flow {
         description "Define flow parameters";
         uses apply-advanced;
         container traceoptions {
           description "Trace options for flow services";
         }
       }
       leaf fpc-pic-information {
         description "Include FPC and PIC slot number in the syslogs";
         type empty;
       }
       leaf utc-timestamp {
         description "Use UTC time for security log timestamps";
         type empty;
       }
       leaf syslog-local-system-timestamp {
         description "Use local system time for services syslog timestamp";
         type empty;
       }
     }
     container t3-options {
       description "T3 interface-specific options";
       uses apply-advanced;
       leaf loopback {
         description "Loopback mode";
         type enumeration {
           enum "local" {
             description "Local loopback";
           }
           enum "remote" {
             description "Remote loopback";
           }
           enum "payload" {
             description "Payload loopback";
           }
         }
       }
       choice long-buildout-choice {
         leaf long-buildout {
           description "Set hardware to drive line longer than 255 feet";
           type empty;
         }
         leaf no-long-buildout {
           description "Don't set hardware to drive line longer than 255 feet";
           type empty;
         }
       }
       choice loop-timing-choice {
         leaf loop-timing {
           description "Set loop timing for T3";
           type empty;
         }
         leaf no-loop-timing {
           description "Don't set loop timing for T3";
           type empty;
         }
       }
       container compatibility-mode {
         description "Set CSU compatibility mode";
         choice vendor {
           case case_1 {
             container larscom {
               presence "enable larscom";
               description "Compatible with Larscom CSU";
               leaf subrate {
                 description "Set subrate value";
                 type union {
                   type string {
                     pattern "<.*>|$.*";
                   }
                   type uint32 {
                     range "1 .. 14";
                   }
                 }
               }
             }
           }
           case case_2 {
             container verilink {
               presence "enable verilink";
               description "Compatible with Verilink CSU (not on 2/4-port T3 PIC)";
               leaf subrate {
                 description "Set subrate value";
                 type union {
                   type string {
                     pattern "<.*>|$.*";
                   }
                   type uint32 {
                     range "1 .. 28";
                   }
                 }
               }
             }
           }
           case case_3 {
             container adtran {
               presence "enable adtran";
               description "Compatible with Adtran CSU (not on 2/4-port T3 PIC)";
               leaf subrate {
                 description "Set subrate value";
                 type union {
                   type string {
                     pattern "<.*>|$.*";
                   }
                   type uint32 {
                     range "1 .. 588";
                   }
                 }
               }
             }
           }
           case case_4 {
             container kentrox {
               presence "enable kentrox";
               description "Compatible with Kentrox CSU";
               leaf subrate {
                 description "Set subrate value (not on 2/4-port T3 PIC)";
                 type union {
                   type string {
                     pattern "<.*>|$.*";
                   }
                   type uint32 {
                     range "1 .. 69";
                   }
                 }
               }
             }
           }
           case case_5 {
             container digital-link {
               presence "enable digital-link";
               description "Compatible with Digital Link CSU";
               leaf subrate {
                 description "Set subrate value";
                 type enumeration {
                   enum "301Kb" {
                     description "301 Kbps";
                   }
                   enum "601Kb" {
                     description "601 Kbps";
                   }
                   enum "902Kb" {
                     description "902 Kbps";
                   }
                   enum "1.2Mb" {
                     description "1.2 Mbps";
                   }
                   enum "1.5Mb" {
                     description "1.5 Mbps";
                   }
                   enum "1.8Mb" {
                     description "1.8 Mbps";
                   }
                   enum "2.1Mb" {
                     description "2.1 Mbps";
                   }
                   enum "2.4Mb" {
                     description "2.4 Mbps";
                   }
                   enum "2.7Mb" {
                     description "2.7 Mbps";
                   }
                   enum "3.0Mb" {
                     description "3.0 Mbps";
                   }
                   enum "3.3Mb" {
                     description "3.3 Mbps";
                   }
                   enum "3.6Mb" {
                     description "3.6 Mbps";
                   }
                   enum "3.9Mb" {
                     description "3.9 Mbps";
                   }
                   enum "4.2Mb" {
                     description "4.2 Mbps";
                   }
                   enum "4.5Mb" {
                     description "4.5 Mbps";
                   }
                   enum "4.8Mb" {
                     description "4.8 Mbps";
                   }
                   enum "5.1Mb" {
                     description "5.1 Mbps";
                   }
                   enum "5.4Mb" {
                     description "5.4 Mbps";
                   }
                   enum "5.7Mb" {
                     description "5.7 Mbps";
                   }
                   enum "6.0Mb" {
                     description "6.0 Mbps";
                   }
                   enum "6.3Mb" {
                     description "6.3 Mbps";
                   }
                   enum "6.6Mb" {
                     description "6.6 Mbps";
                   }
                   enum "6.9Mb" {
                     description "6.9 Mbps";
                   }
                   enum "7.2Mb" {
                     description "7.2 Mbps";
                   }
                   enum "7.5Mb" {
                     description "7.5 Mbps";
                   }
                   enum "7.8Mb" {
                     description "7.8 Mbps";
                   }
                   enum "8.1Mb" {
                     description "8.1 Mbps";
                   }
                   enum "8.4Mb" {
                     description "8.4 Mbps";
                   }
                   enum "8.7Mb" {
                     description "8.7 Mbps";
                   }
                   enum "9.0Mb" {
                     description "9.0 Mbps";
                   }
                   enum "9.3Mb" {
                     description "9.3 Mbps";
                   }
                   enum "9.6Mb" {
                     description "9.6 Mbps";
                   }
                   enum "9.9Mb" {
                     description "9.9 Mbps";
                   }
                   enum "10.2Mb" {
                     description "10.2 Mbps";
                   }
                   enum "10.5Mb" {
                     description "10.5 Mbps";
                   }
                   enum "10.8Mb" {
                     description "10.8 Mbps";
                   }
                   enum "11.1Mb" {
                     description "11.1 Mbps";
                   }
                   enum "11.4Mb" {
                     description "11.4 Mbps";
                   }
                   enum "11.7Mb" {
                     description "11.7 Mbps";
                   }
                   enum "12.0Mb" {
                     description "12.0 Mbps";
                   }
                   enum "12.3Mb" {
                     description "12.3 Mbps";
                   }
                   enum "12.6Mb" {
                     description "12.6 Mbps";
                   }
                   enum "12.9Mb" {
                     description "12.9 Mbps";
                   }
                   enum "13.2Mb" {
                     description "13.2 Mbps";
                   }
                   enum "13.5Mb" {
                     description "13.5 Mbps";
                   }
                   enum "13.8Mb" {
                     description "13.8 Mbps";
                   }
                   enum "14.1Mb" {
                     description "14.1 Mbps";
                   }
                   enum "14.4Mb" {
                     description "14.4 Mbps";
                   }
                   enum "14.7Mb" {
                     description "14.7 Mbps";
                   }
                   enum "15.0Mb" {
                     description "15.0 Mbps";
                   }
                   enum "15.3Mb" {
                     description "15.3 Mbps";
                   }
                   enum "15.6Mb" {
                     description "15.6 Mbps";
                   }
                   enum "15.9Mb" {
                     description "15.9 Mbps";
                   }
                   enum "16.2Mb" {
                     description "16.2 Mbps";
                   }
                   enum "16.5Mb" {
                     description "16.5 Mbps";
                   }
                   enum "16.8Mb" {
                     description "16.8 Mbps";
                   }
                   enum "17.1Mb" {
                     description "17.1 Mbps";
                   }
                   enum "17.4Mb" {
                     description "17.4 Mbps";
                   }
                   enum "17.7Mb" {
                     description "17.7 Mbps";
                   }
                   enum "18.0Mb" {
                     description "18.0 Mbps";
                   }
                   enum "18.3Mb" {
                     description "18.3 Mbps";
                   }
                   enum "18.6Mb" {
                     description "18.6 Mbps";
                   }
                   enum "18.9Mb" {
                     description "18.9 Mbps";
                   }
                   enum "19.2Mb" {
                     description "19.2 Mbps";
                   }
                   enum "19.5Mb" {
                     description "19.5 Mbps";
                   }
                   enum "19.8Mb" {
                     description "19.8 Mbps";
                   }
                   enum "20.1Mb" {
                     description "20.1 Mbps";
                   }
                   enum "20.5Mb" {
                     description "20.5 Mbps";
                   }
                   enum "20.8Mb" {
                     description "20.8 Mbps";
                   }
                   enum "21.1Mb" {
                     description "21.1 Mbps";
                   }
                   enum "21.4Mb" {
                     description "21.4 Mbps";
                   }
                   enum "21.7Mb" {
                     description "21.7 Mbps";
                   }
                   enum "22.0Mb" {
                     description "22.0 Mbps";
                   }
                   enum "22.3Mb" {
                     description "22.3 Mbps";
                   }
                   enum "22.6Mb" {
                     description "22.6 Mbps";
                   }
                   enum "22.9Mb" {
                     description "22.9 Mbps";
                   }
                   enum "23.2Mb" {
                     description "23.2 Mbps";
                   }
                   enum "23.5Mb" {
                     description "23.5 Mbps";
                   }
                   enum "23.8Mb" {
                     description "23.8 Mbps";
                   }
                   enum "24.1Mb" {
                     description "24.1 Mbps";
                   }
                   enum "24.4Mb" {
                     description "24.4 Mbps";
                   }
                   enum "24.7Mb" {
                     description "24.7 Mbps";
                   }
                   enum "25.0Mb" {
                     description "25.0 Mbps";
                   }
                   enum "25.3Mb" {
                     description "25.3 Mbps";
                   }
                   enum "25.6Mb" {
                     description "25.6 Mbps";
                   }
                   enum "25.9Mb" {
                     description "25.9 Mbps";
                   }
                   enum "26.2Mb" {
                     description "26.2 Mbps";
                   }
                   enum "26.5Mb" {
                     description "26.5 Mbps";
                   }
                   enum "26.8Mb" {
                     description "26.8 Mbps";
                   }
                   enum "27.1Mb" {
                     description "27.1 Mbps";
                   }
                   enum "27.4Mb" {
                     description "27.4 Mbps";
                   }
                   enum "27.7Mb" {
                     description "27.7 Mbps";
                   }
                   enum "28.0Mb" {
                     description "28.0 Mbps";
                   }
                   enum "28.3Mb" {
                     description "28.3 Mbps";
                   }
                   enum "28.6Mb" {
                     description "28.6 Mbps";
                   }
                   enum "28.9Mb" {
                     description "28.9 Mbps";
                   }
                   enum "29.2Mb" {
                     description "29.2 Mbps";
                   }
                   enum "29.5Mb" {
                     description "29.5 Mbps";
                   }
                   enum "29.8Mb" {
                     description "29.8 Mbps";
                   }
                   enum "30.1Mb" {
                     description "30.1 Mbps";
                   }
                   enum "30.4Mb" {
                     description "30.4 Mbps";
                   }
                   enum "30.7Mb" {
                     description "30.7 Mbps";
                   }
                   enum "31.0Mb" {
                     description "31.0 Mbps";
                   }
                   enum "31.3Mb" {
                     description "31.3 Mbps";
                   }
                   enum "31.6Mb" {
                     description "31.6 Mbps";
                   }
                   enum "31.9Mb" {
                     description "31.9 Mbps";
                   }
                   enum "32.2Mb" {
                     description "32.2 Mbps";
                   }
                   enum "32.5Mb" {
                     description "32.5 Mbps";
                   }
                   enum "32.8Mb" {
                     description "32.8 Mbps";
                   }
                   enum "33.1Mb" {
                     description "33.1 Mbps";
                   }
                   enum "33.4Mb" {
                     description "33.4 Mbps";
                   }
                   enum "33.7Mb" {
                     description "33.7 Mbps";
                   }
                   enum "34.0Mb" {
                     description "34.0 Mbps";
                   }
                   enum "34.3Mb" {
                     description "34.3 Mbps";
                   }
                   enum "34.6Mb" {
                     description "34.6 Mbps";
                   }
                   enum "34.9Mb" {
                     description "34.9 Mbps";
                   }
                   enum "35.2Mb" {
                     description "35.2 Mbps";
                   }
                   enum "35.5Mb" {
                     description "35.5 Mbps";
                   }
                   enum "35.8Mb" {
                     description "35.8 Mbps";
                   }
                   enum "36.1Mb" {
                     description "36.1 Mbps";
                   }
                   enum "36.4Mb" {
                     description "36.4 Mbps";
                   }
                   enum "36.7Mb" {
                     description "36.7 Mbps";
                   }
                   enum "37.0Mb" {
                     description "37.0 Mbps";
                   }
                   enum "37.3Mb" {
                     description "37.3 Mbps";
                   }
                   enum "37.6Mb" {
                     description "37.6 Mbps";
                   }
                   enum "37.9Mb" {
                     description "37.9 Mbps";
                   }
                   enum "38.2Mb" {
                     description "38.2 Mbps";
                   }
                   enum "38.5Mb" {
                     description "38.5 Mbps";
                   }
                   enum "38.8Mb" {
                     description "38.8 Mbps";
                   }
                   enum "39.1Mb" {
                     description "39.1 Mbps";
                   }
                   enum "39.4Mb" {
                     description "39.4 Mbps";
                   }
                   enum "39.7Mb" {
                     description "39.7 Mbps";
                   }
                   enum "40.0Mb" {
                     description "40.0 Mbps";
                   }
                   enum "40.3Mb" {
                     description "40.3 Mbps";
                   }
                   enum "40.6Mb" {
                     description "40.6 Mbps";
                   }
                   enum "40.9Mb" {
                     description "40.9 Mbps";
                   }
                   enum "41.2Mb" {
                     description "41.2 Mbps";
                   }
                   enum "41.5Mb" {
                     description "41.5 Mbps";
                   }
                   enum "41.8Mb" {
                     description "41.8 Mbps";
                   }
                   enum "42.1Mb" {
                     description "42.1 Mbps";
                   }
                   enum "42.4Mb" {
                     description "42.4 Mbps";
                   }
                   enum "42.7Mb" {
                     description "42.7 Mbps";
                   }
                   enum "43.0Mb" {
                     description "43.0 Mbps";
                   }
                   enum "43.3Mb" {
                     description "43.3 Mbps";
                   }
                   enum "43.6Mb" {
                     description "43.6 Mbps";
                   }
                   enum "43.9Mb" {
                     description "43.9 Mbps";
                   }
                   enum "44.2Mb" {
                     description "44.2 Mbps";
                   }
                 }
               }
             }
           }
         }
       }
       choice payload-scrambler-choice {
         leaf payload-scrambler {
           description "Enable payload scrambling";
           type empty;
         }
         leaf no-payload-scrambler {
           description "Don't enable payload scrambling";
           type empty;
         }
       }
       choice cbit-parity-choice {
         leaf cbit-parity {
           description "Enable C-bit parity mode";
           type empty;
         }
         leaf no-cbit-parity {
           description "Don't enable C-bit parity mode";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       choice feac-loop-respond-choice {
         leaf feac-loop-respond {
           description "Respond to FEAC loop requests";
           type empty;
         }
         leaf no-feac-loop-respond {
           description "Don't respond to FEAC loop requests";
           type empty;
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "DS-3 interface encapsulation";
         type enumeration {
           enum "plcp" {
             description "PLCP encapsulation";
           }
           enum "direct" {
             description "ATM direct mapping";
           }
         }
       }
     }
     container e3-options {
       description "E3 interface-specific options";
       uses apply-advanced;
       leaf loopback {
         description "Loopback mode";
         type enumeration {
           enum "local" {
             description "Local loopback";
           }
           enum "remote" {
             description "Remote loopback";
           }
         }
       }
       choice unframed-choice {
         leaf unframed {
           description "Enable unframed mode";
           type empty;
         }
         leaf no-unframed {
           description "Don't enable unframed mode";
           type empty;
         }
       }
       container compatibility-mode {
         description "Set CSU compatibility mode";
         choice vendor {
           case case_1 {
             leaf larscom {
               description "Compatible with Larscom CSU (only non IQ E3 interfaces)";
               type empty;
             }
           }
           case case_2 {
             container digital-link {
               presence "enable digital-link";
               description "Compatible with Digital Link CSU";
               leaf subrate {
                 description "Set subrate value";
                 type enumeration {
                   enum "358Kb" {
                     description "358 Kbps";
                   }
                   enum "716Kb" {
                     description "716 Kbps";
                   }
                   enum "1.1Mb" {
                     description "1.1 Mbps";
                   }
                   enum "1.4Mb" {
                     description "1.4 Mbps";
                   }
                   enum "1.8Mb" {
                     description "1.8 Mbps";
                   }
                   enum "2.1Mb" {
                     description "2.1 Mbps";
                   }
                   enum "2.5Mb" {
                     description "2.5 Mbps";
                   }
                   enum "2.9Mb" {
                     description "2.9 Mbps";
                   }
                   enum "3.2Mb" {
                     description "3.2 Mbps";
                   }
                   enum "3.6Mb" {
                     description "3.6 Mbps";
                   }
                   enum "3.9Mb" {
                     description "3.9 Mbps";
                   }
                   enum "4.3Mb" {
                     description "4.3 Mbps";
                   }
                   enum "4.7Mb" {
                     description "4.7 Mbps";
                   }
                   enum "5.0Mb" {
                     description "5.0 Mbps";
                   }
                   enum "5.4Mb" {
                     description "5.4 Mbps";
                   }
                   enum "5.7Mb" {
                     description "5.7 Mbps";
                   }
                   enum "6.1Mb" {
                     description "6.1 Mbps";
                   }
                   enum "6.4Mb" {
                     description "6.4 Mbps";
                   }
                   enum "6.8Mb" {
                     description "6.8 Mbps";
                   }
                   enum "7.2Mb" {
                     description "7.2 Mbps";
                   }
                   enum "7.5Mb" {
                     description "7.5 Mbps";
                   }
                   enum "7.9Mb" {
                     description "7.9 Mbps";
                   }
                   enum "8.2Mb" {
                     description "8.2 Mbps";
                   }
                   enum "8.6Mb" {
                     description "8.6 Mbps";
                   }
                   enum "9.0Mb" {
                     description "9.0 Mbps";
                   }
                   enum "9.3Mb" {
                     description "9.3 Mbps";
                   }
                   enum "9.7Mb" {
                     description "9.7 Mbps";
                   }
                   enum "10.0Mb" {
                     description "10.0 Mbps";
                   }
                   enum "10.4Mb" {
                     description "10.4 Mbps";
                   }
                   enum "10.7Mb" {
                     description "10.7 Mbps";
                   }
                   enum "11.1Mb" {
                     description "11.1 Mbps";
                   }
                   enum "11.5Mb" {
                     description "11.5 Mbps";
                   }
                   enum "11.8Mb" {
                     description "11.8 Mbps";
                   }
                   enum "12.2Mb" {
                     description "12.2 Mbps";
                   }
                   enum "12.5Mb" {
                     description "12.5 Mbps";
                   }
                   enum "12.9Mb" {
                     description "12.9 Mbps";
                   }
                   enum "13.2Mb" {
                     description "13.2 Mbps";
                   }
                   enum "13.6Mb" {
                     description "13.6 Mbps";
                   }
                   enum "14.0Mb" {
                     description "14.0 Mbps";
                   }
                   enum "14.3Mb" {
                     description "14.3 Mbps";
                   }
                   enum "14.7Mb" {
                     description "14.7 Mbps";
                   }
                   enum "15.0Mb" {
                     description "15.0 Mbps";
                   }
                   enum "15.4Mb" {
                     description "15.4 Mbps";
                   }
                   enum "15.8Mb" {
                     description "15.8 Mbps";
                   }
                   enum "16.1Mb" {
                     description "16.1 Mbps";
                   }
                   enum "16.5Mb" {
                     description "16.5 Mbps";
                   }
                   enum "16.8Mb" {
                     description "16.8 Mbps";
                   }
                   enum "17.2Mb" {
                     description "17.2 Mbps";
                   }
                   enum "17.5Mb" {
                     description "17.5 Mbps";
                   }
                   enum "17.9Mb" {
                     description "17.9 Mbps";
                   }
                   enum "18.3Mb" {
                     description "18.3 Mbps";
                   }
                   enum "18.6Mb" {
                     description "18.6 Mbps";
                   }
                   enum "19.0Mb" {
                     description "19.0 Mbps";
                   }
                   enum "19.3Mb" {
                     description "19.3 Mbps";
                   }
                   enum "19.7Mb" {
                     description "19.7 Mbps";
                   }
                   enum "20.0Mb" {
                     description "20.0 Mbps";
                   }
                   enum "20.4Mb" {
                     description "20.4 Mbps";
                   }
                   enum "20.8Mb" {
                     description "20.8 Mbps";
                   }
                   enum "21.1Mb" {
                     description "21.1 Mbps";
                   }
                   enum "21.5Mb" {
                     description "21.5 Mbps";
                   }
                   enum "21.8Mb" {
                     description "21.8 Mbps";
                   }
                   enum "22.2Mb" {
                     description "22.2 Mbps";
                   }
                   enum "22.6Mb" {
                     description "22.6 Mbps";
                   }
                   enum "22.9Mb" {
                     description "22.9 Mbps";
                   }
                   enum "23.3Mb" {
                     description "23.3 Mbps";
                   }
                   enum "23.6Mb" {
                     description "23.6 Mbps";
                   }
                   enum "24.0Mb" {
                     description "24.0 Mbps";
                   }
                   enum "24.3Mb" {
                     description "24.3 Mbps";
                   }
                   enum "24.7Mb" {
                     description "24.7 Mbps";
                   }
                   enum "25.1Mb" {
                     description "25.1 Mbps";
                   }
                   enum "25.4Mb" {
                     description "25.4 Mbps";
                   }
                   enum "25.8Mb" {
                     description "25.8 Mbps";
                   }
                   enum "26.1Mb" {
                     description "26.1 Mbps";
                   }
                   enum "26.5Mb" {
                     description "26.5 Mbps";
                   }
                   enum "26.9Mb" {
                     description "26.9 Mbps";
                   }
                   enum "27.2Mb" {
                     description "27.2 Mbps";
                   }
                   enum "27.6Mb" {
                     description "27.6 Mbps";
                   }
                   enum "27.9Mb" {
                     description "27.9 Mbps";
                   }
                   enum "28.3Mb" {
                     description "28.3 Mbps";
                   }
                   enum "28.6Mb" {
                     description "28.6 Mbps";
                   }
                   enum "29.0Mb" {
                     description "29.0 Mbps";
                   }
                   enum "29.4Mb" {
                     description "29.4 Mbps";
                   }
                   enum "29.7Mb" {
                     description "29.7 Mbps";
                   }
                   enum "30.1Mb" {
                     description "30.1 Mbps";
                   }
                   enum "30.4Mb" {
                     description "30.4 Mbps";
                   }
                   enum "30.8Mb" {
                     description "30.8 Mbps";
                   }
                   enum "31.1Mb" {
                     description "31.1 Mbps";
                   }
                   enum "31.5Mb" {
                     description "31.5 Mbps";
                   }
                   enum "31.9Mb" {
                     description "31.9 Mbps";
                   }
                   enum "32.2Mb" {
                     description "32.2 Mbps";
                   }
                   enum "32.6Mb" {
                     description "32.6 Mbps";
                   }
                   enum "32.9Mb" {
                     description "32.9 Mbps";
                   }
                   enum "33.3Mb" {
                     description "33.3 Mbps";
                   }
                   enum "33.7Mb" {
                     description "33.7 Mbps";
                   }
                   enum "34.0Mb" {
                     description "34.0 Mbps";
                   }
                 }
               }
             }
           }
           case case_3 {
             container kentrox {
               presence "enable kentrox";
               description "Compatible with Kentrox CSU";
               leaf subrate {
                 description "Set subrate value (only for E3 IQ interfaces)";
                 type union {
                   type string {
                     pattern "<.*>|$.*";
                   }
                   type uint32 {
                     range "1 .. 48";
                   }
                 }
               }
             }
           }
         }
       }
       choice payload-scrambler-choice {
         leaf payload-scrambler {
           description "Enable payload scrambling";
           type empty;
         }
         leaf no-payload-scrambler {
           description "Don't enable payload scrambling";
           type empty;
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf invert-data {
         description "Invert data";
         type empty;
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
       leaf buildout {
         description "Line buildout";
         units "feet";
         type union {
           type string {
             pattern "<.*>|$.*";
           }
           type uint32 {
             range "0 .. 450";
           }
         }
       }
       leaf atm-encapsulation {
         description "E3 interface encapsulation";
         type enumeration {
           enum "plcp" {
             description "PLCP encapsulation";
           }
           enum "direct" {
             description "ATM direct mapping";
           }
         }
       }
       leaf framing {
         description "E3 line format";
         type enumeration {
           enum "g.751" {
             description "G.751 format";
           }
           enum "g.832" {
             description "G.832 format";
           }
         }
       }
     }
     container e1-options {
       description "E1 interface-specific options";
       uses apply-advanced;
       leaf timeslots {
         description "Timeslots (1..32); for example, 1-4,6,9-11,32 (no space)";
         type string;
       }
       leaf loopback {
         description "Loopback mode";
         type enumeration {
           enum "local" {
             description "Local loopback";
           }
           enum "remote" {
             description "Remote loopback";
           }
         }
       }
       leaf framing {
         description "Framing mode";
         type enumeration {
           enum "g704" {
             description "G704 mode with CRC4";
           }
           enum "unframed" {
             description "Unframed mode";
           }
           enum "g704-no-crc4" {
             description "G704 mode without CRC4";
           }
         }
       }
       leaf fcs {
         description "Frame checksum";
         type enumeration {
           enum "32" {
             description "32-bit mode";
           }
           enum "16" {
             description "16-bit mode";
           }
         }
       }
       leaf invert-data {
         description "Invert data";
         type empty;
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
     }
     container t1-options {
       description "T1 interface-specific options";
       uses apply-advanced;
       leaf timeslots {
         description "Timeslots (1..24; for example, 1-3,4,9,22-24 (no space)";
         type string;
       }
       leaf loopback {
         description "Loopback mode";
         type enumeration {
           enum "local" {
             description "Local loopback";
           }
           enum "remote" {
             description "Remote loopback";
           }
           enum "payload" {
             description "Payload loopback";
           }
         }
       }
       leaf buildout {
         description "Line buildout";
         type enumeration {
           enum "0-132" {
             description "Line buildout is between 0-132 feet";
           }
           enum "133-265" {
             description "Line buildout is between 133-265 feet";
           }
           enum "266-398" {
             description "Line buildout is between 266-398 feet";
           }
           enum "399-531" {
             description "Line buildout is between 399-531 feet";
           }
           enum "532-655" {
             description "Line buildout is between 532-655 feet";
           }
           enum "long-0db" {
             description "Long buildout with 0 dB transmit attenuation";
           }
           enum "long-7.5db" {
             description "Long buildout with 7.5 dB transmit attenuation";
           }
           enum "long-15db" {
             description "Long buildout with 15 dB transmit attenuation";
           }
           enum "long-22.5db" {
             description "Long buildout with 22.5 dB transmit attenuation";
           }
         }
       }
       leaf byte-encoding {
         description "Byte encoding";
         type enumeration {
           enum "nx64" {
             description "8 bits per byte";
           }
           enum "nx56" {
             description "7 bits per byte";
           }
         }
       }
       leaf line-encoding {
         description "Line encoding";
         type enumeration {
           enum "ami" {
             description "Automatic mark inversion";
           }
           enum "b8zs" {
             description "8-bit zero suppression";
           }
         }
       }
       leaf invert-data {
         description "Invert data";
         type empty;
       }
       leaf framing {
         description "Framing mode";
         type enumeration {
           enum "sf" {
             description "Super frame";
           }
           enum "esf" {
             description "Extended super frame";
           }
         }
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e3" {
             description "Pattern is 2^3 - 1";
           }
           enum "pseudo-2e4" {
             description "Pattern is 2^4 - 1";
           }
           enum "pseudo-2e5" {
             description "Pattern is 2^5 - 1";
           }
           enum "pseudo-2e6" {
             description "Pattern is 2^6 - 1";
           }
           enum "pseudo-2e7" {
             description "Pattern is 2^7 - 1";
           }
           enum "pseudo-2e9-o153" {
             description "Pattern is 2^9 - 1 (per O.153 standard)";
           }
           enum "pseudo-2e10" {
             description "Pattern is 2^10 - 1";
           }
           enum "pseudo-2e11-o152" {
             description "Pattern is 2^11 -1 (per O.152 standard)";
           }
           enum "pseudo-2e15-o151" {
             description "Pattern is 2^15 - 1 (per O.151 standard)";
           }
           enum "pseudo-2e17" {
             description "Pattern is 2^17 - 1";
           }
           enum "pseudo-2e18" {
             description "Pattern is 2^18 - 1";
           }
           enum "pseudo-2e20-o153" {
             description "Pattern is 2^20 - 1 (per O.153 standard)";
           }
           enum "pseudo-2e20-o151" {
             description "Pattern is 2^20 - 1 (per O.151 standard)";
           }
           enum "pseudo-2e21" {
             description "Pattern is 2^21 - 1";
           }
           enum "pseudo-2e22" {
             description "Pattern is 2^22 - 1";
           }
           enum "pseudo-2e23-o151" {
             description "Pattern is 2^23 (per O.151 standard)";
           }
           enum "pseudo-2e25" {
             description "Pattern is 2^25 - 1";
           }
           enum "pseudo-2e28" {
             description "Pattern is 2^28 - 1";
           }
           enum "pseudo-2e29" {
             description "Pattern is 2^29 - 1";
           }
           enum "pseudo-2e31" {
             description "Pattern is 2^31 - 1";
           }
           enum "pseudo-2e32" {
             description "Pattern is 2^32 - 1";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 86400";
           }
         }
       }
       leaf remote-loopback-respond {
         description "Respond to loop requests from remote end";
         type empty;
       }
       leaf crc-major-alarm-threshold {
         description "CRC Major alarm threshold value";
         default "5e-5";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
         }
       }
       leaf crc-minor-alarm-threshold {
         description "CRC Minor alarm threshold value";
         default "5e-6";
         type enumeration {
           enum "1e-3" {
             description "1 crc error in 10^3 bits";
           }
           enum "5e-4" {
             description "5 crc errors in 10^4 bits";
           }
           enum "1e-4" {
             description "1 crc error in 10^4 bits";
           }
           enum "5e-5" {
             description "5 crc errors in 10^5 bits";
           }
           enum "1e-5" {
             description "1 crc error in 10^5 bits";
           }
           enum "5e-6" {
             description "5 crc errors in 10^6 bits";
           }
           enum "1e-6" {
             description "1 crc error in 10^6 bits";
           }
         }
       }
     }
     container ds0-options {
       description "DS-0 interface-specific options";
       uses apply-advanced;
       leaf loopback {
         description "Loopback mode";
         type enumeration {
           enum "payload" {
             description "Payload loopback";
           }
         }
       }
       leaf byte-encoding {
         description "Byte encoding";
         type enumeration {
           enum "nx64" {
             description "8 bits per byte";
           }
           enum "nx56" {
             description "7 bits per byte";
           }
         }
       }
       leaf invert-data {
         description "Invert data";
         type empty;
       }
       leaf fcs {
         description "Frame checksum";
         type enumeration {
           enum "32" {
             description "32-bit mode";
           }
           enum "16" {
             description "16-bit mode";
           }
         }
       }
       leaf idle-cycle-flag {
         description "Value to transmit in idle cycles";
         type enumeration {
           enum "flags" {
             description "Transmit 0x7E in idle cycles";
           }
           enum "ones" {
             description "Transmit 0xFF (all ones) in idle cycles";
           }
         }
       }
       leaf start-end-flag {
         description "Set start/end flags on transmission";
         type enumeration {
           enum "shared" {
             description "Share start/end flags on transmit";
           }
           enum "filler" {
             description "Send two idle cycles between start/end flags";
           }
         }
       }
       leaf bert-algorithm {
         description "Set BERT algorithm";
         type enumeration {
           enum "pseudo-2e11-o152" {
             description "Pattern is 2^11 -1 (per O.152 standard)";
           }
           enum "pseudo-2e15-o151" {
             description "Pattern is 2^15 - 1 (per O.151 standard)";
           }
           enum "pseudo-2e20-o153" {
             description "Pattern is 2^20 - 1 (per O.153 standard)";
           }
           enum "pseudo-2e20-o151" {
             description "Pattern is 2^20 - 1 (per O.151 standard)";
           }
           enum "all-ones-repeating" {
             description "Repeating one bits";
           }
           enum "all-zeros-repeating" {
             description "Repeating zero bits";
           }
           enum "alternating-ones-zeros" {
             description "Alternating ones and zeros";
           }
           enum "alternating-double-ones-zeros" {
             description "Alternating pairs of ones and zeros";
           }
           enum "repeating-3-in-24" {
             description "3 bits in 24 are set";
           }
           enum "repeating-1-in-8" {
             description "1 bit in 8 is set";
           }
           enum "repeating-1-in-4" {
             description "1 bit in 4 is set";
           }
           enum "repeating-1-in-16" {
             description "1 bit in 16 is set";
           }
         }
       }
       leaf bert-error-rate {
         description "Bit error rate (10^-n for n > 0, and zero for n = 0)";
         type union {
           type string {
             pattern "<.*>|$.*";
           }
           type uint32 {
             range "0 .. 7";
           }
         }
       }
       leaf bert-period {
         description "Length of BERT test";
         units "seconds";
         type union {
           type string {
             pattern "<.*>|$.*";
           }
           type uint32 {
             range "1 .. 240";
           }
         }
       }
     }
     container serial-options {
       description "Serial interface-specific options";
       uses apply-advanced;
       leaf line-protocol {
         description "Line protocol to be used";
         default "eia530";
         type enumeration {
           enum "eia530" {
             description "Line protocol EIA530";
           }
           enum "v.35" {
             description "Line protocol V.35";
           }
           enum "x.21" {
             description "Line protocol X.21";
           }
         }
       }
       choice control_leads_choice {
         case case_1 {
           container dte-options {
             description "DTE options/control leads";
             uses apply-advanced;
             leaf ignore-all {
               description "Ignore all control leads";
               type empty;
             }
             container dtr {
               description "Data Transmit Ready signal handling";
               choice dtr_choices {
                 case case_1 {
                   leaf assert {
                     description "Assert DTR signal";
                     type empty;
                   }
                 }
                 case case_2 {
                   leaf de-assert {
                     description "Deassert DTR signal";
                     type empty;
                   }
                 }
                 case case_3 {
                   leaf normal {
                     description "Normal DTR signal";
                     type empty;
                   }
                 }
                 case case_4 {
                   container auto-synchronize {
                     presence "enable auto-synchronize";
                     description "Normal DTR signal, with autoresynchronization";
                     uses apply-advanced;
                     leaf duration {
                       description "Duration of autoresynchronization";
                       units "milliseconds";
                       type union {
                         type string {
                           pattern "<.*>|$.*";
                         }
                         type uint16 {
                           range "1 .. 1000";
                         }
                       }
                     }
                     leaf interval {
                       description "Interval for autoresynchronization";
                       units "seconds";
                       type union {
                         type string {
                           pattern "<.*>|$.*";
                         }
                         type uint16 {
                           range "1 .. 31";
                         }
                       }
                     }
                   }
                 }
               }
             }
             leaf control-signal {
               description "X.21 control signal handling";
               type enumeration {
                 enum "assert" {
                   description "Assert control signal";
                 }
                 enum "de-assert" {
                   description "Deassert control signal";
                 }
                 enum "normal" {
                   description "Normal control signal";
                 }
               }
             }
             leaf rts {
               description "Request To Send signal handling";
               type enumeration {
                 enum "assert" {
                   description "Assert RTS signal";
                 }
                 enum "de-assert" {
                   description "Deassert RTS signal";
                 }
                 enum "normal" {
                   description "Normal RTS signal";
                 }
               }
             }
             leaf dcd {
               description "Data Carrier Detect signal handling";
               type enumeration {
                 enum "require" {
                   description "Require DCD signal";
                 }
                 enum "ignore" {
                   description "Ignore DCD signal";
                 }
                 enum "normal" {
                   description "Normal DCD signal";
                 }
               }
             }
             leaf dsr {
               description "Data Set Ready signal handling";
               type enumeration {
                 enum "require" {
                   description "Require DSR signal";
                 }
                 enum "ignore" {
                   description "Ignore DSR signal";
                 }
                 enum "normal" {
                   description "Normal DSR signal";
                 }
               }
             }
             leaf cts {
               description "Clear To Send signal handling";
               type enumeration {
                 enum "require" {
                   description "Require CTS signal";
                 }
                 enum "ignore" {
                   description "Ignore CTS signal";
                 }
                 enum "normal" {
                   description "Normal CTS signal";
                 }
               }
             }
             leaf indication {
               description "X.21 Indication signal handling";
               type enumeration {
                 enum "require" {
                   description "Require Indication signal";
                 }
                 enum "ignore" {
                   description "Ignore Indication signal";
                 }
                 enum "normal" {
                   description "Normal Indication signal";
                 }
               }
             }
             leaf tm {
               description "Test Mode signal handling";
               type enumeration {
                 enum "require" {
                   description "Require TM signal";
                 }
                 enum "ignore" {
                   description "Ignore TM signal";
                 }
                 enum "normal" {
                   description "Normal TM signal";
                 }
               }
             }
           }
         }
         case case_2 {
         }
       }
       leaf dtr-circuit {
         description "Data Transmit Ready circuit mode";
         type enumeration {
           enum "balanced" {
             description "Balanced signal";
           }
           enum "unbalanced" {
             description "Unbalanced signal";
           }
         }
       }
       leaf dtr-polarity {
         description "Data Transmit Ready signal polarity";
         type enumeration {
           enum "positive" {
             description "Positive polarity";
           }
           enum "negative" {
             description "Negative polarity";
           }
         }
       }
       leaf rts-polarity {
         description "Request To Send signal polarity";
         type enumeration {
           enum "positive" {
             description "Positive polarity";
           }
           enum "negative" {
             description "Negative polarity";
           }
         }
       }
       leaf control-polarity {
         description "X.21 Control signal polarity";
         type enumeration {
           enum "positive" {
             description "Positive polarity";
           }
           enum "negative" {
             description "Negative polarity";
           }
         }
       }
       leaf dcd-polarity {
         description "Data Carrier Detect signal polarity";
         type enumeration {
           enum "positive" {
             description "Positive polarity";
           }
           enum "negative" {
             description "Negative polarity";
           }
         }
       }
       leaf dsr-polarity {
         description "Data Set Ready signal polarity";
         type enumeration {
           enum "positive" {
             description "Positive polarity";
           }
           enum "negative" {
             description "Negative polarity";
           }
         }
       }
       leaf cts-polarity {
         description "Clear To Send signal polarity";
         type enumeration {
           enum "positive" {
             description "Positive polarity";
           }
           enum "negative" {
             description "Negative polarity";
           }
         }
       }
       leaf indication-polarity {
         description "X.21 Indication signal polarity";
         type enumeration {
           enum "positive" {
             description "Positive polarity";
           }
           enum "negative" {
             description "Negative polarity";
           }
         }
       }
       leaf tm-polarity {
         description "Test Mode signal polarity";
         type enumeration {
           enum "positive" {
             description "Positive polarity";
           }
           enum "negative" {
             description "Negative polarity";
           }
         }
       }
       leaf clocking-mode {
         description "Clock mode";
         type enumeration {
           enum "dce" {
             description "DCE timing (DTE mode only, not valid for X.21)";
           }
           enum "internal" {
             description "Internal baud timing";
           }
           enum "loop" {
             description "Loop timing";
           }
         }
       }
       leaf transmit-clock {
         description "Transmit clock phase";
         type enumeration {
           enum "invert" {
             description "Shift clock phase 180 degrees";
           }
         }
       }
       leaf clock-rate {
         description "Interface clock rate";
         type enumeration {
           enum "2.048mhz" {
             description "2.048 MHz";
           }
           enum "2.341mhz" {
             description "2.341 MHz";
           }
           enum "2.731mhz" {
             description "2.731 MHz";
           }
           enum "3.277mhz" {
             description "3.277 MHz";
           }
           enum "4.096mhz" {
             description "4.096 MHz";
           }
           enum "5.461mhz" {
             description "5.461 MHz";
           }
           enum "8.192mhz" {
             description "8.192 MHz";
           }
           enum "16.384mhz" {
             description "16.384 MHz";
           }
           enum "1.2khz" {
             description "1.2 KHz";
           }
           enum "2.4khz" {
             description "2.4 KHz";
           }
           enum "9.6khz" {
             description "9.6 KHz";
           }
           enum "19.2khz" {
             description "19.2 KHz";
           }
           enum "38.4khz" {
             description "38.4 KHz";
           }
           enum "56.0khz" {
             description "56.0 KHz";
           }
           enum "64.0khz" {
             description "64.0 KHz";
           }
           enum "72.0khz" {
             description "72.0 KHz";
           }
           enum "125.0khz" {
             description "125.0 KHz";
           }
           enum "148.0khz" {
             description "148.0 KHz";
           }
           enum "250.0khz" {
             description "250.0 KHz";
           }
           enum "500.0khz" {
             description "500.0 KHz";
           }
           enum "800.0khz" {
             description "800.0 KHz";
           }
           enum "1.0mhz" {
             description "1.0 MHz";
           }
           enum "1.3mhz" {
             description "1.3 MHz";
           }
           enum "2.0mhz" {
             description "2.0 MHz";
           }
           enum "4.0mhz" {
             description "4.0 MHz";
           }
           enum "8.0mhz" {
             description "8.0 MHz";
           }
         }
       }
       leaf loopback {
         description "Loopback mode";
         type enumeration {
           enum "local" {
             description "Local loopback";
           }
           enum "remote" {
             description "Remote/LIU loopback";
           }
           enum "dce-local" {
             description "DCE local loopback (DTE mode only)";
           }
           enum "dce-remote" {
             description "DCE remote loopback";
           }
         }
       }
       leaf encoding {
         description "Line encoding";
         type enumeration {
           enum "nrz" {
             description "Non-Return-To-Zero";
           }
           enum "nrzi" {
             description "Non-Return-To-Zero-Invertible";
           }
         }
       }
     }
     choice gratuitous-arp-reply-choice {
       leaf gratuitous-arp-reply {
         description "Enable gratuitous ARP reply";
         type empty;
       }
       leaf no-gratuitous-arp-reply {
         description "Don't enable gratuitous ARP reply";
         type empty;
       }
     }
     choice no-gratuitous-arp-request-choice {
       leaf no-gratuitous-arp-request {
         description "Ignore gratuitous ARP request";
         type empty;
       }
       leaf no-no-gratuitous-arp-request {
         description "Don't ignore gratuitous ARP request";
         type empty;
       }
     }
     container ether-options {
       description "Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         type empty;
       }
       choice source-filtering-choice {
         leaf source-filtering {
           description "Enable source address filtering";
           type empty;
         }
         leaf no-source-filtering {
           description "Don't enable source address filtering";
           type empty;
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container storm-control {
           description "Storm control profile name to bind";
           uses apply-advanced;
           leaf profile-name {
             description "Profile name";
             type string;
             mandatory true;
           }
         }
         container recovery-timeout {
           description "Recovery timeout for this interface";
           leaf time-in-seconds {
             units "seconds";
             type union {
               type string {
                 pattern "<.*>|$.*";
               }
               type uint32 {
                 range "10 .. 3600";
               }
             }
           }
         }
         choice mac-learn-enable-choice {
           leaf mac-learn-enable {
             description "Learn MAC addresses dynamically";
             type empty;
           }
           leaf no-mac-learn-enable {
             description "Don't learn MAC addresses dynamically";
             type empty;
           }
         }
       }
       leaf asynchronous-notification {
         description "Enable sending asynchronous notification to peer on CCC-down";
         type empty;
       }
       list source-address-filter {
         key name;
         description "Source address filters";
         leaf name {
           description "Remote MAC address";
           type jt:mac-addr;
         }
       }
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       leaf link-mode {
         description "Link duplex";
         type enumeration {
           enum "automatic" {
             description "Automatic negotiate duplex ";
           }
           enum "half-duplex" {
             description "Half-duplex operation";
           }
           enum "full-duplex" {
             description "Full-duplex operation";
           }
         }
       }
       container mpls {
         description "MPLS options";
         uses mpls_ifd_options;
       }
       leaf ignore-l3-incompletes {
         description "Ignore L3 incomplete errors";
         type empty;
       }
       leaf no-auto-mdix {
         description "Disable auto MDI/MDIX";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
           enum "fec-etc" {
             description "ETC fec based on IEEE 802.3 Clause 119 for 800G links";
           }
           enum "fec172" {
             description "IEEE 802.3dj Clause 172, RS-FEC for 800G links";
           }
         }
       }
       container speed {
         description "Specify speed";
         choice automatic {
           case case_1 {
             container auto-negotiation {
               presence "enable auto-negotiation";
               description "Enable auto-negotiation";
               leaf auto-negotiate-10-100 {
                 description "Limits the auto-negotiation to 10m/100m only";
                 type empty;
               }
             }
           }
           case case_2 {
             leaf ethernet-10m {
               description "10Mbps";
               type empty;
             }
           }
           case case_3 {
             leaf ethernet-100m {
               description "100Mbps";
               type empty;
             }
           }
           case case_4 {
             leaf ethernet-1g {
               description "1Gbps";
               type empty;
             }
           }
           case case_5 {
             leaf ethernet-10g {
               description "10Gbps";
               type empty;
             }
           }
         }
       }
       container ieee-802.3ad {
         description "IEEE 802.3ad";
         uses apply-advanced;
         container lacp {
           description "Link Aggregation Control Protocol configuration";
           uses apply-advanced;
           leaf force-up {
             description "Keep the port up in absence of received LACPDU";
             type empty;
           }
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
         container link-protection-sub-group {
           description "Link Protection subgroup configuration";
           uses apply-advanced;
           leaf subgroup-name {
             description "Name of the subgroup";
             type string {
               length "2 .. 64";
             }
           }
         }
         leaf port-priority {
           description "Link protection Priority of the port (0 ... 65535)";
           type union {
             type uint16;
             type string {
               pattern "<.*>|$.*";
             }
           }
         }
       }
       leaf ieee-802-3az-eee {
         description "IEEE 802.3az Energy Efficient Ethernet(EEE)";
         type empty;
       }
       leaf mdi-mode {
         description "Cable cross-over mode";
         type enumeration {
           enum "auto" {
             description "Automatic mdi/mdi-x mode";
           }
           enum "force" {
             description "Enable auto-MDIX always";
           }
           enum "mdi" {
             description "MDI(straight through) mode";
           }
           enum "mdix" {
             description "MDI Cross-over mode";
           }
         }
       }
       leaf autostate-exclude {
         description "Interface will not contribute to IRB state";
         type empty;
       }
     }
     container fibrechannel-options {
       description "Fibre Channel interface-specific options";
       uses apply-advanced;
       choice loopback-choice {
         leaf loopback {
           description "Enable loopback";
           type empty;
         }
         leaf no-loopback {
           description "Don't enable loopback";
           type empty;
         }
       }
       leaf bb-sc-n {
         description "B2B state change number";
         type union {
           type string {
             pattern "<.*>|$.*";
           }
           type uint16 {
             range "0 .. 15";
           }
         }
       }
       leaf speed {
         description "Specify speed";
         type enumeration {
           enum "auto-negotiation" {
             description "Enable auto-negotiation";
           }
           enum "1g" {
             description "1Gbps";
           }
           enum "2g" {
             description "2Gbps";
           }
           enum "4g" {
             description "4Gbps";
           }
           enum "8g" {
             description "8Gbps";
           }
         }
       }
     }
     container gigether-options {
       description "Gigabit Ethernet interface-specific options";
       uses apply-advanced;
       choice loopback-choice {
         leaf loopback {
           description "Enable loopback";
           type empty;
         }
         leaf no-loopback {
           description "Don't enable loopback";
           type empty;
         }
       }
       leaf loopback-remote {
         description "Enable remote loopback";
         type empty;
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       choice auto_negotiation_option {
         case case_1 {
           leaf no-auto-negotiation {
             description "Disable auto-negotiation";
             type empty;
           }
         }
         case case_2 {
           container auto-negotiation {
             presence "enable auto-negotiation";
             description "Enable auto-negotiation";
             leaf remote-fault {
               type enumeration {
                 enum "local-interface-offline" {
                   description "Disable local interface";
                 }
                 enum "local-interface-online" {
                   description "Enable local interface";
                 }
               }
             }
           }
         }
       }
       leaf asynchronous-notification {
         description "Enable sending asynchronous notification to peer on CCC-down";
         type empty;
       }
       list source-address-filter {
         key name;
         description "Source address filters";
         leaf name {
           description "Remote MAC address";
           type jt:mac-addr;
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         container ethernet-policer-profile {
           description "Ethernet level CoS-based policer configuration";
           uses apply-advanced;
           container ieee802.1-priority-map {
             presence "enable ieee802.1-priority-map";
             description "Premium priority values for IEEE 802.1p bits";
             status deprecated;
             uses apply-advanced;
             leaf-list premium {
               ordered-by user;
               description "Premium policer priority map";
               type union {
                 type string {
                   pattern "<.*>|$.*";
                 }
                 type uint32 {
                   range "0 .. 7";
                 }
               }
             }
           }
           container input-priority-map {
             description "Input policer priority map";
             uses cos_policer_input_priority_map;
           }
           container output-priority-map {
             description "Output policer priority map";
             uses cos_policer_output_priority_map;
           }
           list policer {
             key name;
             ordered-by user;
             description "Policer template definition";
             uses cos_policer;
           }
         }
         container accept-from {
           description "Accept traffic from or to specified remote MAC";
           status deprecated;
           uses apply-advanced;
           list mac-address {
             key name;
             description "Remote MAC";
             uses mac_list;
           }
         }
         choice reject-the-rest-choice {
           leaf reject-the-rest {
             description "Accept traffic from only the specified MAC addresses";
             status deprecated;
             type empty;
           }
           leaf no-reject-the-rest {
             description "Don't accept traffic from only the specified MAC addresses";
             status deprecated;
             type empty;
           }
         }
         leaf mac-learn-enable {
           description "Learn MAC addresses dynamically";
           type empty;
         }
       }
       container mpls {
         description "MPLS options";
         uses mpls_ifd_options;
       }
       leaf ignore-l3-incompletes {
         description "Ignore L3 incomplete errors";
         type empty;
       }
       leaf ieee-802-3az-eee {
         description "IEEE 802.3az Energy Efficient Ethernet(EEE)";
         type empty;
       }
       leaf fec {
         description "Forward Error Correction mode";
         type enumeration {
           enum "none" {
             description "FEC disabled";
           }
           enum "fec91" {
             description "IEEE 802.3bj Clause 91, Reed-Solomon FEC (RS-FEC)";
           }
           enum "fec74" {
             description "FEC74 enabled";
           }
           enum "fec108" {
             description "IEEE 802.3by Clause 108, Reed-Solomon FEC (RS-FEC) on 25g links";
           }
           enum "fec161" {
             description "IEEE 802.3ck Clause 161 for 100G electrical links";
           }
         }
       }
     }
     container optics-options {
       description "Optics options";
       uses apply-advanced;
       leaf wavelength {
         description "Wavelength of the optics (nanometers) for 50Ghz/100Ghz spacing";
         type enumeration {
           enum "1611.79" {
             description "1611.79 nm/186.000000 THz 3.125/6.25/12.5/50/75/100GHz spacing";
           }
           enum "1611.76" {
             description "1611.76 nm/186.003125 THz 3.125GHz spacing";
           }
           enum "1611.73" {
             description "1611.73 nm/186.006250 THz 3.125/6.25GHz spacing";
           }
           enum "1611.71" {
             description "1611.71 nm/186.009375 THz 3.125GHz spacing";
           }
           enum "1611.68" {
             description "1611.68 nm/186.012500 THz 3.125/6.25/12.5GHz spacing";
           }
           enum "1611.65" {
             description "1611.65 nm/186.015625 THz 3.125GHz spacing";
           }
           enum "1611.62" {
             description "1611.62 nm/186.018750 THz 3.125/6.25GHz spacing";
           }
           enum "1611.60" {
             description "1611.60 nm/186.021875 THz 3.125GHz spacing";
           }
           enum "1611.57" {
             description "1611.57 nm/186.025000 THz 3.125/6.25/12.5GHz spacing";
           }
           enum "1611.54" {
             description "1611.54 nm/186.028125 THz 3.125GHz spacing";
           }
           enum "1611.52" {
             description "1611.52 nm/186.031250 THz 3.125/6.25GHz spacing";
           }
           enum "1611.49" {
             description "1611.49 nm/186.034375 THz 3.125GHz spacing";
           }
           enum "1611.46" {
             description "1611.46 nm/186.037500 THz 3.125/6.25/12.5GHz spacing";
           }
           enum "1611.44" {
             description "1611.44 nm/186.040625 THz 3.125GHz spacing";
           }
           enum "1611.41" {
             description "1611.41 nm/186.043750 THz 3.125/6.25GHz spacing";
           }
           enum "1611.38" {
             description "1611.38 nm/186.046875 THz 3.125GHz spacing";
           }
           enum "1611.35" {
             description "1611.35 nm/186.050000 THz 3.125/6.25/12.5/50/75GHz spacing";
           }
           enum "1611.33" {
             description "1611.33 nm/186.053125 THz 3.125GHz spacing";
           }
           enum "1611.30" {
             description "1611.30 nm/186.056250 THz 3.125/6.25GHz spacing";
           }
           enum "1611.27" {
             description "1611.27 nm/186.059375 THz 3.125GHz spacing";
           }
           enum "1611.25" {
             description "1611.25 nm/186.062500 THz 3.125/6.25/12.5GHz spacing";
           }
           enum "1611.22" {
             description "1611.22 nm/186.065625 THz 3.125GHz spacing";
           }
           enum "1611.19" {
             description "1611.19 nm/186.068750 THz 3.125/6.25GHz spacing";
           }
           enum "1611.16" {
             description "1611.16 nm/186.071875 THz 3.125GHz spacing";
           }
           enum "1611.14" {
             description "1611.14 nm/186.075000 THz 3.125/6.25/12.5GHz spacing";
           }
           enum "1611.11" {
             description "1611.11 nm/186.078125 THz 3.125GHz spacing";
           }
           enum "1611.08" {
             description "1611.08 nm/186.081250 THz 3.125/6.25GHz spacing";
           }
           enum "1611.06" {
             description "1611.06 nm/186.084375 THz 3.125GHz spacing";
           }
           enum "1611.03" {
             description "1611.03 nm/186.087500 THz 3.125/6.25/12.5GHz spacing";
           }
           enum "1611.00" {
             description "1611.00 nm/186.090625 THz 3.125GHz spacing";
           }
           enum "1610.98" {
             description "1610.98 nm/186.093750 THz 3.125/6.25GHz spacing";
           }
           enum "1610.95" {
             description "1610.95 nm/186.096875 THz 3.125GHz spacing";
           }
           enum "1610.92" {
             description "1610.92 nm/186.100000 THz 3.125/6.25/12.5/100GHz spacing";
           }
           enum "1610.89" {
             description "1610.89 nm/186.103125 THz 3.125GHz spacing";
           }
           enum "1610.87" {
             description "1610.87 nm/186.106250 THz 3.125/6.25GHz spacing";
           }
           enum "1610.84" {
             description "1610.84 nm/186.109375 THz 3.125GHz spacing";
           }
           enum "1610.81" {
             description "1610.81 nm/186.112500 THz 3.125/6.25/12.5GHz spacing";
           }
           enum "1610.79" {
             description "1610.79 nm/186.115625 THz 3.125GHz spacing";
           }
           enum "1610.76" {
             description "1610.76 nm/186.118750 THz 3.125/6.25GHz spacing";
           }
           enum "1610.73" {
             description "1610.73 nm/186.121875 THz 3.125GHz spacing";
           }
           enum "1610.70" {
             description "1610.70 nm/186.125000 THz 3.125/6.25/12.5/75GHz spacing";
           }
           enum "1610.68" {
             description "1610.68 nm/186.128125 THz 3.125GHz spacing";
           }
           enum "1610.65" {
             description "1610.65 nm/186.131250 THz 3.125/6.25GHz spacing";
           }
           enum "1610.62" {
             description "1610.62 nm/186.134375 THz 3.125GHz spacing";
           }
           enum "1610.60" {
             description "1610.60 nm/186.137500 THz 3.125/6.25/12.5GHz spacing";
           }
           enum "1610.57" {
             description "1610.57 nm/186.140625 THz 3.125GHz spacing";
           }
           enum "1610.54" {
             description "1610.54 nm/186.143750 THz 3.125/6.25GHz spacing";
           }
           enum "1610.52" {
             description "1610.52 nm/186.146875 THz 3.125GHz spacing";
           }
           enum "1610.49" {
             description "1610.49 nm/186.150000 THz 3.125/6.25/12.5/50GHz spacing";
           }
           enum "1610.46" {
             description "1610.46 nm/186.153125 THz 3.125GHz spacing";
           }
           enum "1610.43" {
             description "1610.43 nm/186.156250 THz 3.125/6.25GHz spacing";
           }
           enum "1610.41" {
             description "1610.41 nm/186.159375 THz 3.125GHz spacing";
           }
           enum "1610.38" {
             description "1610.38 nm/186.162500 THz 3.125/6.25/12.5GHz spacing";
           }
           enum "1610.35" {
             description "1610.35 nm/186.165625 THz 3.125GHz spacing";
           }
           enum "1610.33" {
             description "1610.33 nm/186.168750 THz 3.125/6.25GHz spacing";
           }
           enum "1610.30" {
             description "1610.30 nm/186.171875 THz 3.125GHz spacing";
           }
           enum "1610.27" {
             description "1610.27 nm/186.175000 THz 3.125/6.25/12.5GHz spacing";
           }
           enum "1610.25" {
             description "1610.25 nm/186.178125 THz 3.125GHz spacing";
           }
           enum "1610.22" {
             description "1610.22 nm/186.181250 THz 3.125/6.25GHz spacing";
           }
           enum "1610.19" {
             description "1610.19 nm/186.184375 THz 3.125GHz spacing";
           }
           enum "1610.16" {
             description "1610.16 nm/186.187500 THz 3.125/6.25/12.5GHz spacing";
           }
           enum "1610.14" {
             description "1610.14 nm/186.190625 THz 3.125GHz spacing";
           }
           enum "1610.11" {
             description "1610.11 nm/186.193750 THz 3.125/6.25GHz spacing";
           }
           enum "1610.08" {
             description "1610.08 nm/186.196875 THz 3.125GHz spacing";
           }
           enum "1610.06" {
             description "1610.06 nm/186.200000 THz 3.125/6.25/12.5/100GHz spacing";
           }
           enum "1610.03" {
             description "1610.03 nm/186.203125 THz 3.125GHz spacing";
           }
           enum "1610.00" {
             description "1610.00 nm/186.206250 THz 3.125/6.25GHz spacing";
           }
           enum "1609.98" {
             description "1609.98 nm/186.209375 THz 3.125GHz spacing";
           }
           enum "1609.95" {
             description "1609.95 nm/186.212500 THz 3.125/6.25/12.5GHz spacing";
           }
           enum "1609.92" {
             description "1609.92 nm/186.215625 THz 3.125GHz spacing";
           }
           enum "1609.89" {
             description "1609.89 nm/186.218750 THz 3.125/6.25GHz spacing";
           }
           enum "1609.87" {
             description "1609.87 nm/186.221875 THz 3.125GHz spacing";
           }
           enum "1609.84" {
             description "1609.84 nm/186.225000 THz 3.125/6.25/12.5GHz spacing";
           }
           enum "1609.81" {
             description "1609.81 nm/186.228125 THz 3.125GHz spacing";
           }
           enum "1609.79" {
             description "1609.79 nm/186.231250 THz 3.125/6.25GHz spacing";
           }
           enum "1609.76" {
             description "1609.76 nm/186.234375 THz 3.125GHz spacing";
           }
           enum "1609.73" {
             description "1609.73 nm/186.237500 THz 3.125/6.25/12.5GHz spacing";
           }
           enum "1609.70" {
             description "1609.70 nm/186.240625 THz 3.125GHz spacing";
           }
           enum "1609.68" {
             description "1609.68 nm/186.243750 THz 3.125/6.25GHz spacing";
           }
           enum "1609.65" {
             description "1609.65 nm/186.246875 THz 3.125GHz spacing";
           }
           enum "1609.62" {
             description "1609.62 nm/186.250000 THz 3.125/6.25/12.5/50GHz spacing";
           }
           enum "1609.60" {
             description "1609.60 nm/186.253125 THz 3.125GHz spacing";
           }
           enum "1609.57" {
             description "1609.57 nm/186.256250 THz 3.125/6.25GHz spacing";
           }
           enum "1609.54" {
             description "1609.54 nm/186.259375 THz 3.125GHz spacing";
           }
           enum "1609.52" {
             description "1609.52 nm/186.262500 THz 3.125/6.25/12.5GHz spacing";
           }
           enum "1609.49" {
             description "1609.49 nm/186.265625 THz 3.125GHz spacing";
           }
           enum "1609.46" {
             description "1609.46 nm/186.268750 THz 3.125/6.25GHz spacing";
           }
           enum "1609.43" {
             description "1609.43 nm/186.271875 THz 3.125GHz spacing";
           }
           enum "1609.41" {
             description "1609.41 nm/186.275000 THz 3.125/6.25/12.5/75GHz spacing";
           }
           enum "1609.38" {
             description "1609.38 nm/186.278125 THz 3.125GHz spacing";
           }
           enum "1609.35" {
             description "1609.35 nm/186.281250 THz 3.125/6.25GHz spacing";
           }
           enum "1609.33" {
             description "1609.33 nm/186.284375 THz 3.125GHz spacing";
           }
           enum "1609.30" {
             description "1609.30 nm/186.287500 THz 3.125/6.25/12.5GHz spacing";
           }
           enum "1609.27" {
             description "1609.27 nm/186.290625 THz 3.125GHz spacing";
           }
           enum "1609.25" {
             description "1609.25 nm/186.293750 THz 3.125/6.25GHz spacing";
           }
           enum "1609.22" {
             description "1609.22 nm/186.296875 THz 3.125GHz spacing";
           }
           enum "1609.19" {
             description "1609.19 nm/186.300000 THz 3.125/6.25/12.5/50/75/100GHz spacing";
           }
           enum "1609.16" {
             description "1609.16 nm/186.303125 THz 3.125GHz spacing";
           }
           enum "1609.14" {
             description "1609.14 nm/186.306250 THz 3.125/6.25GHz spacing";
           }
           enum "1609.11" {
             description "1609.11 nm/186.309375 THz 3.125GHz spacing";
           }
           enum "1609.08" {
             description "1609.08 nm/186.312500 THz 3.125/6.25/12.5GHz spacing";
           }
           enum "1609.06" {
             description "1609.06 nm/186.315625 THz 3.125GHz spacing";
           }
           enum "1609.03" {
             description "1609.03 nm/186.318750 THz 3.125/6.25GHz spacing";
           }
           enum "1609.00" {
             description "1609.00 nm/186.321875 THz 3.125GHz spacing";
           }
           enum "1608.98" {
             description "1608.98 nm/186.325000 THz 3.125/6.25/12.5GHz spacing";
           }
           enum "1608.95" {
             description "1608.95 nm/186.328125 THz 3.125GHz spacing";
           }
           enum "1608.92" {
             description "1608.92 nm/186.331250 THz 3.125/6.25GHz spacing";
           }
           enum "1608.90" {
             description "1608.90 nm/186.334375 THz 3.125GHz spacing";
           }
           enum "1608.87" {
             description "1608.87 nm/186.337500 THz 3.125/6.25/12.5GHz spacing";
           }
           enum "1608.84" {
             description "1608.84 nm/186.340625 THz 3.125GHz spacing";
           }
           enum "1608.81" {
             description "1608.81 nm/186.343750 THz 3.125/6.25GHz spacing";
           }
           enum "1608.79" {
             description "1608.79 nm/186.346875 THz 3.125GHz spacing";
           }
           enum "1608.76" {
             description "1608.76 nm/186.350000 THz 3.125/6.25/12.5/50/75GHz spacing";
           }
           enum "1608.73" {
             description "1608.73 nm/186.353125 THz 3.125GHz spacing";
           }
           enum "1608.71" {
             description "1608.71 nm/186.356250 THz 3.125/6.25GHz spacing";
           }
           enum "1608.68" {
             description "1608.68 nm/186.359375 THz 3.125GHz spacing";
           }
           enum "1608.65" {
             description "1608.65 nm/186.362500 THz 3.125/6.25/12.5GHz spacing";
           }
           enum "1608.63" {
             description "1608.63 nm/186.365625 THz 3.125GHz spacing";
           }
           enum "1608.60" {
             description "1608.60 nm/186.368750 THz 3.125/6.25GHz spacing";
           }
           enum "1608.57" {
             description "1608.57 nm/186.371875 THz 3.125GHz spacing";
           }
           enum "1608.54" {
             description "1608.54 nm/186.375000 THz 3.125/6.25/12.5GHz spacing";
           }
           enum "1608.52" {
             description "1608.52 nm/186.378125 THz 3.125GHz spacing";
           }
           enum "1608.49" {
             description "1608.49 nm/186.381250 THz 3.125/6.25GHz spacing";
           }
           enum "1608.46" {
             description "1608.46 nm/186.384375 THz 3.125GHz spacing";
           }
           enum "1608.44" {
             description "1608.44 nm/186.387500 THz 3.125/6.25/12.5GHz spacing";
           }
           enum "1608.41" {
             description "1608.41 nm/186.390625 THz 3.125GHz spacing";
           }
           enum "1608.38" {
             description "1608.38 nm/186.393750 THz 3.125/6.25GHz spacing";
           }
           enum "1608.36" {
             description "1608.36 nm/186.396875 THz 3.125GHz spacing";
           }
           enum "1608.33" {
             description "1608.33 nm/186.400000 THz 3.125/6.25/12.5/100GHz spacing";
           }
           enum "1608.30" {
             description "1608.30 nm/186.403125 THz 3.125GHz spacing";
           }
           enum "1608.27" {
             description "1608.27 nm/186.406250 THz 3.125/6.25GHz spacing";
           }
           enum "1608.25" {
             description "1608.25 nm/186.409375 THz 3.125GHz spacing";
           }
           enum "1608.22" {
             description "1608.22 nm/186.412500 THz 3.125/6.25/12.5GHz spacing";
           }
           enum "1608.19" {
             description "1608.19 nm/186.415625 THz 3.125GHz spacing";
           }
           enum "1608.17" {
             description "1608.17 nm/186.418750 THz 3.125/6.25GHz spacing";
           }
           enum "1608.14" {
             description "1608.14 nm/186.421875 THz 3.125GHz spacing";
           }
           enum "1608.11" {
             description "1608.11 nm/186.425000 THz 3.125/6.25/12.5/75GHz spacing";
           }
           enum "1608.09" {
             description "1608.09 nm/186.428125 THz 3.125GHz spacing";
           }
           enum "1608.06" {
             description "1608.06 nm/186.431250 THz 3.125/6.25GHz spacing";
           }
           enum "1608.03" {
             description "1608.03 nm/186.434375 THz 3.125GHz spacing";
           }
           enum "1608.01" {
             description "1608.01 nm/186.437500 THz 3.125/6.25/12.5GHz spacing";
           }
           enum "1607.98" {
             description "1607.98 nm/186.440625 THz 3.125GHz spacing";
           }
           enum "1607.95" {
             description "1607.95 nm/186.443750 THz 3.125/6.25GHz spacing";
           }
           enum "1607.92" {
             description "1607.92 nm/186.446875 THz 3.125GHz spacing";
           }
           enum "1607.90" {
             description "1607.90 nm/186.450000 THz 3.125/6.25/12.5/50GHz spacing";
           }
           enum "1607.87" {
             description "1607.87 nm/186.453125 THz 3.125GHz spacing";
           }
           enum "1607.84" {
             description "1607.84 nm/186.456250 THz 3.125/6.25GHz spacing";
           }
           enum "1607.82" {
             description "1607.82 nm/186.459375 THz 3.125GHz spacing";
           }
           enum "1607.79" {
             description "1607.79 nm/186.462500 THz 3.125/6.25/12.5GHz spacing";
           }
           enum "1607.76" {
             description "1607.76 nm/186.465625 THz 3.125GHz spacing";
           }
           enum "1607.74" {
             description "1607.74 nm/186.468750 THz 3.125/6.25GHz spacing";
           }
           enum "1607.71" {
             description "1607.71 nm/186.471875 THz 3.125GHz spacing";
           }
           enum "1607.68" {
             description "1607.68 nm/186.475000 THz 3.125/6.25/12.5GHz spacing";
           }
           enum "1607.65" {
             description "1607.65 nm/186.478125 THz 3.125GHz spacing";
           }
           enum "1607.63" {
             description "1607.63 nm/186.481250 THz 3.125/6.25GHz spacing";
           }
           enum "1607.60" {
             description "1607.60 nm/186.484375 THz 3.125GHz spacing";
           }
           enum "1607.57" {
             description "1607.57 nm/186.487500 THz 3.125/6.25/12.5GHz spacing";
           }
           enum "1607.55" {
             description "1607.55 nm/186.490625 THz 3.125GHz spacing";
           }
           enum "1607.52" {
             description "1607.52 nm/186.493750 THz 3.125/6.25GHz spacing";
           }
           enum "1607.49" {
             description "1607.49 nm/186.496875 THz 3.125GHz spacing";
           }
           enum "1607.47" {
             description "1607.47 nm/186.500000 THz 3.125/6.25/12.5/100GHz spacing";
           }
           enum "1607.44" {
             description "1607.44 nm/186.503125 THz 3.125GHz spacing";
           }
           enum "1607.41" {
             description "1607.41 nm/186.506250 THz 3.125/6.25GHz spacing";
           }
           enum "1607.39" {
             description "1607.39 nm/186.509375 THz 3.125GHz spacing";
           }
           enum "1607.36" {
             description "1607.36 nm/186.512500 THz 3.125/6.25/12.5GHz spacing";
           }
           enum "1607.33" {
             description "1607.33 nm/186.515625 THz 3.125GHz spacing";
           }
           enum "1607.30" {
             description "1607.30 nm/186.518750 THz 3.125/6.25GHz spacing";
           }
           enum "1607.28" {
             description "1607.28 nm/186.521875 THz 3.125GHz spacing";
           }
           enum "1607.25" {
             description "1607.25 nm/186.525000 THz 3.125/6.25/12.5GHz spacing";
           }
           enum "1607.22" {
             description "1607.22 nm/186.528125 THz 3.125GHz spacing";
           }
           enum "1607.20" {
             description "1607.20 nm/186.531250 THz 3.125/6.25GHz spacing";
           }
           enum "1607.17" {
             description "1607.17 nm/186.534375 THz 3.125GHz spacing";
           }
           enum "1607.14" {
             description "1607.14 nm/186.537500 THz 3.125/6.25/12.5GHz spacing";
           }
           enum "1607.12" {
             description "1607.12 nm/186.540625 THz 3.125GHz spacing";
           }
           enum "1607.09" {
             description "1607.09 nm/186.543750 THz 3.125/6.25GHz spacing";
           }
           enum "1607.06" {
             description "1607.06 nm/186.546875 THz 3.125GHz spacing";
           }
           enum "1607.04" {
             description "1607.04 nm/186.550000 THz 3.125/6.25/12.5/50GHz spacing";
           }
           enum "1607.01" {
             description "1607.01 nm/186.553125 THz 3.125GHz spacing";
           }
           enum "1606.98" {
             description "1606.98 nm/186.556250 THz 3.125/6.25GHz spacing";
           }
           enum "1606.95" {
             description "1606.95 nm/186.559375 THz 3.125GHz spacing";
           }
           enum "1606.93" {
             description "1606.93 nm/186.562500 THz 3.125/6.25/12.5GHz spacing";
           }
           enum "1606.90" {
             description "1606.90 nm/186.565625 THz 3.125GHz spacing";
           }
           enum "1606.87" {
             description "1606.87 nm/186.568750 THz 3.125/6.25GHz spacing";
           }
           enum "1606.85" {
             description "1606.85 nm/186.571875 THz 3.125GHz spacing";
           }
           enum "1606.82" {
             description "1606.82 nm/186.575000 THz 3.125/6.25/12.5/75GHz spacing";
           }
           enum "1606.79" {
             description "1606.79 nm/186.578125 THz 3.125GHz spacing";
           }
           enum "1606.77" {
             description "1606.77 nm/186.581250 THz 3.125/6.25GHz spacing";
           }
           enum "1606.74" {
             description "1606.74 nm/186.584375 THz 3.125GHz spacing";
           }
           enum "1606.71" {
             description "1606.71 nm/186.587500 THz 3.125/6.25/12.5GHz spacing";
           }
           enum "1606.69" {
             description "1606.69 nm/186.590625 THz 3.125GHz spacing";
           }
           enum "1606.66" {
             description "1606.66 nm/186.593750 THz 3.125/6.25GHz spacing";
           }
           enum "1606.63" {
             description "1606.63 nm/186.596875 THz 3.125GHz spacing";
           }
           enum "1606.60" {
             description "1606.60 nm/186.600000 THz 3.125/6.25/12.5/50/75/100GHz spacing";
           }
           enum "1606.58" {
             description "1606.58 nm/186.603125 THz 3.125GHz spacing";
           }
           enum "1606.55" {
             description "1606.55 nm/186.606250 THz 3.125/6.25GHz spacing";
           }
           enum "1606.52" {
             description "1606.52 nm/186.609375 THz 3.125GHz spacing";
           }
           enum "1606.50" {
             description "1606.50 nm/186.612500 THz 3.125/6.25/12.5GHz spacing";
           }
           enum "1606.47" {
             description "1606.47 nm/186.615625 THz 3.125GHz spacing";
           }
           enum "1606.44" {
             description "1606.44 nm/186.618750 THz 3.125/6.25GHz spacing";
           }
           enum "1606.42" {
             description "1606.42 nm/186.621875 THz 3.125GHz spacing";
           }
           enum "1606.39" {
             description "1606.39 nm/186.625000 THz 3.125/6.25/12.5GHz spacing";
           }
           enum "1606.36" {
             description "1606.36 nm/186.628125 THz 3.125GHz spacing";
           }
           enum "1606.34" {
             description "1606.34 nm/186.631250 THz 3.125/6.25GHz spacing";
           }
           enum "1606.31" {
             description "1606.31 nm/186.634375 THz 3.125GHz spacing";
           }
           enum "1606.28" {
             description "1606.28 nm/186.637500 THz 3.125/6.25/12.5GHz spacing";
           }
           enum "1606.26" {
             description "1606.26 nm/186.640625 THz 3.125GHz spacing";
           }
           enum "1606.23" {
             description "1606.23 nm/186.643750 THz 3.125/6.25GHz spacing";
           }
           enum "1606.20" {
             description "1606.20 nm/186.646875 THz 3.125GHz spacing";
           }
           enum "1606.17" {
             description "1606.17 nm/186.650000 THz 3.125/6.25/12.5/50/75GHz spacing";
           }
           enum "1606.15" {
             description "1606.15 nm/186.653125 THz 3.125GHz spacing";
           }
           enum "1606.12" {
             description "1606.12 nm/186.656250 THz 3.125/6.25GHz spacing";
           }
           enum "1606.09" {
             description "1606.09 nm/186.659375 THz 3.125GHz spacing";
           }
           enum "1606.07" {
             description "1606.07 nm/186.662500 THz 3.125/6.25/12.5GHz spacing";
           }
           enum "1606.04" {
             description "1606.04 nm/186.665625 THz 3.125GHz spacing";
           }
           enum "1606.01" {
             description "1606.01 nm/186.668750 THz 3.125/6.25GHz spacing";
           }
           enum "1605.99" {
             description "1605.99 nm/186.671875 THz 3.125GHz spacing";
           }
           enum "1605.96" {
             description "1605.96 nm/186.675000 THz 3.125/6.25/12.5GHz spacing";
           }
           enum "1605.93" {
             description "1605.93 nm/186.678125 THz 3.125GHz spacing";
           }
           enum "1605.91" {
             description "1605.91 nm/186.681250 THz 3.125/6.25GHz spacing";
           }
           enum "1605.88" {
             description "1605.88 nm/186.684375 THz 3.125GHz spacing";
           }
           enum "1605.85" {
             description "1605.85 nm/186.687500 THz 3.125/6.25/12.5GHz spacing";
           }
           enum "1605.82" {
             description "1605.82 nm/186.690625 THz 3.125GHz spacing";
           }
           enum "1605.80" {
             description "1605.80 nm/186.693750 THz 3.125/6.25GHz spacing";
           }
           enum "1605.77" {
             description "1605.77 nm/186.696875 THz 3.125GHz spacing";
           }
           enum "1605.74" {
             description "1605.74 nm/186.700000 THz 3.125/6.25/12.5/100GHz spacing";
           }
           enum "1605.72" {
             description "1605.72 nm/186.703125 THz 3.125GHz spacing";
           }
           enum "1605.69" {
             description "1605.69 nm/186.706250 THz 3.125/6.25GHz spacing";
           }
           enum "1605.66" {
             description "1605.66 nm/186.709375 THz 3.125GHz spacing";
           }
           enum "1605.64" {
             description "1605.64 nm/186.712500 THz 3.125/6.25/12.5GHz spacing";
           }
           enum "1605.61" {
             description "1605.61 nm/186.715625 THz 3.125GHz spacing";
           }
           enum "1605.58" {
             description "1605.58 nm/186.718750 THz 3.125/6.25GHz spacing";
           }
           enum "1605.56" {
             description "1605.56 nm/186.721875 THz 3.125GHz spacing";
           }
           enum "1605.53" {
             description "1605.53 nm/186.725000 THz 3.125/6.25/12.5/75GHz spacing";
           }
           enum "1605.50" {
             description "1605.50 nm/186.728125 THz 3.125GHz spacing";
           }
           enum "1605.48" {
             description "1605.48 nm/186.731250 THz 3.125/6.25GHz spacing";
           }
           enum "1605.45" {
             description "1605.45 nm/186.734375 THz 3.125GHz spacing";
           }
           enum "1605.42" {
             description "1605.42 nm/186.737500 THz 3.125/6.25/12.5GHz spacing";
           }
           enum "1605.39" {
             description "1605.39 nm/186.740625 THz 3.125GHz spacing";
           }
           enum "1605.37" {
             description "1605.37 nm/186.743750 THz 3.125/6.25GHz spacing";
           }
           enum "1605.34" {
             description "1605.34 nm/186.746875 THz 3.125GHz spacing";
           }
           enum "1605.31" {
             description "1605.31 nm/186.750000 THz 3.125/6.25/12.5/50GHz spacing";
           }
           enum "1605.29" {
             description "1605.29 nm/186.753125 THz 3.125GHz spacing";
           }
           enum "1605.26" {
             description "1605.26 nm/186.756250 THz 3.125/6.25GHz spacing";
           }
           enum "1605.23" {
             description "1605.23 nm/186.759375 THz 3.125GHz spacing";
           }
           enum "1605.21" {
             description "1605.21 nm/186.762500 THz 3.125/6.25/12.5GHz spacing";
           }
           enum "1605.18" {
             description "1605.18 nm/186.765625 THz 3.125GHz spacing";
           }
           enum "1605.15" {
             description "1605.15 nm/186.768750 THz 3.125/6.25GHz spacing";
           }
           enum "1605.13" {
             description "1605.13 nm/186.771875 THz 3.125GHz spacing";
           }
           enum "1605.10" {
             description "1605.10 nm/186.775000 THz 3.125/6.25/12.5GHz spacing";
           }
           enum "1605.07" {
             description "1605.07 nm/186.778125 THz 3.125GHz spacing";
           }
           enum "1605.05" {
             description "1605.05 nm/186.781250 THz 3.125/6.25GHz spacing";
           }
           enum "1605.02" {
             description "1605.02 nm/186.784375 THz 3.125GHz spacing";
           }
           enum "1604.99" {
             description "1604.99 nm/186.787500 THz 3.125/6.25/12.5GHz spacing";
           }
           enum "1604.97" {
             description "1604.97 nm/186.790625 THz 3.125GHz spacing";
           }
           enum "1604.94" {
             description "1604.94 nm/186.793750 THz 3.125/6.25GHz spacing";
           }
           enum "1604.91" {
             description "1604.91 nm/186.796875 THz 3.125GHz spacing";
           }
           enum "1604.88" {
             description "1604.88 nm/186.800000 THz 3.125/6.25/12.5/100GHz spacing";
           }
           enum "1604.86" {
             description "1604.86 nm/186.803125 THz 3.125GHz spacing";
           }
           enum "1604.83" {
             description "1604.83 nm/186.806250 THz 3.125/6.25GHz spacing";
           }
           enum "1604.80" {
             description "1604.80 nm/186.809375 THz 3.125GHz spacing";
           }
           enum "1604.78" {
             description "1604.78 nm/186.812500 THz 3.125/6.25/12.5GHz spacing";
           }
           enum "1604.75" {
             description "1604.75 nm/186.815625 THz 3.125GHz spacing";
           }
           enum "1604.72" {
             description "1604.72 nm/186.818750 THz 3.125/6.25GHz spacing";
           }
           enum "1604.70" {
             description "1604.70 nm/186.821875 THz 3.125GHz spacing";
           }
           enum "1604.67" {
             description "1604.67 nm/186.825000 THz 3.125/6.25/12.5GHz spacing";
           }
           enum "1604.64" {
             description "1604.64 nm/186.828125 THz 3.125GHz spacing";
           }
           enum "1604.62" {
             description "1604.62 nm/186.831250 THz 3.125/6.25GHz spacing";
           }
           enum "1604.59" {
             description "1604.59 nm/186.834375 THz 3.125GHz spacing";
           }
           enum "1604.56" {
             description "1604.56 nm/186.837500 THz 3.125/6.25/12.5GHz spacing";
           }
           enum "1604.54" {
             description "1604.54 nm/186.840625 THz 3.125GHz spacing";
           }
           enum "1604.51" {
             description "1604.51 nm/186.843750 THz 3.125/6.25GHz spacing";
           }
           enum "1604.48" {
             description "1604.48 nm/186.846875 THz 3.125GHz spacing";
           }
           enum "1604.46" {
             description "1604.46 nm/186.850000 THz 3.125/6.25/12.5/50GHz spacing";
           }
           enum "1604.43" {
             description "1604.43 nm/186.853125 THz 3.125GHz spacing";
           }
           enum "1604.40" {
             description "1604.40 nm/186.856250 THz 3.125/6.25GHz spacing";
           }
           enum "1604.37" {
             description "1604.37 nm/186.859375 THz 3.125GHz spacing";
           }
           enum "1604.35" {
             description "1604.35 nm/186.862500 THz 3.125/6.25/12.5GHz spacing";
           }
           enum "1604.32" {
             description "1604.32 nm/186.865625 THz 3.125GHz spacing";
           }
           enum "1604.29" {
             description "1604.29 nm/186.868750 THz 3.125/6.25GHz spacing";
           }
           enum "1604.27" {
             description "1604.27 nm/186.871875 THz 3.125GHz spacing";
           }
           enum "1604.24" {
             description "1604.24 nm/186.875000 THz 3.125/6.25/12.5/75GHz spacing";
           }
           enum "1604.21" {
             description "1604.21 nm/186.878125 THz 3.125GHz spacing";
           }
           enum "1604.19" {
             description "1604.19 nm/186.881250 THz 3.125/6.25GHz spacing";
           }
           enum "1604.16" {
             description "1604.16 nm/186.884375 THz 3.125GHz spacing";
           }
           enum "1604.13" {
             description "1604.13 nm/186.887500 THz 3.125/6.25/12.5GHz spacing";
           }
           enum "1604.11" {
             description "1604.11 nm/186.890625 THz 3.125GHz spacing";
           }
           enum "1604.08" {
             description "1604.08 nm/186.893750 THz 3.125/6.25GHz spacing";
           }
           enum "1604.05" {
             description "1604.05 nm/186.896875 THz 3.125GHz spacing";
           }
           enum "1604.03" {
             description "1604.03 nm/186.900000 THz 3.125/6.25/12.5/50/75/100GHz spacing";
           }
           enum "1604.00" {
             description "1604.00 nm/186.903125 THz 3.125GHz spacing";
           }
           enum "1603.97" {
             description "1603.97 nm/186.906250 THz 3.125/6.25GHz spacing";
           }
           enum "1603.95" {
             description "1603.95 nm/186.909375 THz 3.125GHz spacing";
           }
           enum "1603.92" {
             description "1603.92 nm/186.912500 THz 3.125/6.25/12.5GHz spacing";
           }
           enum "1603.89" {
             description "1603.89 nm/186.915625 THz 3.125GHz spacing";
           }
           enum "1603.87" {
             description "1603.87 nm/186.918750 THz 3.125/6.25GHz spacing";
           }
           enum "1603.84" {
             description "1603.84 nm/186.921875 THz 3.125GHz spacing";
           }
           enum "1603.81" {
             description "1603.81 nm/186.925000 THz 3.125/6.25/12.5GHz spacing";
           }
           enum "1603.78" {
             description "1603.78 nm/186.928125 THz 3.125GHz spacing";
           }
           enum "1603.76" {
             description "1603.76 nm/186.931250 THz 3.125/6.25GHz spacing";
           }
           enum "1603.73" {
             description "1603.73 nm/186.934375 THz 3.125GHz spacing";
           }
           enum "1603.70" {
             description "1603.70 nm/186.937500 THz 3.125/6.25/12.5GHz spacing";
           }
           enum "1603.68" {
             description "1603.68 nm/186.940625 THz 3.125GHz spacing";
           }
           enum "1603.65" {
             description "1603.65 nm/186.943750 THz 3.125/6.25GHz spacing";
           }
           enum "1603.62" {
             description "1603.62 nm/186.946875 THz 3.125GHz spacing";
           }
           enum "1603.60" {
             description "1603.60 nm/186.950000 THz 3.125/6.25/12.5/50/75GHz spacing";
           }
           enum "1603.57" {
             description "1603.57 nm/186.953125 THz 3.125GHz spacing";
           }
           enum "1603.54" {
             description "1603.54 nm/186.956250 THz 3.125/6.25GHz spacing";
           }
           enum "1603.52" {
             description "1603.52 nm/186.959375 THz 3.125GHz spacing";
           }
           enum "1603.49" {
             description "1603.49 nm/186.962500 THz 3.125/6.25/12.5GHz spacing";
           }
           enum "1603.46" {
             description "1603.46 nm/186.965625 THz 3.125GHz spacing";
           }
           enum "1603.44" {
             description "1603.44 nm/186.968750 THz 3.125/6.25GHz spacing";
           }
           enum "1603.41" {
             description "1603.41 nm/186.971875 THz 3.125GHz spacing";
           }
           enum "1603.38" {
             description "1603.38 nm/186.975000 THz 3.125/6.25/12.5GHz spacing";
           }
           enum "1603.36" {
             description "1603.36 nm/186.978125 THz 3.125GHz spacing";
           }
           enum "1603.33" {
             description "1603.33 nm/186.981250 THz 3.125/6.25GHz spacing";
           }
           enum "1603.30" {
             description "1603.30 nm/186.984375 THz 3.125GHz spacing";
           }
           enum "1603.28" {
             description "1603.28 nm/186.987500 THz 3.125/6.25/12.5GHz spacing";
           }
           enum "1603.25" {
             description "1603.25 nm/186.990625 THz 3.125GHz spacing";
           }
           enum "1603.22" {
             description "1603.22 nm/186.993750 THz 3.125/6.25GHz spacing";
           }
           enum "1603.20" {
             description "1603.20 nm/186.996875 THz 3.125GHz spacing";
           }
           enum "1603.17" {
             description "1603.17 nm/187.000000 THz 3.125/6.25/12.5/100GHz spacing";
           }
           enum "1603.14" {
             description "1603.14 nm/187.003125 THz 3.125GHz spacing";
           }
           enum "1603.11" {
             description "1603.11 nm/187.006250 THz 3.125/6.25GHz spacing";
           }
           enum "1603.09" {
             description "1603.09 nm/187.009375 THz 3.125GHz spacing";
           }
           enum "1603.06" {
             description "1603.06 nm/187.012500 THz 3.125/6.25/12.5GHz spacing";
           }
           enum "1603.03" {
             description "1603.03 nm/187.015625 THz 3.125GHz spacing";
           }
           enum "1603.01" {
             description "1603.01 nm/187.018750 THz 3.125/6.25GHz spacing";
           }
           enum "1602.98" {
             description "1602.98 nm/187.021875 THz 3.125GHz spacing";
           }
           enum "1602.95" {
             description "1602.95 nm/187.025000 THz 3.125/6.25/12.5/75GHz spacing";
           }
           enum "1602.93" {
             description "1602.93 nm/187.028125 THz 3.125GHz spacing";
           }
           enum "1602.90" {
             description "1602.90 nm/187.031250 THz 3.125/6.25GHz spacing";
           }
           enum "1602.87" {
             description "1602.87 nm/187.034375 THz 3.125GHz spacing";
           }
           enum "1602.85" {
             description "1602.85 nm/187.037500 THz 3.125/6.25/12.5GHz spacing";
           }
           enum "1602.82" {
             description "1602.82 nm/187.040625 THz 3.125GHz spacing";
           }
           enum "1602.79" {
             description "1602.79 nm/187.043750 THz 3.125/6.25GHz spacing";
           }
           enum "1602.77" {
             description "1602.77 nm/187.046875 THz 3.125GHz spacing";
           }
           enum "1602.74" {
             description "1602.74 nm/187.050000 THz 3.125/6.25/12.5/50GHz spacing";
           }
           enum "1602.71" {
             description "1602.71 nm/187.053125 THz 3.125GHz spacing";
           }
           enum "1602.69" {
             description "1602.69 nm/187.056250 THz 3.125/6.25GHz spacing";
           }
           enum "1602.66" {
             description "1602.66 nm/187.059375 THz 3.125GHz spacing";
           }
           enum "1602.63" {
             description "1602.63 nm/187.062500 THz 3.125/6.25/12.5GHz spacing";
           }
           enum "1602.61" {
             description "1602.61 nm/187.065625 THz 3.125GHz spacing";
           }
           enum "1602.58" {
             description "1602.58 nm/187.068750 THz 3.125/6.25GHz spacing";
           }
           enum "1602.55" {
             description "1602.55 nm/187.071875 THz 3.125GHz spacing";
           }
           enum "1602.53" {
             description "1602.53 nm/187.075000 THz 3.125/6.25/12.5GHz spacing";
           }
           enum "1602.50" {
             description "1602.50 nm/187.078125 THz 3.125GHz spacing";
           }
           enum "1602.47" {
             description "1602.47 nm/187.081250 THz 3.125/6.25GHz spacing";
           }
           enum "1602.45" {
             description "1602.45 nm/187.084375 THz 3.125GHz spacing";
           }
           enum "1602.42" {
             description "1602.42 nm/187.087500 THz 3.125/6.25/12.5GHz spacing";
           }
           enum "1602.39" {
             description "1602.39 nm/187.090625 THz 3.125GHz spacing";
           }
           enum "1602.36" {
             description "1602.36 nm/187.093750 THz 3.125/6.25GHz spacing";
           }
           enum "1602.34" {
             description "1602.34 nm/187.096875 THz 3.125GHz spacing";
           }
           enum "1602.31" {
             description "1602.31 nm/187.100000 THz 3.125/6.25/12.5/100GHz spacing";
           }
           enum "1602.28" {
             description "1602.28 nm/187.103125 THz 3.125GHz spacing";
           }
           enum "1602.26" {
             description "1602.26 nm/187.106250 THz 3.125/6.25GHz spacing";
           }
           enum "1602.23" {
             description "1602.23 nm/187.109375 THz 3.125GHz spacing";
           }
           enum "1602.20" {
             description "1602.20 nm/187.112500 THz 3.125/6.25/12.5GHz spacing";
           }
           enum "1602.18" {
             description "1602.18 nm/187.115625 THz 3.125GHz spacing";
           }
           enum "1602.15" {
             description "1602.15 nm/187.118750 THz 3.125/6.25GHz spacing";
           }
           enum "1602.12" {
             description "1602.12 nm/187.121875 THz 3.125GHz spacing";
           }
           enum "1602.10" {
             description "1602.10 nm/187.125000 THz 3.125/6.25/12.5GHz spacing";
           }
           enum "1602.07" {
             description "1602.07 nm/187.128125 THz 3.125GHz spacing";
           }
           enum "1602.04" {
             description "1602.04 nm/187.131250 THz 3.125/6.25GHz spacing";
           }
           enum "1602.02" {
             description "1602.02 nm/187.134375 THz 3.125GHz spacing";
           }
           enum "1601.99" {
             description "1601.99 nm/187.137500 THz 3.125/6.25/12.5GHz spacing";
           }
           enum "1601.96" {
             description "1601.96 nm/187.140625 THz 3.125GHz spacing";
           }
           enum "1601.94" {
             description "1601.94 nm/187.143750 THz 3.125/6.25GHz spacing";
           }
           enum "1601.91" {
             description "1601.91 nm/187.146875 THz 3.125GHz spacing";
           }
           enum "1601.88" {
             description "1601.88 nm/187.150000 THz 3.125/6.25/12.5/50GHz spacing";
           }
           enum "1601.86" {
             description "1601.86 nm/187.153125 THz 3.125GHz spacing";
           }
           enum "1601.83" {
             description "1601.83 nm/187.156250 THz 3.125/6.25GHz spacing";
           }
           enum "1601.80" {
             description "1601.80 nm/187.159375 THz 3.125GHz spacing";
           }
           enum "1601.78" {
             description "1601.78 nm/187.162500 THz 3.125/6.25/12.5GHz spacing";
           }
           enum "1601.75" {
             description "1601.75 nm/187.165625 THz 3.125GHz spacing";
           }
           enum "1601.72" {
             description "1601.72 nm/187.168750 THz 3.125/6.25GHz spacing";
           }
           enum "1601.70" {
             description "1601.70 nm/187.171875 THz 3.125GHz spacing";
           }
           enum "1601.67" {
             description "1601.67 nm/187.175000 THz 3.125/6.25/12.5/75GHz spacing";
           }
           enum "1601.64" {
             description "1601.64 nm/187.178125 THz 3.125GHz spacing";
           }
           enum "1601.62" {
             description "1601.62 nm/187.181250 THz 3.125/6.25GHz spacing";
           }
           enum "1601.59" {
             description "1601.59 nm/187.184375 THz 3.125GHz spacing";
           }
           enum "1601.56" {
             description "1601.56 nm/187.187500 THz 3.125/6.25/12.5GHz spacing";
           }
           enum "1601.54" {
             description "1601.54 nm/187.190625 THz 3.125GHz spacing";
           }
           enum "1601.51" {
             description "1601.51 nm/187.193750 THz 3.125/6.25GHz spacing";
           }
           enum "1601.48" {
             description "1601.48 nm/187.196875 THz 3.125GHz spacing";
           }
           enum "1601.46" {
             description "1601.46 nm/187.200000 THz 3.125/6.25/12.5/50/75/100GHz spacing";
           }
           enum "1601.43" {
             description "1601.43 nm/187.203125 THz 3.125GHz spacing";
           }
           enum "1601.40" {
             description "1601.40 nm/187.206250 THz 3.125/6.25GHz spacing";
           }
           enum "1601.38" {
             description "1601.38 nm/187.209375 THz 3.125GHz spacing";
           }
           enum "1601.35" {
             description "1601.35 nm/187.212500 THz 3.125/6.25/12.5GHz spacing";
           }
           enum "1601.32" {
             description "1601.32 nm/187.215625 THz 3.125GHz spacing";
           }
           enum "1601.30" {
             description "1601.30 nm/187.218750 THz 3.125/6.25GHz spacing";
           }
           enum "1601.27" {
             description "1601.27 nm/187.221875 THz 3.125GHz spacing";
           }
           enum "1601.24" {
             description "1601.24 nm/187.225000 THz 3.125/6.25/12.5GHz spacing";
           }
           enum "1601.21" {
             description "1601.21 nm/187.228125 THz 3.125GHz spacing";
           }
           enum "1601.19" {
             description "1601.19 nm/187.231250 THz 3.125/6.25GHz spacing";
           }
           enum "1601.16" {
             description "1601.16 nm/187.234375 THz 3.125GHz spacing";
           }
           enum "1601.13" {
             description "1601.13 nm/187.237500 THz 3.125/6.25/12.5GHz spacing";
           }
           enum "1601.11" {
             description "1601.11 nm/187.240625 THz 3.125GHz spacing";
           }
           enum "1601.08" {
             description "1601.08 nm/187.243750 THz 3.125/6.25GHz spacing";
           }
           enum "1601.05" {
             description "1601.05 nm/187.246875 THz 3.125GHz spacing";
           }
           enum "1601.03" {
             description "1601.03 nm/187.250000 THz 3.125/6.25/12.5/50/75GHz spacing";
           }
           enum "1601.00" {
             description "1601.00 nm/187.253125 THz 3.125GHz spacing";
           }
           enum "1600.97" {
             description "1600.97 nm/187.256250 THz 3.125/6.25GHz spacing";
           }
           enum "1600.95" {
             description "1600.95 nm/187.259375 THz 3.125GHz spacing";
           }
           enum "1600.92" {
             description "1600.92 nm/187.262500 THz 3.125/6.25/12.5GHz spacing";
           }
           enum "1600.89" {
             description "1600.89 nm/187.265625 THz 3.125GHz spacing";
           }
           enum "1600.87" {
             description "1600.87 nm/187.268750 THz 3.125/6.25GHz spacing";
           }
           enum "1600.84" {
             description "1600.84 nm/187.271875 THz 3.125GHz spacing";
           }
           enum "1600.81" {
             description "1600.81 nm/187.275000 THz 3.125/6.25/12.5GHz spacing";
           }
           enum "1600.79" {
             description "1600.79 nm/187.278125 THz 3.125GHz spacing";
           }
           enum "1600.76" {
             description "1600.76 nm/187.281250 THz 3.125/6.25GHz spacing";
           }
           enum "1600.73" {
             description "1600.73 nm/187.284375 THz 3.125GHz spacing";
           }
           enum "1600.71" {
             description "1600.71 nm/187.287500 THz 3.125/6.25/12.5GHz spacing";
           }
           enum "1600.68" {
             description "1600.68 nm/187.290625 THz 3.125GHz spacing";
           }
           enum "1600.65" {
             description "1600.65 nm/187.293750 THz 3.125/6.25GHz spacing";
           }
           enum "1600.63" {
             description "1600.63 nm/187.296875 THz 3.125GHz spacing";
           }
           enum "1600.60" {
             description "1600.60 nm/187.300000 THz 3.125/6.25/12.5/100GHz spacing";
           }
           enum "1600.57" {
             description "1600.57 nm/187.303125 THz 3.125GHz spacing";
           }
           enum "1600.55" {
             description "1600.55 nm/187.306250 THz 3.125/6.25GHz spacing";
           }
           enum "1600.52" {
             description "1600.52 nm/187.309375 THz 3.125GHz spacing";
           }
           enum "1600.49" {
             description "1600.49 nm/187.312500 THz 3.125/6.25/12.5GHz spacing";
           }
           enum "1600.47" {
             description "1600.47 nm/187.315625 THz 3.125GHz spacing";
           }
           enum "1600.44" {
             description "1600.44 nm/187.318750 THz 3.125/6.25GHz spacing";
           }
           enum "1600.41" {
             description "1600.41 nm/187.321875 THz 3.125GHz spacing";
           }
           enum "1600.39" {
             description "1600.39 nm/187.325000 THz 3.125/6.25/12.5/75GHz spacing";
           }
           enum "1600.36" {
             description "1600.36 nm/187.328125 THz 3.125GHz spacing";
           }
           enum "1600.33" {
             description "1600.33 nm/187.331250 THz 3.125/6.25GHz spacing";
           }
           enum "1600.31" {
             description "1600.31 nm/187.334375 THz 3.125GHz spacing";
           }
           enum "1600.28" {
             description "1600.28 nm/187.337500 THz 3.125/6.25/12.5GHz spacing";
           }
           enum "1600.25" {
             description "1600.25 nm/187.340625 THz 3.125GHz spacing";
           }
           enum "1600.23" {
             description "1600.23 nm/187.343750 THz 3.125/6.25GHz spacing";
           }
           enum "1600.20" {
             description "1600.20 nm/187.346875 THz 3.125GHz spacing";
           }
           enum "1600.17" {
             description "1600.17 nm/187.350000 THz 3.125/6.25/12.5/50GHz spacing";
           }
           enum "1600.15" {
             description "1600.15 nm/187.353125 THz 3.125GHz spacing";
           }
           enum "1600.12" {
             description "1600.12 nm/187.356250 THz 3.125/6.25GHz spacing";
           }
           enum "1600.09" {
             description "1600.09 nm/187.359375 THz 3.125GHz spacing";
           }
           enum "1600.07" {
             description "1600.07 nm/187.362500 THz 3.125/6.25/12.5GHz spacing";
           }
           enum "1600.04" {
             description "1600.04 nm/187.365625 THz 3.125GHz spacing";
           }
           enum "1600.01" {
             description "1600.01 nm/187.368750 THz 3.125/6.25GHz spacing";
           }
           enum "1599.99" {
             description "1599.99 nm/187.371875 THz 3.125GHz spacing";
           }
           enum "1599.96" {
             description "1599.96 nm/187.375000 THz 3.125/6.25/12.5GHz spacing";
           }
           enum "1599.93" {
             description "1599.93 nm/187.378125 THz 3.125GHz spacing";
           }
           enum "1599.91" {
             description "1599.91 nm/187.381250 THz 3.125/6.25GHz spacing";
           }
           enum "1599.88" {
             description "1599.88 nm/187.384375 THz 3.125GHz spacing";
           }
           enum "1599.85" {
             description "1599.85 nm/187.387500 THz 3.125/6.25/12.5GHz spacing";
           }
           enum "1599.83" {
             description "1599.83 nm/187.390625 THz 3.125GHz spacing";
           }
           enum "1599.80" {
             description "1599.80 nm/187.393750 THz 3.125/6.25GHz spacing";
           }
           enum "1599.77" {
             description "1599.77 nm/187.396875 THz 3.125GHz spacing";
           }
           enum "1599.75" {
             description "1599.75 nm/187.400000 THz 3.125/6.25/12.5/100GHz spacing";
           }
           enum "1599.72" {
             description "1599.72 nm/187.403125 THz 3.125GHz spacing";
           }
           enum "1599.69" {
             description "1599.69 nm/187.406250 THz 3.125/6.25GHz spacing";
           }
           enum "1599.67" {
             description "1599.67 nm/187.409375 THz 3.125GHz spacing";
           }
           enum "1599.64" {
             description "1599.64 nm/187.412500 THz 3.125/6.25/12.5GHz spacing";
           }
           enum "1599.61" {
             description "1599.61 nm/187.415625 THz 3.125GHz spacing";
           }
           enum "1599.59" {
             description "1599.59 nm/187.418750 THz 3.125/6.25GHz spacing";
           }
           enum "1599.56" {
             description "1599.56 nm/187.421875 THz 3.125GHz spacing";
           }
           enum "1599.53" {
             description "1599.53 nm/187.425000 THz 3.125/6.25/12.5GHz spacing";
           }
           enum "1599.51" {
             description "1599.51 nm/187.428125 THz 3.125GHz spacing";
           }
           enum "1599.48" {
             description "1599.48 nm/187.431250 THz 3.125/6.25GHz spacing";
           }
           enum "1599.45" {
             description "1599.45 nm/187.434375 THz 3.125GHz spacing";
           }
           enum "1599.43" {
             description "1599.43 nm/187.437500 THz 3.125/6.25/12.5GHz spacing";
           }
           enum "1599.40" {
             description "1599.40 nm/187.440625 THz 3.125GHz spacing";
           }
           enum "1599.37" {
             description "1599.37 nm/187.443750 THz 3.125/6.25GHz spacing";
           }
           enum "1599.35" {
             description "1599.35 nm/187.446875 THz 3.125GHz spacing";
           }
           enum "1599.32" {
             description "1599.32 nm/187.450000 THz 3.125/6.25/12.5/50GHz spacing";
           }
           enum "1599.29" {
             description "1599.29 nm/187.453125 THz 3.125GHz spacing";
           }
           enum "1599.27" {
             description "1599.27 nm/187.456250 THz 3.125/6.25GHz spacing";
           }
           enum "1599.24" {
             description "1599.24 nm/187.459375 THz 3.125GHz spacing";
           }
           enum "1599.21" {
             description "1599.21 nm/187.462500 THz 3.125/6.25/12.5GHz spacing";
           }
           enum "1599.19" {
             description "1599.19 nm/187.465625 THz 3.125GHz spacing";
           }
           enum "1599.16" {
             description "1599.16 nm/187.468750 THz 3.125/6.25GHz spacing";
           }
           enum "1599.13" {
             description "1599.13 nm/187.471875 THz 3.125GHz spacing";
           }
           enum "1599.11" {
             description "1599.11 nm/187.475000 THz 3.125/6.25/12.5/75GHz spacing";
           }
           enum "1599.08" {
             description "1599.08 nm/187.478125 THz 3.125GHz spacing";
           }
           enum "1599.05" {
             description "1599.05 nm/187.481250 THz 3.125/6.25GHz spacing";
           }
           enum "1599.03" {
             description "1599.03 nm/187.484375 THz 3.125GHz spacing";
           }
           enum "1599.00" {
             description "1599.00 nm/187.487500 THz 3.125/6.25/12.5GHz spacing";
           }
           enum "1598.97" {
             description "1598.97 nm/187.490625 THz 3.125GHz spacing";
           }
           enum "1598.95" {
             description "1598.95 nm/187.493750 THz 3.125/6.25GHz spacing";
           }
           enum "1598.92" {
             description "1598.92 nm/187.496875 THz 3.125GHz spacing";
           }
           enum "1598.89" {
             description "1598.89 nm/187.500000 THz 3.125/6.25/12.5/50/75/100GHz spacing";
           }
           enum "1598.87" {
             description "1598.87 nm/187.503125 THz 3.125GHz spacing";
           }
           enum "1598.84" {
             description "1598.84 nm/187.506250 THz 3.125/6.25GHz spacing";
           }
           enum "1598.81" {
             description "1598.81 nm/187.509375 THz 3.125GHz spacing";
           }
           enum "1598.79" {
             description "1598.79 nm/187.512500 THz 3.125/6.25/12.5GHz spacing";
           }
           enum "1598.76" {
             description "1598.76 nm/187.515625 THz 3.125GHz spacing";
           }
           enum "1598.73" {
             description "1598.73 nm/187.518750 THz 3.125/6.25GHz spacing";
           }
           enum "1598.71" {
             description "1598.71 nm/187.521875 THz 3.125GHz spacing";
           }
           enum "1598.68" {
             description "1598.68 nm/187.525000 THz 3.125/6.25/12.5GHz spacing";
           }
           enum "1598.65" {
             description "1598.65 nm/187.528125 THz 3.125GHz spacing";
           }
           enum "1598.63" {
             description "1598.63 nm/187.531250 THz 3.125/6.25GHz spacing";
           }
           enum "1598.60" {
             description "1598.60 nm/187.534375 THz 3.125GHz spacing";
           }
           enum "1598.57" {
             description "1598.57 nm/187.537500 THz 3.125/6.25/12.5GHz spacing";
           }
           enum "1598.55" {
             description "1598.55 nm/187.540625 THz 3.125GHz spacing";
           }
           enum "1598.52" {
             description "1598.52 nm/187.543750 THz 3.125/6.25GHz spacing";
           }
           enum "1598.49" {
             description "1598.49 nm/187.546875 THz 3.125GHz spacing";
           }
           enum "1598.47" {
             description "1598.47 nm/187.550000 THz 3.125/6.25/12.5/50/75GHz spacing";
           }
           enum "1598.44" {
             description "1598.44 nm/187.553125 THz 3.125GHz spacing";
           }
           enum "1598.41" {
             description "1598.41 nm/187.556250 THz 3.125/6.25GHz spacing";
           }
           enum "1598.39" {
             description "1598.39 nm/187.559375 THz 3.125GHz spacing";
           }
           enum "1598.36" {
             description "1598.36 nm/187.562500 THz 3.125/6.25/12.5GHz spacing";
           }
           enum "1598.33" {
             description "1598.33 nm/187.565625 THz 3.125GHz spacing";
           }
           enum "1598.31" {
             description "1598.31 nm/187.568750 THz 3.125/6.25GHz spacing";
           }
           enum "1598.28" {
             description "1598.28 nm/187.571875 THz 3.125GHz spacing";
           }
           enum "1598.25" {
             description "1598.25 nm/187.575000 THz 3.125/6.25/12.5GHz spacing";
           }
           enum "1598.23" {
             description "1598.23 nm/187.578125 THz 3.125GHz spacing";
           }
           enum "1598.20" {
             description "1598.20 nm/187.581250 THz 3.125/6.25GHz spacing";
           }
           enum "1598.17" {
             description "1598.17 nm/187.584375 THz 3.125GHz spacing";
           }
           enum "1598.15" {
             description "1598.15 nm/187.587500 THz 3.125/6.25/12.5GHz spacing";
           }
           enum "1598.12" {
             description "1598.12 nm/187.590625 THz 3.125GHz spacing";
           }
           enum "1598.09" {
             description "1598.09 nm/187.593750 THz 3.125/6.25GHz spacing";
           }
           enum "1598.07" {
             description "1598.07 nm/187.596875 THz 3.125GHz spacing";
           }
           enum "1598.04" {
             description "1598.04 nm/187.600000 THz 3.125/6.25/12.5/100GHz spacing";
           }
           enum "1598.01" {
             description "1598.01 nm/187.603125 THz 3.125GHz spacing";
           }
           enum "1597.99" {
             description "1597.99 nm/187.606250 THz 3.125/6.25GHz spacing";
           }
           enum "1597.96" {
             description "1597.96 nm/187.609375 THz 3.125GHz spacing";
           }
           enum "1597.93" {
             description "1597.93 nm/187.612500 THz 3.125/6.25/12.5GHz spacing";
           }
           enum "1597.91" {
             description "1597.91 nm/187.615625 THz 3.125GHz spacing";
           }
           enum "1597.88" {
             description "1597.88 nm/187.618750 THz 3.125/6.25GHz spacing";
           }
           enum "1597.85" {
             description "1597.85 nm/187.621875 THz 3.125GHz spacing";
           }
           enum "1597.83" {
             description "1597.83 nm/187.625000 THz 3.125/6.25/12.5/75GHz spacing";
           }
           enum "1597.80" {
             description "1597.80 nm/187.628125 THz 3.125GHz spacing";
           }
           enum "1597.77" {
             description "1597.77 nm/187.631250 THz 3.125/6.25GHz spacing";
           }
           enum "1597.75" {
             description "1597.75 nm/187.634375 THz 3.125GHz spacing";
           }
           enum "1597.72" {
             description "1597.72 nm/187.637500 THz 3.125/6.25/12.5GHz spacing";
           }
           enum "1597.69" {
             description "1597.69 nm/187.640625 THz 3.125GHz spacing";
           }
           enum "1597.67" {
             description "1597.67 nm/187.643750 THz 3.125/6.25GHz spacing";
           }
           enum "1597.64" {
             description "1597.64 nm/187.646875 THz 3.125GHz spacing";
           }
           enum "1597.62" {
             description "1597.62 nm/187.650000 THz 3.125/6.25/12.5/50GHz spacing";
           }
           enum "1597.59" {
             description "1597.59 nm/187.653125 THz 3.125GHz spacing";
           }
           enum "1597.56" {
             description "1597.56 nm/187.656250 THz 3.125/6.25GHz spacing";
           }
           enum "1597.54" {
             description "1597.54 nm/187.659375 THz 3.125GHz spacing";
           }
           enum "1597.51" {
             description "1597.51 nm/187.662500 THz 3.125/6.25/12.5GHz spacing";
           }
           enum "1597.48" {
             description "1597.48 nm/187.665625 THz 3.125GHz spacing";
           }
           enum "1597.46" {
             description "1597.46 nm/187.668750 THz 3.125/6.25GHz spacing";
           }
           enum "1597.43" {
             description "1597.43 nm/187.671875 THz 3.125GHz spacing";
           }
           enum "1597.40" {
             description "1597.40 nm/187.675000 THz 3.125/6.25/12.5GHz spacing";
           }
           enum "1597.38" {
             description "1597.38 nm/187.678125 THz 3.125GHz spacing";
           }
           enum "1597.35" {
             description "1597.35 nm/187.681250 THz 3.125/6.25GHz spacing";
           }
           enum "1597.32" {
             description "1597.32 nm/187.684375 THz 3.125GHz spacing";
           }
           enum "1597.30" {
             description "1597.30 nm/187.687500 THz 3.125/6.25/12.5GHz spacing";
           }
           enum "1597.27" {
             description "1597.27 nm/187.690625 THz 3.125GHz spacing";
           }
           enum "1597.24" {
             description "1597.24 nm/187.693750 THz 3.125/6.25GHz spacing";
           }
           enum "1597.22" {
             description "1597.22 nm/187.696875 THz 3.125GHz spacing";
           }
           enum "1597.19" {
             description "1597.19 nm/187.700000 THz 3.125/6.25/12.5/100GHz spacing";
           }
           enum "1597.16" {
             description "1597.16 nm/187.703125 THz 3.125GHz spacing";
           }
           enum "1597.14" {
             description "1597.14 nm/187.706250 THz 3.125/6.25GHz spacing";
           }
           enum "1597.11" {
             description "1597.11 nm/187.709375 THz 3.125GHz spacing";
           }
           enum "1597.08" {
             description "1597.08 nm/187.712500 THz 3.125/6.25/12.5GHz spacing";
           }
           enum "1597.06" {
             description "1597.06 nm/187.715625 THz 3.125GHz spacing";
           }
           enum "1597.03" {
             description "1597.03 nm/187.718750 THz 3.125/6.25GHz spacing";
           }
           enum "1597.00" {
             description "1597.00 nm/187.721875 THz 3.125GHz spacing";
           }
           enum "1596.98" {
             description "1596.98 nm/187.725000 THz 3.125/6.25/12.5GHz spacing";
           }
           enum "1596.95" {
             description "1596.95 nm/187.728125 THz 3.125GHz spacing";
           }
           enum "1596.92" {
             description "1596.92 nm/187.731250 THz 3.125/6.25GHz spacing";
           }
           enum "1596.90" {
             description "1596.90 nm/187.734375 THz 3.125GHz spacing";
           }
           enum "1596.87" {
             description "1596.87 nm/187.737500 THz 3.125/6.25/12.5GHz spacing";
           }
           enum "1596.84" {
             description "1596.84 nm/187.740625 THz 3.125GHz spacing";
           }
           enum "1596.82" {
             description "1596.82 nm/187.743750 THz 3.125/6.25GHz spacing";
           }
           enum "1596.79" {
             description "1596.79 nm/187.746875 THz 3.125GHz spacing";
           }
           enum "1596.76" {
             description "1596.76 nm/187.750000 THz 3.125/6.25/12.5/50GHz spacing";
           }
           enum "1596.74" {
             description "1596.74 nm/187.753125 THz 3.125GHz spacing";
           }
           enum "1596.71" {
             description "1596.71 nm/187.756250 THz 3.125/6.25GHz spacing";
           }
           enum "1596.68" {
             description "1596.68 nm/187.759375 THz 3.125GHz spacing";
           }
           enum "1596.66" {
             description "1596.66 nm/187.762500 THz 3.125/6.25/12.5GHz spacing";
           }
           enum "1596.63" {
             description "1596.63 nm/187.765625 THz 3.125GHz spacing";
           }
           enum "1596.60" {
             description "1596.60 nm/187.768750 THz 3.125/6.25GHz spacing";
           }
           enum "1596.58" {
             description "1596.58 nm/187.771875 THz 3.125GHz spacing";
           }
           enum "1596.55" {
             description "1596.55 nm/187.775000 THz 3.125/6.25/12.5/75GHz spacing";
           }
           enum "1596.52" {
             description "1596.52 nm/187.778125 THz 3.125GHz spacing";
           }
           enum "1596.50" {
             description "1596.50 nm/187.781250 THz 3.125/6.25GHz spacing";
           }
           enum "1596.47" {
             description "1596.47 nm/187.784375 THz 3.125GHz spacing";
           }
           enum "1596.45" {
             description "1596.45 nm/187.787500 THz 3.125/6.25/12.5GHz spacing";
           }
           enum "1596.42" {
             description "1596.42 nm/187.790625 THz 3.125GHz spacing";
           }
           enum "1596.39" {
             description "1596.39 nm/187.793750 THz 3.125/6.25GHz spacing";
           }
           enum "1596.37" {
             description "1596.37 nm/187.796875 THz 3.125GHz spacing";
           }
           enum "1596.34" {
             description "1596.34 nm/187.800000 THz 3.125/6.25/12.5/50/75/100GHz spacing";
           }
           enum "1596.31" {
             description "1596.31 nm/187.803125 THz 3.125GHz spacing";
           }
           enum "1596.29" {
             description "1596.29 nm/187.806250 THz 3.125/6.25GHz spacing";
           }
           enum "1596.26" {
             description "1596.26 nm/187.809375 THz 3.125GHz spacing";
           }
           enum "1596.23" {
             description "1596.23 nm/187.812500 THz 3.125/6.25/12.5GHz spacing";
           }
           enum "1596.21" {
             description "1596.21 nm/187.815625 THz 3.125GHz spacing";
           }
           enum "1596.18" {
             description "1596.18 nm/187.818750 THz 3.125/6.25GHz spacing";
           }
           enum "1596.15" {
             description "1596.15 nm/187.821875 THz 3.125GHz spacing";
           }
           enum "1596.13" {
             description "1596.13 nm/187.825000 THz 3.125/6.25/12.5GHz spacing";
           }
           enum "1596.10" {
             description "1596.10 nm/187.828125 THz 3.125GHz spacing";
           }
           enum "1596.07" {
             description "1596.07 nm/187.831250 THz 3.125/6.25GHz spacing";
           }
           enum "1596.05" {
             description "1596.05 nm/187.834375 THz 3.125GHz spacing";
           }
           enum "1596.02" {
             description "1596.02 nm/187.837500 THz 3.125/6.25/12.5GHz spacing";
           }
           enum "1595.99" {
             description "1595.99 nm/187.840625 THz 3.125GHz spacing";
           }
           enum "1595.97" {
             description "1595.97 nm/187.843750 THz 3.125/6.25GHz spacing";
           }
           enum "1595.94" {
             description "1595.94 nm/187.846875 THz 3.125GHz spacing";
           }
           enum "1595.91" {
             description "1595.91 nm/187.850000 THz 3.125/6.25/12.5/50/75GHz spacing";
           }
           enum "1595.89" {
             description "1595.89 nm/187.853125 THz 3.125GHz spacing";
           }
           enum "1595.86" {
             description "1595.86 nm/187.856250 THz 3.125/6.25GHz spacing";
           }
           enum "1595.83" {
             description "1595.83 nm/187.859375 THz 3.125GHz spacing";
           }
           enum "1595.81" {
             description "1595.81 nm/187.862500 THz 3.125/6.25/12.5GHz spacing";
           }
           enum "1595.78" {
             description "1595.78 nm/187.865625 THz 3.125GHz spacing";
           }
           enum "1595.75" {
             description "1595.75 nm/187.868750 THz 3.125/6.25GHz spacing";
           }
           enum "1595.73" {
             description "1595.73 nm/187.871875 THz 3.125GHz spacing";
           }
           enum "1595.70" {
             description "1595.70 nm/187.875000 THz 3.125/6.25/12.5GHz spacing";
           }
           enum "1595.68" {
             description "1595.68 nm/187.878125 THz 3.125GHz spacing";
           }
           enum "1595.65" {
             description "1595.65 nm/187.881250 THz 3.125/6.25GHz spacing";
           }
           enum "1595.62" {
             description "1595.62 nm/187.884375 THz 3.125GHz spacing";
           }
           enum "1595.60" {
             description "1595.60 nm/187.887500 THz 3.125/6.25/12.5GHz spacing";
           }
           enum "1595.57" {
             description "1595.57 nm/187.890625 THz 3.125GHz spacing";
           }
           enum "1595.54" {
             description "1595.54 nm/187.893750 THz 3.125/6.25GHz spacing";
           }
           enum "1595.52" {
             description "1595.52 nm/187.896875 THz 3.125GHz spacing";
           }
           enum "1595.49" {
             description "1595.49 nm/187.900000 THz 3.125/6.25/12.5/100GHz spacing";
           }
           enum "1595.46" {
             description "1595.46 nm/187.903125 THz 3.125GHz spacing";
           }
           enum "1595.44" {
             description "1595.44 nm/187.906250 THz 3.125/6.25GHz spacing";
           }
           enum "1595.41" {
             description "1595.41 nm/187.909375 THz 3.125GHz spacing";
           }
           enum "1595.38" {
             description "1595.38 nm/187.912500 THz 3.125/6.25/12.5GHz spacing";
           }
           enum "1595.36" {
             description "1595.36 nm/187.915625 THz 3.125GHz spacing";
           }
           enum "1595.33" {
             description "1595.33 nm/187.918750 THz 3.125/6.25GHz spacing";
           }
           enum "1595.30" {
             description "1595.30 nm/187.921875 THz 3.125GHz spacing";
           }
           enum "1595.28" {
             description "1595.28 nm/187.925000 THz 3.125/6.25/12.5/75GHz spacing";
           }
           enum "1595.25" {
             description "1595.25 nm/187.928125 THz 3.125GHz spacing";
           }
           enum "1595.22" {
             description "1595.22 nm/187.931250 THz 3.125/6.25GHz spacing";
           }
           enum "1595.20" {
             description "1595.20 nm/187.934375 THz 3.125GHz spacing";
           }
           enum "1595.17" {
             description "1595.17 nm/187.937500 THz 3.125/6.25/12.5GHz spacing";
           }
           enum "1595.14" {
             description "1595.14 nm/187.940625 THz 3.125GHz spacing";
           }
           enum "1595.12" {
             description "1595.12 nm/187.943750 THz 3.125/6.25GHz spacing";
           }
           enum "1595.09" {
             description "1595.09 nm/187.946875 THz 3.125GHz spacing";
           }
           enum "1595.06" {
             description "1595.06 nm/187.950000 THz 3.125/6.25/12.5/50GHz spacing";
           }
           enum "1595.04" {
             description "1595.04 nm/187.953125 THz 3.125GHz spacing";
           }
           enum "1595.01" {
             description "1595.01 nm/187.956250 THz 3.125/6.25GHz spacing";
           }
           enum "1594.99" {
             description "1594.99 nm/187.959375 THz 3.125GHz spacing";
           }
           enum "1594.96" {
             description "1594.96 nm/187.962500 THz 3.125/6.25/12.5GHz spacing";
           }
           enum "1594.93" {
             description "1594.93 nm/187.965625 THz 3.125GHz spacing";
           }
           enum "1594.91" {
             description "1594.91 nm/187.968750 THz 3.125/6.25GHz spacing";
           }
           enum "1594.88" {
             description "1594.88 nm/187.971875 THz 3.125GHz spacing";
           }
           enum "1594.85" {
             description "1594.85 nm/187.975000 THz 3.125/6.25/12.5GHz spacing";
           }
           enum "1594.83" {
             description "1594.83 nm/187.978125 THz 3.125GHz spacing";
           }
           enum "1594.80" {
             description "1594.80 nm/187.981250 THz 3.125/6.25GHz spacing";
           }
           enum "1594.77" {
             description "1594.77 nm/187.984375 THz 3.125GHz spacing";
           }
           enum "1594.75" {
             description "1594.75 nm/187.987500 THz 3.125/6.25/12.5GHz spacing";
           }
           enum "1594.72" {
             description "1594.72 nm/187.990625 THz 3.125GHz spacing";
           }
           enum "1594.69" {
             description "1594.69 nm/187.993750 THz 3.125/6.25GHz spacing";
           }
           enum "1594.67" {
             description "1594.67 nm/187.996875 THz 3.125GHz spacing";
           }
           enum "1594.64" {
             description "1594.64 nm/188.000000 THz 3.125/6.25/12.5/100GHz spacing";
           }
           enum "1594.61" {
             description "1594.61 nm/188.003125 THz 3.125GHz spacing";
           }
           enum "1594.59" {
             description "1594.59 nm/188.006250 THz 3.125/6.25GHz spacing";
           }
           enum "1594.56" {
             description "1594.56 nm/188.009375 THz 3.125GHz spacing";
           }
           enum "1594.53" {
             description "1594.53 nm/188.012500 THz 3.125/6.25/12.5GHz spacing";
           }
           enum "1594.51" {
             description "1594.51 nm/188.015625 THz 3.125GHz spacing";
           }
           enum "1594.48" {
             description "1594.48 nm/188.018750 THz 3.125/6.25GHz spacing";
           }
           enum "1594.46" {
             description "1594.46 nm/188.021875 THz 3.125GHz spacing";
           }
           enum "1594.43" {
             description "1594.43 nm/188.025000 THz 3.125/6.25/12.5GHz spacing";
           }
           enum "1594.40" {
             description "1594.40 nm/188.028125 THz 3.125GHz spacing";
           }
           enum "1594.38" {
             description "1594.38 nm/188.031250 THz 3.125/6.25GHz spacing";
           }
           enum "1594.35" {
             description "1594.35 nm/188.034375 THz 3.125GHz spacing";
           }
           enum "1594.32" {
             description "1594.32 nm/188.037500 THz 3.125/6.25/12.5GHz spacing";
           }
           enum "1594.30" {
             description "1594.30 nm/188.040625 THz 3.125GHz spacing";
           }
           enum "1594.27" {
             description "1594.27 nm/188.043750 THz 3.125/6.25GHz spacing";
           }
           enum "1594.24" {
             description "1594.24 nm/188.046875 THz 3.125GHz spacing";
           }
           enum "1594.22" {
             description "1594.22 nm/188.050000 THz 3.125/6.25/12.5/50GHz spacing";
           }
           enum "1594.19" {
             description "1594.19 nm/188.053125 THz 3.125GHz spacing";
           }
           enum "1594.16" {
             description "1594.16 nm/188.056250 THz 3.125/6.25GHz spacing";
           }
           enum "1594.14" {
             description "1594.14 nm/188.059375 THz 3.125GHz spacing";
           }
           enum "1594.11" {
             description "1594.11 nm/188.062500 THz 3.125/6.25/12.5GHz spacing";
           }
           enum "1594.08" {
             description "1594.08 nm/188.065625 THz 3.125GHz spacing";
           }
           enum "1594.06" {
             description "1594.06 nm/188.068750 THz 3.125/6.25GHz spacing";
           }
           enum "1594.03" {
             description "1594.03 nm/188.071875 THz 3.125GHz spacing";
           }
           enum "1594.00" {
             description "1594.00 nm/188.075000 THz 3.125/6.25/12.5/75GHz spacing";
           }
           enum "1593.98" {
             description "1593.98 nm/188.078125 THz 3.125GHz spacing";
           }
           enum "1593.95" {
             description "1593.95 nm/188.081250 THz 3.125/6.25GHz spacing";
           }
           enum "1593.93" {
             description "1593.93 nm/188.084375 THz 3.125GHz spacing";
           }
           enum "1593.90" {
             description "1593.90 nm/188.087500 THz 3.125/6.25/12.5GHz spacing";
           }
           enum "1593.87" {
             description "1593.87 nm/188.090625 THz 3.125GHz spacing";
           }
           enum "1593.85" {
             description "1593.85 nm/188.093750 THz 3.125/6.25GHz spacing";
           }
           enum "1593.82" {
             description "1593.82 nm/188.096875 THz 3.125GHz spacing";
           }
           enum "1593.79" {
             description "1593.79 nm/188.100000 THz 3.125/6.25/12.5/50/75/100GHz spacing";
           }
           enum "1593.77" {
             description "1593.77 nm/188.103125 THz 3.125GHz spacing";
           }
           enum "1593.74" {
             description "1593.74 nm/188.106250 THz 3.125/6.25GHz spacing";
           }
           enum "1593.71" {
             description "1593.71 nm/188.109375 THz 3.125GHz spacing";
           }
           enum "1593.69" {
             description "1593.69 nm/188.112500 THz 3.125/6.25/12.5GHz spacing";
           }
           enum "1593.66" {
             description "1593.66 nm/188.115625 THz 3.125GHz spacing";
           }
           enum "1593.63" {
             description "1593.63 nm/188.118750 THz 3.125/6.25GHz spacing";
           }
           enum "1593.61" {
             description "1593.61 nm/188.121875 THz 3.125GHz spacing";
           }
           enum "1593.58" {
             description "1593.58 nm/188.125000 THz 3.125/6.25/12.5GHz spacing";
           }
           enum "1593.55" {
             description "1593.55 nm/188.128125 THz 3.125GHz spacing";
           }
           enum "1593.53" {
             description "1593.53 nm/188.131250 THz 3.125/6.25GHz spacing";
           }
           enum "1593.50" {
             description "1593.50 nm/188.134375 THz 3.125GHz spacing";
           }
           enum "1593.48" {
             description "1593.48 nm/188.137500 THz 3.125/6.25/12.5GHz spacing";
           }
           enum "1593.45" {
             description "1593.45 nm/188.140625 THz 3.125GHz spacing";
           }
           enum "1593.42" {
             description "1593.42 nm/188.143750 THz 3.125/6.25GHz spacing";
           }
           enum "1593.40" {
             description "1593.40 nm/188.146875 THz 3.125GHz spacing";
           }
           enum "1593.37" {
             description "1593.37 nm/188.150000 THz 3.125/6.25/12.5/50/75GHz spacing";
           }
           enum "1593.34" {
             description "1593.34 nm/188.153125 THz 3.125GHz spacing";
           }
           enum "1593.32" {
             description "1593.32 nm/188.156250 THz 3.125/6.25GHz spacing";
           }
           enum "1593.29" {
             description "1593.29 nm/188.159375 THz 3.125GHz spacing";
           }
           enum "1593.26" {
             description "1593.26 nm/188.162500 THz 3.125/6.25/12.5GHz spacing";
           }
           enum "1593.24" {
             description "1593.24 nm/188.165625 THz 3.125GHz spacing";
           }
           enum "1593.21" {
             description "1593.21 nm/188.168750 THz 3.125/6.25GHz spacing";
           }
           enum "1593.18" {
             description "1593.18 nm/188.171875 THz 3.125GHz spacing";
           }
           enum "1593.16" {
             description "1593.16 nm/188.175000 THz 3.125/6.25/12.5GHz spacing";
           }
           enum "1593.13" {
             description "1593.13 nm/188.178125 THz 3.125GHz spacing";
           }
           enum "1593.10" {
             description "1593.10 nm/188.181250 THz 3.125/6.25GHz spacing";
           }
           enum "1593.08" {
             description "1593.08 nm/188.184375 THz 3.125GHz spacing";
           }
           enum "1593.05" {
             description "1593.05 nm/188.187500 THz 3.125/6.25/12.5GHz spacing";
           }
           enum "1593.03" {
             description "1593.03 nm/188.190625 THz 3.125GHz spacing";
           }
           enum "1593.00" {
             description "1593.00 nm/188.193750 THz 3.125/6.25GHz spacing";
           }
           enum "1592.97" {
             description "1592.97 nm/188.196875 THz 3.125GHz spacing";
           }
           enum "1592.95" {
             description "1592.95 nm/188.200000 THz 3.125/6.25/12.5/100GHz spacing";
           }
           enum "1592.92" {
             description "1592.92 nm/188.203125 THz 3.125GHz spacing";
           }
           enum "1592.89" {
             description "1592.89 nm/188.206250 THz 3.125/6.25GHz spacing";
           }
           enum "1592.87" {
             description "1592.87 nm/188.209375 THz 3.125GHz spacing";
           }
           enum "1592.84" {
             description "1592.84 nm/188.212500 THz 3.125/6.25/12.5GHz spacing";
           }
           enum "1592.81" {
             description "1592.81 nm/188.215625 THz 3.125GHz spacing";
           }
           enum "1592.79" {
             description "1592.79 nm/188.218750 THz 3.125/6.25GHz spacing";
           }
           enum "1592.76" {
             description "1592.76 nm/188.221875 THz 3.125GHz spacing";
           }
           enum "1592.73" {
             description "1592.73 nm/188.225000 THz 3.125/6.25/12.5/75GHz spacing";
           }
           enum "1592.71" {
             description "1592.71 nm/188.228125 THz 3.125GHz spacing";
           }
           enum "1592.68" {
             description "1592.68 nm/188.231250 THz 3.125/6.25GHz spacing";
           }
           enum "1592.66" {
             description "1592.66 nm/188.234375 THz 3.125GHz spacing";
           }
           enum "1592.63" {
             description "1592.63 nm/188.237500 THz 3.125/6.25/12.5GHz spacing";
           }
           enum "1592.60" {
             description "1592.60 nm/188.240625 THz 3.125GHz spacing";
           }
           enum "1592.58" {
             description "1592.58 nm/188.243750 THz 3.125/6.25GHz spacing";
           }
           enum "1592.55" {
             description "1592.55 nm/188.246875 THz 3.125GHz spacing";
           }
           enum "1592.52" {
             description "1592.52 nm/188.250000 THz 3.125/6.25/12.5/50GHz spacing";
           }
           enum "1592.50" {
             description "1592.50 nm/188.253125 THz 3.125GHz spacing";
           }
           enum "1592.47" {
             description "1592.47 nm/188.256250 THz 3.125/6.25GHz spacing";
           }
           enum "1592.44" {
             description "1592.44 nm/188.259375 THz 3.125GHz spacing";
           }
           enum "1592.42" {
             description "1592.42 nm/188.262500 THz 3.125/6.25/12.5GHz spacing";
           }
           enum "1592.39" {
             description "1592.39 nm/188.265625 THz 3.125GHz spacing";
           }
           enum "1592.36" {
             description "1592.36 nm/188.268750 THz 3.125/6.25GHz spacing";
           }
           enum "1592.34" {
             description "1592.34 nm/188.271875 THz 3.125GHz spacing";
           }
           enum "1592.31" {
             description "1592.31 nm/188.275000 THz 3.125/6.25/12.5GHz spacing";
           }
           enum "1592.29" {
             description "1592.29 nm/188.278125 THz 3.125GHz spacing";
           }
           enum "1592.26" {
             description "1592.26 nm/188.281250 THz 3.125/6.25GHz spacing";
           }
           enum "1592.23" {
             description "1592.23 nm/188.284375 THz 3.125GHz spacing";
           }
           enum "1592.21" {
             description "1592.21 nm/188.287500 THz 3.125/6.25/12.5GHz spacing";
           }
           enum "1592.18" {
             description "1592.18 nm/188.290625 THz 3.125GHz spacing";
           }
           enum "1592.15" {
             description "1592.15 nm/188.293750 THz 3.125/6.25GHz spacing";
           }
           enum "1592.13" {
             description "1592.13 nm/188.296875 THz 3.125GHz spacing";
           }
           enum "1592.10" {
             description "1592.10 nm/188.300000 THz 3.125/6.25/12.5/100GHz spacing";
           }
           enum "1592.07" {
             description "1592.07 nm/188.303125 THz 3.125GHz spacing";
           }
           enum "1592.05" {
             description "1592.05 nm/188.306250 THz 3.125/6.25GHz spacing";
           }
           enum "1592.02" {
             description "1592.02 nm/188.309375 THz 3.125GHz spacing";
           }
           enum "1591.99" {
             description "1591.99 nm/188.312500 THz 3.125/6.25/12.5GHz spacing";
           }
           enum "1591.97" {
             description "1591.97 nm/188.315625 THz 3.125GHz spacing";
           }
           enum "1591.94" {
             description "1591.94 nm/188.318750 THz 3.125/6.25GHz spacing";
           }
           enum "1591.92" {
             description "1591.92 nm/188.321875 THz 3.125GHz spacing";
           }
           enum "1591.89" {
             description "1591.89 nm/188.325000 THz 3.125/6.25/12.5GHz spacing";
           }
           enum "1591.86" {
             description "1591.86 nm/188.328125 THz 3.125GHz spacing";
           }
           enum "1591.84" {
             description "1591.84 nm/188.331250 THz 3.125/6.25GHz spacing";
           }
           enum "1591.81" {
             description "1591.81 nm/188.334375 THz 3.125GHz spacing";
           }
           enum "1591.78" {
             description "1591.78 nm/188.337500 THz 3.125/6.25/12.5GHz spacing";
           }
           enum "1591.76" {
             description "1591.76 nm/188.340625 THz 3.125GHz spacing";
           }
           enum "1591.73" {
             description "1591.73 nm/188.343750 THz 3.125/6.25GHz spacing";
           }
           enum "1591.70" {
             description "1591.70 nm/188.346875 THz 3.125GHz spacing";
           }
           enum "1591.68" {
             description "1591.68 nm/188.350000 THz 3.125/6.25/12.5/50GHz spacing";
           }
           enum "1591.65" {
             description "1591.65 nm/188.353125 THz 3.125GHz spacing";
           }
           enum "1591.62" {
             description "1591.62 nm/188.356250 THz 3.125/6.25GHz spacing";
           }
           enum "1591.60" {
             description "1591.60 nm/188.359375 THz 3.125GHz spacing";
           }
           enum "1591.57" {
             description "1591.57 nm/188.362500 THz 3.125/6.25/12.5GHz spacing";
           }
           enum "1591.55" {
             description "1591.55 nm/188.365625 THz 3.125GHz spacing";
           }
           enum "1591.52" {
             description "1591.52 nm/188.368750 THz 3.125/6.25GHz spacing";
           }
           enum "1591.49" {
             description "1591.49 nm/188.371875 THz 3.125GHz spacing";
           }
           enum "1591.47" {
             description "1591.47 nm/188.375000 THz 3.125/6.25/12.5/75GHz spacing";
           }
           enum "1591.44" {
             description "1591.44 nm/188.378125 THz 3.125GHz spacing";
           }
           enum "1591.41" {
             description "1591.41 nm/188.381250 THz 3.125/6.25GHz spacing";
           }
           enum "1591.39" {
             description "1591.39 nm/188.384375 THz 3.125GHz spacing";
           }
           enum "1591.36" {
             description "1591.36 nm/188.387500 THz 3.125/6.25/12.5GHz spacing";
           }
           enum "1591.33" {
             description "1591.33 nm/188.390625 THz 3.125GHz spacing";
           }
           enum "1591.31" {
             description "1591.31 nm/188.393750 THz 3.125/6.25GHz spacing";
           }
           enum "1591.28" {
             description "1591.28 nm/188.396875 THz 3.125GHz spacing";
           }
           enum "1591.26" {
             description "1591.26 nm/188.400000 THz 3.125/6.25/12.5/50/75/100GHz spacing";
           }
           enum "1591.23" {
             description "1591.23 nm/188.403125 THz 3.125GHz spacing";
           }
           enum "1591.20" {
             description "1591.20 nm/188.406250 THz 3.125/6.25GHz spacing";
           }
           enum "1591.18" {
             description "1591.18 nm/188.409375 THz 3.125GHz spacing";
           }
           enum "1591.15" {
             description "1591.15 nm/188.412500 THz 3.125/6.25/12.5GHz spacing";
           }
           enum "1591.12" {
             description "1591.12 nm/188.415625 THz 3.125GHz spacing";
           }
           enum "1591.10" {
             description "1591.10 nm/188.418750 THz 3.125/6.25GHz spacing";
           }
           enum "1591.07" {
             description "1591.07 nm/188.421875 THz 3.125GHz spacing";
           }
           enum "1591.04" {
             description "1591.04 nm/188.425000 THz 3.125/6.25/12.5GHz spacing";
           }
           enum "1591.02" {
             description "1591.02 nm/188.428125 THz 3.125GHz spacing";
           }
           enum "1590.99" {
             description "1590.99 nm/188.431250 THz 3.125/6.25GHz spacing";
           }
           enum "1590.96" {
             description "1590.96 nm/188.434375 THz 3.125GHz spacing";
           }
           enum "1590.94" {
             description "1590.94 nm/188.437500 THz 3.125/6.25/12.5GHz spacing";
           }
           enum "1590.91" {
             description "1590.91 nm/188.440625 THz 3.125GHz spacing";
           }
           enum "1590.89" {
             description "1590.89 nm/188.443750 THz 3.125/6.25GHz spacing";
           }
           enum "1590.86" {
             description "1590.86 nm/188.446875 THz 3.125GHz spacing";
           }
           enum "1590.83" {
             description "1590.83 nm/188.450000 THz 3.125/6.25/12.5/50/75GHz spacing";
           }
           enum "1590.81" {
             description "1590.81 nm/188.453125 THz 3.125GHz spacing";
           }
           enum "1590.78" {
             description "1590.78 nm/188.456250 THz 3.125/6.25GHz spacing";
           }
           enum "1590.75" {
             description "1590.75 nm/188.459375 THz 3.125GHz spacing";
           }
           enum "1590.73" {
             description "1590.73 nm/188.462500 THz 3.125/6.25/12.5GHz spacing";
           }
           enum "1590.70" {
             description "1590.70 nm/188.465625 THz 3.125GHz spacing";
           }
           enum "1590.67" {
             description "1590.67 nm/188.468750 THz 3.125/6.25GHz spacing";
           }
           enum "1590.65" {
             description "1590.65 nm/188.471875 THz 3.125GHz spacing";
           }
           enum "1590.62" {
             description "1590.62 nm/188.475000 THz 3.125/6.25/12.5GHz spacing";
           }
           enum "1590.60" {
             description "1590.60 nm/188.478125 THz 3.125GHz spacing";
           }
           enum "1590.57" {
             description "1590.57 nm/188.481250 THz 3.125/6.25GHz spacing";
           }
           enum "1590.54" {
             description "1590.54 nm/188.484375 THz 3.125GHz spacing";
           }
           enum "1590.52" {
             description "1590.52 nm/188.487500 THz 3.125/6.25/12.5GHz spacing";
           }
           enum "1590.49" {
             description "1590.49 nm/188.490625 THz 3.125GHz spacing";
           }
           enum "1590.46" {
             description "1590.46 nm/188.493750 THz 3.125/6.25GHz spacing";
           }
           enum "1590.44" {
             description "1590.44 nm/188.496875 THz 3.125GHz spacing";
           }
           enum "1590.41" {
             description "1590.41 nm/188.500000 THz 3.125/6.25/12.5/100GHz spacing";
           }
           enum "1590.38" {
             description "1590.38 nm/188.503125 THz 3.125GHz spacing";
           }
           enum "1590.36" {
             description "1590.36 nm/188.506250 THz 3.125/6.25GHz spacing";
           }
           enum "1590.33" {
             description "1590.33 nm/188.509375 THz 3.125GHz spacing";
           }
           enum "1590.31" {
             description "1590.31 nm/188.512500 THz 3.125/6.25/12.5GHz spacing";
           }
           enum "1590.28" {
             description "1590.28 nm/188.515625 THz 3.125GHz spacing";
           }
           enum "1590.25" {
             description "1590.25 nm/188.518750 THz 3.125/6.25GHz spacing";
           }
           enum "1590.23" {
             description "1590.23 nm/188.521875 THz 3.125GHz spacing";
           }
           enum "1590.20" {
             description "1590.20 nm/188.525000 THz 3.125/6.25/12.5/75GHz spacing";
           }
           enum "1590.17" {
             description "1590.17 nm/188.528125 THz 3.125GHz spacing";
           }
           enum "1590.15" {
             description "1590.15 nm/188.531250 THz 3.125/6.25GHz spacing";
           }
           enum "1590.12" {
             description "1590.12 nm/188.534375 THz 3.125GHz spacing";
           }
           enum "1590.09" {
             description "1590.09 nm/188.537500 THz 3.125/6.25/12.5GHz spacing";
           }
           enum "1590.07" {
             description "1590.07 nm/188.540625 THz 3.125GHz spacing";
           }
           enum "1590.04" {
             description "1590.04 nm/188.543750 THz 3.125/6.25GHz spacing";
           }
           enum "1590.02" {
             description "1590.02 nm/188.546875 THz 3.125GHz spacing";
           }
           enum "1589.99" {
             description "1589.99 nm/188.550000 THz 3.125/6.25/12.5/50GHz spacing";
           }
           enum "1589.96" {
             description "1589.96 nm/188.553125 THz 3.125GHz spacing";
           }
           enum "1589.94" {
             description "1589.94 nm/188.556250 THz 3.125/6.25GHz spacing";
           }
           enum "1589.91" {
             description "1589.91 nm/188.559375 THz 3.125GHz spacing";
           }
           enum "1589.88" {
             description "1589.88 nm/188.562500 THz 3.125/6.25/12.5GHz spacing";
           }
           enum "1589.86" {
             description "1589.86 nm/188.565625 THz 3.125GHz spacing";
           }
           enum "1589.83" {
             description "1589.83 nm/188.568750 THz 3.125/6.25GHz spacing";
           }
           enum "1589.80" {
             description "1589.80 nm/188.571875 THz 3.125GHz spacing";
           }
           enum "1589.78" {
             description "1589.78 nm/188.575000 THz 3.125/6.25/12.5GHz spacing";
           }
           enum "1589.75" {
             description "1589.75 nm/188.578125 THz 3.125GHz spacing";
           }
           enum "1589.73" {
             description "1589.73 nm/188.581250 THz 3.125/6.25GHz spacing";
           }
           enum "1589.70" {
             description "1589.70 nm/188.584375 THz 3.125GHz spacing";
           }
           enum "1589.67" {
             description "1589.67 nm/188.587500 THz 3.125/6.25/12.5GHz spacing";
           }
           enum "1589.65" {
             description "1589.65 nm/188.590625 THz 3.125GHz spacing";
           }
           enum "1589.62" {
             description "1589.62 nm/188.593750 THz 3.125/6.25GHz spacing";
           }
           enum "1589.59" {
             description "1589.59 nm/188.596875 THz 3.125GHz spacing";
           }
           enum "1589.57" {
             description "1589.57 nm/188.600000 THz 3.125/6.25/12.5/100GHz spacing";
           }
           enum "1589.54" {
             description "1589.54 nm/188.603125 THz 3.125GHz spacing";
           }
           enum "1589.51" {
             description "1589.51 nm/188.606250 THz 3.125/6.25GHz spacing";
           }
           enum "1589.49" {
             description "1589.49 nm/188.609375 THz 3.125GHz spacing";
           }
           enum "1589.46" {
             description "1589.46 nm/188.612500 THz 3.125/6.25/12.5GHz spacing";
           }
           enum "1589.44" {
             description "1589.44 nm/188.615625 THz 3.125GHz spacing";
           }
           enum "1589.41" {
             description "1589.41 nm/188.618750 THz 3.125/6.25GHz spacing";
           }
           enum "1589.38" {
             description "1589.38 nm/188.621875 THz 3.125GHz spacing";
           }
           enum "1589.36" {
             description "1589.36 nm/188.625000 THz 3.125/6.25/12.5GHz spacing";
           }
           enum "1589.33" {
             description "1589.33 nm/188.628125 THz 3.125GHz spacing";
           }
           enum "1589.30" {
             description "1589.30 nm/188.631250 THz 3.125/6.25GHz spacing";
           }
           enum "1589.28" {
             description "1589.28 nm/188.634375 THz 3.125GHz spacing";
           }
           enum "1589.25" {
             description "1589.25 nm/188.637500 THz 3.125/6.25/12.5GHz spacing";
           }
           enum "1589.23" {
             description "1589.23 nm/188.640625 THz 3.125GHz spacing";
           }
           enum "1589.20" {
             description "1589.20 nm/188.643750 THz 3.125/6.25GHz spacing";
           }
           enum "1589.17" {
             description "1589.17 nm/188.646875 THz 3.125GHz spacing";
           }
           enum "1589.15" {
             description "1589.15 nm/188.650000 THz 3.125/6.25/12.5/50GHz spacing";
           }
           enum "1589.12" {
             description "1589.12 nm/188.653125 THz 3.125GHz spacing";
           }
           enum "1589.09" {
             description "1589.09 nm/188.656250 THz 3.125/6.25GHz spacing";
           }
           enum "1589.07" {
             description "1589.07 nm/188.659375 THz 3.125GHz spacing";
           }
           enum "1589.04" {
             description "1589.04 nm/188.662500 THz 3.125/6.25/12.5GHz spacing";
           }
           enum "1589.01" {
             description "1589.01 nm/188.665625 THz 3.125GHz spacing";
           }
           enum "1588.99" {
             description "1588.99 nm/188.668750 THz 3.125/6.25GHz spacing";
           }
           enum "1588.96" {
             description "1588.96 nm/188.671875 THz 3.125GHz spacing";
           }
           enum "1588.94" {
             description "1588.94 nm/188.675000 THz 3.125/6.25/12.5/75GHz spacing";
           }
           enum "1588.91" {
             description "1588.91 nm/188.678125 THz 3.125GHz spacing";
           }
           enum "1588.88" {
             description "1588.88 nm/188.681250 THz 3.125/6.25GHz spacing";
           }
           enum "1588.86" {
             description "1588.86 nm/188.684375 THz 3.125GHz spacing";
           }
           enum "1588.83" {
             description "1588.83 nm/188.687500 THz 3.125/6.25/12.5GHz spacing";
           }
           enum "1588.80" {
             description "1588.80 nm/188.690625 THz 3.125GHz spacing";
           }
           enum "1588.78" {
             description "1588.78 nm/188.693750 THz 3.125/6.25GHz spacing";
           }
           enum "1588.75" {
             description "1588.75 nm/188.696875 THz 3.125GHz spacing";
           }
           enum "1588.73" {
             description "1588.73 nm/188.700000 THz 3.125/6.25/12.5/50/75/100GHz spacing";
           }
           enum "1588.70" {
             description "1588.70 nm/188.703125 THz 3.125GHz spacing";
           }
           enum "1588.67" {
             description "1588.67 nm/188.706250 THz 3.125/6.25GHz spacing";
           }
           enum "1588.65" {
             description "1588.65 nm/188.709375 THz 3.125GHz spacing";
           }
           enum "1588.62" {
             description "1588.62 nm/188.712500 THz 3.125/6.25/12.5GHz spacing";
           }
           enum "1588.59" {
             description "1588.59 nm/188.715625 THz 3.125GHz spacing";
           }
           enum "1588.57" {
             description "1588.57 nm/188.718750 THz 3.125/6.25GHz spacing";
           }
           enum "1588.54" {
             description "1588.54 nm/188.721875 THz 3.125GHz spacing";
           }
           enum "1588.51" {
             description "1588.51 nm/188.725000 THz 3.125/6.25/12.5GHz spacing";
           }
           enum "1588.49" {
             description "1588.49 nm/188.728125 THz 3.125GHz spacing";
           }
           enum "1588.46" {
             description "1588.46 nm/188.731250 THz 3.125/6.25GHz spacing";
           }
           enum "1588.44" {
             description "1588.44 nm/188.734375 THz 3.125GHz spacing";
           }
           enum "1588.41" {
             description "1588.41 nm/188.737500 THz 3.125/6.25/12.5GHz spacing";
           }
           enum "1588.38" {
             description "1588.38 nm/188.740625 THz 3.125GHz spacing";
           }
           enum "1588.36" {
             description "1588.36 nm/188.743750 THz 3.125/6.25GHz spacing";
           }
           enum "1588.33" {
             description "1588.33 nm/188.746875 THz 3.125GHz spacing";
           }
           enum "1588.30" {
             description "1588.30 nm/188.750000 THz 3.125/6.25/12.5/50/75GHz spacing";
           }
           enum "1588.28" {
             description "1588.28 nm/188.753125 THz 3.125GHz spacing";
           }
           enum "1588.25" {
             description "1588.25 nm/188.756250 THz 3.125/6.25GHz spacing";
           }
           enum "1588.23" {
             description "1588.23 nm/188.759375 THz 3.125GHz spacing";
           }
           enum "1588.20" {
             description "1588.20 nm/188.762500 THz 3.125/6.25/12.5GHz spacing";
           }
           enum "1588.17" {
             description "1588.17 nm/188.765625 THz 3.125GHz spacing";
           }
           enum "1588.15" {
             description "1588.15 nm/188.768750 THz 3.125/6.25GHz spacing";
           }
           enum "1588.12" {
             description "1588.12 nm/188.771875 THz 3.125GHz spacing";
           }
           enum "1588.09" {
             description "1588.09 nm/188.775000 THz 3.125/6.25/12.5GHz spacing";
           }
           enum "1588.07" {
             description "1588.07 nm/188.778125 THz 3.125GHz spacing";
           }
           enum "1588.04" {
             description "1588.04 nm/188.781250 THz 3.125/6.25GHz spacing";
           }
           enum "1588.02" {
             description "1588.02 nm/188.784375 THz 3.125GHz spacing";
           }
           enum "1587.99" {
             description "1587.99 nm/188.787500 THz 3.125/6.25/12.5GHz spacing";
           }
           enum "1587.96" {
             description "1587.96 nm/188.790625 THz 3.125GHz spacing";
           }
           enum "1587.94" {
             description "1587.94 nm/188.793750 THz 3.125/6.25GHz spacing";
           }
           enum "1587.91" {
             description "1587.91 nm/188.796875 THz 3.125GHz spacing";
           }
           enum "1587.88" {
             description "1587.88 nm/188.800000 THz 3.125/6.25/12.5/100GHz spacing";
           }
           enum "1587.86" {
             description "1587.86 nm/188.803125 THz 3.125GHz spacing";
           }
           enum "1587.83" {
             description "1587.83 nm/188.806250 THz 3.125/6.25GHz spacing";
           }
           enum "1587.80" {
             description "1587.80 nm/188.809375 THz 3.125GHz spacing";
           }
           enum "1587.78" {
             description "1587.78 nm/188.812500 THz 3.125/6.25/12.5GHz spacing";
           }
           enum "1587.75" {
             description "1587.75 nm/188.815625 THz 3.125GHz spacing";
           }
           enum "1587.73" {
             description "1587.73 nm/188.818750 THz 3.125/6.25GHz spacing";
           }
           enum "1587.70" {
             description "1587.70 nm/188.821875 THz 3.125GHz spacing";
           }
           enum "1587.67" {
             description "1587.67 nm/188.825000 THz 3.125/6.25/12.5/75GHz spacing";
           }
           enum "1587.65" {
             description "1587.65 nm/188.828125 THz 3.125GHz spacing";
           }
           enum "1587.62" {
             description "1587.62 nm/188.831250 THz 3.125/6.25GHz spacing";
           }
           enum "1587.59" {
             description "1587.59 nm/188.834375 THz 3.125GHz spacing";
           }
           enum "1587.57" {
             description "1587.57 nm/188.837500 THz 3.125/6.25/12.5GHz spacing";
           }
           enum "1587.54" {
             description "1587.54 nm/188.840625 THz 3.125GHz spacing";
           }
           enum "1587.52" {
             description "1587.52 nm/188.843750 THz 3.125/6.25GHz spacing";
           }
           enum "1587.49" {
             description "1587.49 nm/188.846875 THz 3.125GHz spacing";
           }
           enum "1587.46" {
             description "1587.46 nm/188.850000 THz 3.125/6.25/12.5/50GHz spacing";
           }
           enum "1587.44" {
             description "1587.44 nm/188.853125 THz 3.125GHz spacing";
           }
           enum "1587.41" {
             description "1587.41 nm/188.856250 THz 3.125/6.25GHz spacing";
           }
           enum "1587.38" {
             description "1587.38 nm/188.859375 THz 3.125GHz spacing";
           }
           enum "1587.36" {
             description "1587.36 nm/188.862500 THz 3.125/6.25/12.5GHz spacing";
           }
           enum "1587.33" {
             description "1587.33 nm/188.865625 THz 3.125GHz spacing";
           }
           enum "1587.31" {
             description "1587.31 nm/188.868750 THz 3.125/6.25GHz spacing";
           }
           enum "1587.28" {
             description "1587.28 nm/188.871875 THz 3.125GHz spacing";
           }
           enum "1587.25" {
             description "1587.25 nm/188.875000 THz 3.125/6.25/12.5GHz spacing";
           }
           enum "1587.23" {
             description "1587.23 nm/188.878125 THz 3.125GHz spacing";
           }
           enum "1587.20" {
             description "1587.20 nm/188.881250 THz 3.125/6.25GHz spacing";
           }
           enum "1587.17" {
             description "1587.17 nm/188.884375 THz 3.125GHz spacing";
           }
           enum "1587.15" {
             description "1587.15 nm/188.887500 THz 3.125/6.25/12.5GHz spacing";
           }
           enum "1587.12" {
             description "1587.12 nm/188.890625 THz 3.125GHz spacing";
           }
           enum "1587.10" {
             description "1587.10 nm/188.893750 THz 3.125/6.25GHz spacing";
           }
           enum "1587.07" {
             description "1587.07 nm/188.896875 THz 3.125GHz spacing";
           }
           enum "1587.04" {
             description "1587.04 nm/188.900000 THz 3.125/6.25/12.5/100GHz spacing";
           }
           enum "1587.02" {
             description "1587.02 nm/188.903125 THz 3.125GHz spacing";
           }
           enum "1586.99" {
             description "1586.99 nm/188.906250 THz 3.125/6.25GHz spacing";
           }
           enum "1586.96" {
             description "1586.96 nm/188.909375 THz 3.125GHz spacing";
           }
           enum "1586.94" {
             description "1586.94 nm/188.912500 THz 3.125/6.25/12.5GHz spacing";
           }
           enum "1586.91" {
             description "1586.91 nm/188.915625 THz 3.125GHz spacing";
           }
           enum "1586.89" {
             description "1586.89 nm/188.918750 THz 3.125/6.25GHz spacing";
           }
           enum "1586.86" {
             description "1586.86 nm/188.921875 THz 3.125GHz spacing";
           }
           enum "1586.83" {
             description "1586.83 nm/188.925000 THz 3.125/6.25/12.5GHz spacing";
           }
           enum "1586.81" {
             description "1586.81 nm/188.928125 THz 3.125GHz spacing";
           }
           enum "1586.78" {
             description "1586.78 nm/188.931250 THz 3.125/6.25GHz spacing";
           }
           enum "1586.75" {
             description "1586.75 nm/188.934375 THz 3.125GHz spacing";
           }
           enum "1586.73" {
             description "1586.73 nm/188.937500 THz 3.125/6.25/12.5GHz spacing";
           }
           enum "1586.70" {
             description "1586.70 nm/188.940625 THz 3.125GHz spacing";
           }
           enum "1586.68" {
             description "1586.68 nm/188.943750 THz 3.125/6.25GHz spacing";
           }
           enum "1586.65" {
             description "1586.65 nm/188.946875 THz 3.125GHz spacing";
           }
           enum "1586.62" {
             description "1586.62 nm/188.950000 THz 3.125/6.25/12.5/50GHz spacing";
           }
           enum "1586.60" {
             description "1586.60 nm/188.953125 THz 3.125GHz spacing";
           }
           enum "1586.57" {
             description "1586.57 nm/188.956250 THz 3.125/6.25GHz spacing";
           }
           enum "1586.54" {
             description "1586.54 nm/188.959375 THz 3.125GHz spacing";
           }
           enum "1586.52" {
             description "1586.52 nm/188.962500 THz 3.125/6.25/12.5GHz spacing";
           }
           enum "1586.49" {
             description "1586.49 nm/188.965625 THz 3.125GHz spacing";
           }
           enum "1586.47" {
             description "1586.47 nm/188.968750 THz 3.125/6.25GHz spacing";
           }
           enum "1586.44" {
             description "1586.44 nm/188.971875 THz 3.125GHz spacing";
           }
           enum "1586.41" {
             description "1586.41 nm/188.975000 THz 3.125/6.25/12.5/75GHz spacing";
           }
           enum "1586.39" {
             description "1586.39 nm/188.978125 THz 3.125GHz spacing";
           }
           enum "1586.36" {
             description "1586.36 nm/188.981250 THz 3.125/6.25GHz spacing";
           }
           enum "1586.33" {
             description "1586.33 nm/188.984375 THz 3.125GHz spacing";
           }
           enum "1586.31" {
             description "1586.31 nm/188.987500 THz 3.125/6.25/12.5GHz spacing";
           }
           enum "1586.28" {
             description "1586.28 nm/188.990625 THz 3.125GHz spacing";
           }
           enum "1586.26" {
             description "1586.26 nm/188.993750 THz 3.125/6.25GHz spacing";
           }
           enum "1586.23" {
             description "1586.23 nm/188.996875 THz 3.125GHz spacing";
           }
           enum "1586.20" {
             description "1586.20 nm/189.000000 THz 3.125/6.25/12.5/50/75/100GHz spacing";
           }
           enum "1586.18" {
             description "1586.18 nm/189.003125 THz 3.125GHz spacing";
           }
           enum "1586.15" {
             description "1586.15 nm/189.006250 THz 3.125/6.25GHz spacing";
           }
           enum "1586.12" {
             description "1586.12 nm/189.009375 THz 3.125GHz spacing";
           }
           enum "1586.10" {
             description "1586.10 nm/189.012500 THz 3.125/6.25/12.5GHz spacing";
           }
           enum "1586.07" {
             description "1586.07 nm/189.015625 THz 3.125GHz spacing";
           }
           enum "1586.05" {
             description "1586.05 nm/189.018750 THz 3.125/6.25GHz spacing";
           }
           enum "1586.02" {
             description "1586.02 nm/189.021875 THz 3.125GHz spacing";
           }
           enum "1585.99" {
             description "1585.99 nm/189.025000 THz 3.125/6.25/12.5GHz spacing";
           }
           enum "1585.97" {
             description "1585.97 nm/189.028125 THz 3.125GHz spacing";
           }
           enum "1585.94" {
             description "1585.94 nm/189.031250 THz 3.125/6.25GHz spacing";
           }
           enum "1585.92" {
             description "1585.92 nm/189.034375 THz 3.125GHz spacing";
           }
           enum "1585.89" {
             description "1585.89 nm/189.037500 THz 3.125/6.25/12.5GHz spacing";
           }
           enum "1585.86" {
             description "1585.86 nm/189.040625 THz 3.125GHz spacing";
           }
           enum "1585.84" {
             description "1585.84 nm/189.043750 THz 3.125/6.25GHz spacing";
           }
           enum "1585.81" {
             description "1585.81 nm/189.046875 THz 3.125GHz spacing";
           }
           enum "1585.78" {
             description "1585.78 nm/189.050000 THz 3.125/6.25/12.5/50/75GHz spacing";
           }
           enum "1585.76" {
             description "1585.76 nm/189.053125 THz 3.125GHz spacing";
           }
           enum "1585.73" {
             description "1585.73 nm/189.056250 THz 3.125/6.25GHz spacing";
           }
           enum "1585.71" {
             description "1585.71 nm/189.059375 THz 3.125GHz spacing";
           }
           enum "1585.68" {
             description "1585.68 nm/189.062500 THz 3.125/6.25/12.5GHz spacing";
           }
           enum "1585.65" {
             description "1585.65 nm/189.065625 THz 3.125GHz spacing";
           }
           enum "1585.63" {
             description "1585.63 nm/189.068750 THz 3.125/6.25GHz spacing";
           }
           enum "1585.60" {
             description "1585.60 nm/189.071875 THz 3.125GHz spacing";
           }
           enum "1585.57" {
             description "1585.57 nm/189.075000 THz 3.125/6.25/12.5GHz spacing";
           }
           enum "1585.55" {
             description "1585.55 nm/189.078125 THz 3.125GHz spacing";
           }
           enum "1585.52" {
             description "1585.52 nm/189.081250 THz 3.125/6.25GHz spacing";
           }
           enum "1585.50" {
             description "1585.50 nm/189.084375 THz 3.125GHz spacing";
           }
           enum "1585.47" {
             description "1585.47 nm/189.087500 THz 3.125/6.25/12.5GHz spacing";
           }
           enum "1585.44" {
             description "1585.44 nm/189.090625 THz 3.125GHz spacing";
           }
           enum "1585.42" {
             description "1585.42 nm/189.093750 THz 3.125/6.25GHz spacing";
           }
           enum "1585.39" {
             description "1585.39 nm/189.096875 THz 3.125GHz spacing";
           }
           enum "1585.36" {
             description "1585.36 nm/189.100000 THz 3.125/6.25/12.5/100GHz spacing";
           }
           enum "1585.34" {
             description "1585.34 nm/189.103125 THz 3.125GHz spacing";
           }
           enum "1585.31" {
             description "1585.31 nm/189.106250 THz 3.125/6.25GHz spacing";
           }
           enum "1585.29" {
             description "1585.29 nm/189.109375 THz 3.125GHz spacing";
           }
           enum "1585.26" {
             description "1585.26 nm/189.112500 THz 3.125/6.25/12.5GHz spacing";
           }
           enum "1585.23" {
             description "1585.23 nm/189.115625 THz 3.125GHz spacing";
           }
           enum "1585.21" {
             description "1585.21 nm/189.118750 THz 3.125/6.25GHz spacing";
           }
           enum "1585.18" {
             description "1585.18 nm/189.121875 THz 3.125GHz spacing";
           }
           enum "1585.16" {
             description "1585.16 nm/189.125000 THz 3.125/6.25/12.5/75GHz spacing";
           }
           enum "1585.13" {
             description "1585.13 nm/189.128125 THz 3.125GHz spacing";
           }
           enum "1585.10" {
             description "1585.10 nm/189.131250 THz 3.125/6.25GHz spacing";
           }
           enum "1585.08" {
             description "1585.08 nm/189.134375 THz 3.125GHz spacing";
           }
           enum "1585.05" {
             description "1585.05 nm/189.137500 THz 3.125/6.25/12.5GHz spacing";
           }
           enum "1585.02" {
             description "1585.02 nm/189.140625 THz 3.125GHz spacing";
           }
           enum "1585.00" {
             description "1585.00 nm/189.143750 THz 3.125/6.25GHz spacing";
           }
           enum "1584.97" {
             description "1584.97 nm/189.146875 THz 3.125GHz spacing";
           }
           enum "1584.95" {
             description "1584.95 nm/189.150000 THz 3.125/6.25/12.5/50GHz spacing";
           }
           enum "1584.92" {
             description "1584.92 nm/189.153125 THz 3.125GHz spacing";
           }
           enum "1584.89" {
             description "1584.89 nm/189.156250 THz 3.125/6.25GHz spacing";
           }
           enum "1584.87" {
             description "1584.87 nm/189.159375 THz 3.125GHz spacing";
           }
           enum "1584.84" {
             description "1584.84 nm/189.162500 THz 3.125/6.25/12.5GHz spacing";
           }
           enum "1584.81" {
             description "1584.81 nm/189.165625 THz 3.125GHz spacing";
           }
           enum "1584.79" {
             description "1584.79 nm/189.168750 THz 3.125/6.25GHz spacing";
           }
           enum "1584.76" {
             description "1584.76 nm/189.171875 THz 3.125GHz spacing";
           }
           enum "1584.74" {
             description "1584.74 nm/189.175000 THz 3.125/6.25/12.5GHz spacing";
           }
           enum "1584.71" {
             description "1584.71 nm/189.178125 THz 3.125GHz spacing";
           }
           enum "1584.68" {
             description "1584.68 nm/189.181250 THz 3.125/6.25GHz spacing";
           }
           enum "1584.66" {
             description "1584.66 nm/189.184375 THz 3.125GHz spacing";
           }
           enum "1584.63" {
             description "1584.63 nm/189.187500 THz 3.125/6.25/12.5GHz spacing";
           }
           enum "1584.61" {
             description "1584.61 nm/189.190625 THz 3.125GHz spacing";
           }
           enum "1584.58" {
             description "1584.58 nm/189.193750 THz 3.125/6.25GHz spacing";
           }
           enum "1584.55" {
             description "1584.55 nm/189.196875 THz 3.125GHz spacing";
           }
           enum "1584.53" {
             description "1584.53 nm/189.200000 THz 3.125/6.25/12.5/100GHz spacing";
           }
           enum "1584.50" {
             description "1584.50 nm/189.203125 THz 3.125GHz spacing";
           }
           enum "1584.47" {
             description "1584.47 nm/189.206250 THz 3.125/6.25GHz spacing";
           }
           enum "1584.45" {
             description "1584.45 nm/189.209375 THz 3.125GHz spacing";
           }
           enum "1584.42" {
             description "1584.42 nm/189.212500 THz 3.125/6.25/12.5GHz spacing";
           }
           enum "1584.40" {
             description "1584.40 nm/189.215625 THz 3.125GHz spacing";
           }
           enum "1584.37" {
             description "1584.37 nm/189.218750 THz 3.125/6.25GHz spacing";
           }
           enum "1584.34" {
             description "1584.34 nm/189.221875 THz 3.125GHz spacing";
           }
           enum "1584.32" {
             description "1584.32 nm/189.225000 THz 3.125/6.25/12.5GHz spacing";
           }
           enum "1584.29" {
             description "1584.29 nm/189.228125 THz 3.125GHz spacing";
           }
           enum "1584.27" {
             description "1584.27 nm/189.231250 THz 3.125/6.25GHz spacing";
           }
           enum "1584.24" {
             description "1584.24 nm/189.234375 THz 3.125GHz spacing";
           }
           enum "1584.21" {
             description "1584.21 nm/189.237500 THz 3.125/6.25/12.5GHz spacing";
           }
           enum "1584.19" {
             description "1584.19 nm/189.240625 THz 3.125GHz spacing";
           }
           enum "1584.16" {
             description "1584.16 nm/189.243750 THz 3.125/6.25GHz spacing";
           }
           enum "1584.13" {
             description "1584.13 nm/189.246875 THz 3.125GHz spacing";
           }
           enum "1584.11" {
             description "1584.11 nm/189.250000 THz 3.125/6.25/12.5/50GHz spacing";
           }
           enum "1584.08" {
             description "1584.08 nm/189.253125 THz 3.125GHz spacing";
           }
           enum "1584.06" {
             description "1584.06 nm/189.256250 THz 3.125/6.25GHz spacing";
           }
           enum "1584.03" {
             description "1584.03 nm/189.259375 THz 3.125GHz spacing";
           }
           enum "1584.00" {
             description "1584.00 nm/189.262500 THz 3.125/6.25/12.5GHz spacing";
           }
           enum "1583.98" {
             description "1583.98 nm/189.265625 THz 3.125GHz spacing";
           }
           enum "1583.95" {
             description "1583.95 nm/189.268750 THz 3.125/6.25GHz spacing";
           }
           enum "1583.93" {
             description "1583.93 nm/189.271875 THz 3.125GHz spacing";
           }
           enum "1583.90" {
             description "1583.90 nm/189.275000 THz 3.125/6.25/12.5/75GHz spacing";
           }
           enum "1583.87" {
             description "1583.87 nm/189.278125 THz 3.125GHz spacing";
           }
           enum "1583.85" {
             description "1583.85 nm/189.281250 THz 3.125/6.25GHz spacing";
           }
           enum "1583.82" {
             description "1583.82 nm/189.284375 THz 3.125GHz spacing";
           }
           enum "1583.79" {
             description "1583.79 nm/189.287500 THz 3.125/6.25/12.5GHz spacing";
           }
           enum "1583.77" {
             description "1583.77 nm/189.290625 THz 3.125GHz spacing";
           }
           enum "1583.74" {
             description "1583.74 nm/189.293750 THz 3.125/6.25GHz spacing";
           }
           enum "1583.72" {
             description "1583.72 nm/189.296875 THz 3.125GHz spacing";
           }
           enum "1583.69" {
             description "1583.69 nm/189.300000 THz 3.125/6.25/12.5/50/75/100GHz spacing";
           }
           enum "1583.66" {
             description "1583.66 nm/189.303125 THz 3.125GHz spacing";
           }
           enum "1583.64" {
             description "1583.64 nm/189.306250 THz 3.125/6.25GHz spacing";
           }
           enum "1583.61" {
             description "1583.61 nm/189.309375 THz 3.125GHz spacing";
           }
           enum "1583.59" {
             description "1583.59 nm/189.312500 THz 3.125/6.25/12.5GHz spacing";
           }
           enum "1583.56" {
             description "1583.56 nm/189.315625 THz 3.125GHz spacing";
           }
           enum "1583.53" {
             description "1583.53 nm/189.318750 THz 3.125/6.25GHz spacing";
           }
           enum "1583.51" {
             description "1583.51 nm/189.321875 THz 3.125GHz spacing";
           }
           enum "1583.48" {
             description "1583.48 nm/189.325000 THz 3.125/6.25/12.5GHz spacing";
           }
           enum "1583.45" {
             description "1583.45 nm/189.328125 THz 3.125GHz spacing";
           }
           enum "1583.43" {
             description "1583.43 nm/189.331250 THz 3.125/6.25GHz spacing";
           }
           enum "1583.40" {
             description "1583.40 nm/189.334375 THz 3.125GHz spacing";
           }
           enum "1583.38" {
             description "1583.38 nm/189.337500 THz 3.125/6.25/12.5GHz spacing";
           }
           enum "1583.35" {
             description "1583.35 nm/189.340625 THz 3.125GHz spacing";
           }
           enum "1583.32" {
             description "1583.32 nm/189.343750 THz 3.125/6.25GHz spacing";
           }
           enum "1583.30" {
             description "1583.30 nm/189.346875 THz 3.125GHz spacing";
           }
           enum "1583.27" {
             description "1583.27 nm/189.350000 THz 3.125/6.25/12.5/50/75GHz spacing";
           }
           enum "1583.25" {
             description "1583.25 nm/189.353125 THz 3.125GHz spacing";
           }
           enum "1583.22" {
             description "1583.22 nm/189.356250 THz 3.125/6.25GHz spacing";
           }
           enum "1583.19" {
             description "1583.19 nm/189.359375 THz 3.125GHz spacing";
           }
           enum "1583.17" {
             description "1583.17 nm/189.362500 THz 3.125/6.25/12.5GHz spacing";
           }
           enum "1583.14" {
             description "1583.14 nm/189.365625 THz 3.125GHz spacing";
           }
           enum "1583.11" {
             description "1583.11 nm/189.368750 THz 3.125/6.25GHz spacing";
           }
           enum "1583.09" {
             description "1583.09 nm/189.371875 THz 3.125GHz spacing";
           }
           enum "1583.06" {
             description "1583.06 nm/189.375000 THz 3.125/6.25/12.5GHz spacing";
           }
           enum "1583.04" {
             description "1583.04 nm/189.378125 THz 3.125GHz spacing";
           }
           enum "1583.01" {
             description "1583.01 nm/189.381250 THz 3.125/6.25GHz spacing";
           }
           enum "1582.98" {
             description "1582.98 nm/189.384375 THz 3.125GHz spacing";
           }
           enum "1582.96" {
             description "1582.96 nm/189.387500 THz 3.125/6.25/12.5GHz spacing";
           }
           enum "1582.93" {
             description "1582.93 nm/189.390625 THz 3.125GHz spacing";
           }
           enum "1582.91" {
             description "1582.91 nm/189.393750 THz 3.125/6.25GHz spacing";
           }
           enum "1582.88" {
             description "1582.88 nm/189.396875 THz 3.125GHz spacing";
           }
           enum "1582.85" {
             description "1582.85 nm/189.400000 THz 3.125/6.25/12.5/100GHz spacing";
           }
           enum "1582.83" {
             description "1582.83 nm/189.403125 THz 3.125GHz spacing";
           }
           enum "1582.80" {
             description "1582.80 nm/189.406250 THz 3.125/6.25GHz spacing";
           }
           enum "1582.78" {
             description "1582.78 nm/189.409375 THz 3.125GHz spacing";
           }
           enum "1582.75" {
             description "1582.75 nm/189.412500 THz 3.125/6.25/12.5GHz spacing";
           }
           enum "1582.72" {
             description "1582.72 nm/189.415625 THz 3.125GHz spacing";
           }
           enum "1582.70" {
             description "1582.70 nm/189.418750 THz 3.125/6.25GHz spacing";
           }
           enum "1582.67" {
             description "1582.67 nm/189.421875 THz 3.125GHz spacing";
           }
           enum "1582.64" {
             description "1582.64 nm/189.425000 THz 3.125/6.25/12.5/75GHz spacing";
           }
           enum "1582.62" {
             description "1582.62 nm/189.428125 THz 3.125GHz spacing";
           }
           enum "1582.59" {
             description "1582.59 nm/189.431250 THz 3.125/6.25GHz spacing";
           }
           enum "1582.57" {
             description "1582.57 nm/189.434375 THz 3.125GHz spacing";
           }
           enum "1582.54" {
             description "1582.54 nm/189.437500 THz 3.125/6.25/12.5GHz spacing";
           }
           enum "1582.51" {
             description "1582.51 nm/189.440625 THz 3.125GHz spacing";
           }
           enum "1582.49" {
             description "1582.49 nm/189.443750 THz 3.125/6.25GHz spacing";
           }
           enum "1582.46" {
             description "1582.46 nm/189.446875 THz 3.125GHz spacing";
           }
           enum "1582.44" {
             description "1582.44 nm/189.450000 THz 3.125/6.25/12.5/50GHz spacing";
           }
           enum "1582.41" {
             description "1582.41 nm/189.453125 THz 3.125GHz spacing";
           }
           enum "1582.38" {
             description "1582.38 nm/189.456250 THz 3.125/6.25GHz spacing";
           }
           enum "1582.36" {
             description "1582.36 nm/189.459375 THz 3.125GHz spacing";
           }
           enum "1582.33" {
             description "1582.33 nm/189.462500 THz 3.125/6.25/12.5GHz spacing";
           }
           enum "1582.31" {
             description "1582.31 nm/189.465625 THz 3.125GHz spacing";
           }
           enum "1582.28" {
             description "1582.28 nm/189.468750 THz 3.125/6.25GHz spacing";
           }
           enum "1582.25" {
             description "1582.25 nm/189.471875 THz 3.125GHz spacing";
           }
           enum "1582.23" {
             description "1582.23 nm/189.475000 THz 3.125/6.25/12.5GHz spacing";
           }
           enum "1582.20" {
             description "1582.20 nm/189.478125 THz 3.125GHz spacing";
           }
           enum "1582.17" {
             description "1582.17 nm/189.481250 THz 3.125/6.25GHz spacing";
           }
           enum "1582.15" {
             description "1582.15 nm/189.484375 THz 3.125GHz spacing";
           }
           enum "1582.12" {
             description "1582.12 nm/189.487500 THz 3.125/6.25/12.5GHz spacing";
           }
           enum "1582.10" {
             description "1582.10 nm/189.490625 THz 3.125GHz spacing";
           }
           enum "1582.07" {
             description "1582.07 nm/189.493750 THz 3.125/6.25GHz spacing";
           }
           enum "1582.04" {
             description "1582.04 nm/189.496875 THz 3.125GHz spacing";
           }
           enum "1582.02" {
             description "1582.02 nm/189.500000 THz 3.125/6.25/12.5/100GHz spacing";
           }
           enum "1581.99" {
             description "1581.99 nm/189.503125 THz 3.125GHz spacing";
           }
           enum "1581.97" {
             description "1581.97 nm/189.506250 THz 3.125/6.25GHz spacing";
           }
           enum "1581.94" {
             description "1581.94 nm/189.509375 THz 3.125GHz spacing";
           }
           enum "1581.91" {
             description "1581.91 nm/189.512500 THz 3.125/6.25/12.5GHz spacing";
           }
           enum "1581.89" {
             description "1581.89 nm/189.515625 THz 3.125GHz spacing";
           }
           enum "1581.86" {
             description "1581.86 nm/189.518750 THz 3.125/6.25GHz spacing";
           }
           enum "1581.84" {
             description "1581.84 nm/189.521875 THz 3.125GHz spacing";
           }
           enum "1581.81" {
             description "1581.81 nm/189.525000 THz 3.125/6.25/12.5GHz spacing";
           }
           enum "1581.78" {
             description "1581.78 nm/189.528125 THz 3.125GHz spacing";
           }
           enum "1581.76" {
             description "1581.76 nm/189.531250 THz 3.125/6.25GHz spacing";
           }
           enum "1581.73" {
             description "1581.73 nm/189.534375 THz 3.125GHz spacing";
           }
           enum "1581.71" {
             description "1581.71 nm/189.537500 THz 3.125/6.25/12.5GHz spacing";
           }
           enum "1581.68" {
             description "1581.68 nm/189.540625 THz 3.125GHz spacing";
           }
           enum "1581.65" {
             description "1581.65 nm/189.543750 THz 3.125/6.25GHz spacing";
           }
           enum "1581.63" {
             description "1581.63 nm/189.546875 THz 3.125GHz spacing";
           }
           enum "1581.60" {
             description "1581.60 nm/189.550000 THz 3.125/6.25/12.5/50GHz spacing";
           }
           enum "1581.57" {
             description "1581.57 nm/189.553125 THz 3.125GHz spacing";
           }
           enum "1581.55" {
             description "1581.55 nm/189.556250 THz 3.125/6.25GHz spacing";
           }
           enum "1581.52" {
             description "1581.52 nm/189.559375 THz 3.125GHz spacing";
           }
           enum "1581.50" {
             description "1581.50 nm/189.562500 THz 3.125/6.25/12.5GHz spacing";
           }
           enum "1581.47" {
             description "1581.47 nm/189.565625 THz 3.125GHz spacing";
           }
           enum "1581.44" {
             description "1581.44 nm/189.568750 THz 3.125/6.25GHz spacing";
           }
           enum "1581.42" {
             description "1581.42 nm/189.571875 THz 3.125GHz spacing";
           }
           enum "1581.39" {
             description "1581.39 nm/189.575000 THz 3.125/6.25/12.5/75GHz spacing";
           }
           enum "1581.37" {
             description "1581.37 nm/189.578125 THz 3.125GHz spacing";
           }
           enum "1581.34" {
             description "1581.34 nm/189.581250 THz 3.125/6.25GHz spacing";
           }
           enum "1581.31" {
             description "1581.31 nm/189.584375 THz 3.125GHz spacing";
           }
           enum "1581.29" {
             description "1581.29 nm/189.587500 THz 3.125/6.25/12.5GHz spacing";
           }
           enum "1581.26" {
             description "1581.26 nm/189.590625 THz 3.125GHz spacing";
           }
           enum "1581.24" {
             description "1581.24 nm/189.593750 THz 3.125/6.25GHz spacing";
           }
           enum "1581.21" {
             description "1581.21 nm/189.596875 THz 3.125GHz spacing";
           }
           enum "1581.18" {
             description "1581.18 nm/189.600000 THz 3.125/6.25/12.5/50/75/100GHz spacing";
           }
           enum "1581.16" {
             description "1581.16 nm/189.603125 THz 3.125GHz spacing";
           }
           enum "1581.13" {
             description "1581.13 nm/189.606250 THz 3.125/6.25GHz spacing";
           }
           enum "1581.11" {
             description "1581.11 nm/189.609375 THz 3.125GHz spacing";
           }
           enum "1581.08" {
             description "1581.08 nm/189.612500 THz 3.125/6.25/12.5GHz spacing";
           }
           enum "1581.05" {
             description "1581.05 nm/189.615625 THz 3.125GHz spacing";
           }
           enum "1581.03" {
             description "1581.03 nm/189.618750 THz 3.125/6.25GHz spacing";
           }
           enum "1581.00" {
             description "1581.00 nm/189.621875 THz 3.125GHz spacing";
           }
           enum "1580.98" {
             description "1580.98 nm/189.625000 THz 3.125/6.25/12.5GHz spacing";
           }
           enum "1580.95" {
             description "1580.95 nm/189.628125 THz 3.125GHz spacing";
           }
           enum "1580.92" {
             description "1580.92 nm/189.631250 THz 3.125/6.25GHz spacing";
           }
           enum "1580.90" {
             description "1580.90 nm/189.634375 THz 3.125GHz spacing";
           }
           enum "1580.87" {
             description "1580.87 nm/189.637500 THz 3.125/6.25/12.5GHz spacing";
           }
           enum "1580.85" {
             description "1580.85 nm/189.640625 THz 3.125GHz spacing";
           }
           enum "1580.82" {
             description "1580.82 nm/189.643750 THz 3.125/6.25GHz spacing";
           }
           enum "1580.79" {
             description "1580.79 nm/189.646875 THz 3.125GHz spacing";
           }
           enum "1580.77" {
             description "1580.77 nm/189.650000 THz 3.125/6.25/12.5/50/75GHz spacing";
           }
           enum "1580.74" {
             description "1580.74 nm/189.653125 THz 3.125GHz spacing";
           }
           enum "1580.71" {
             description "1580.71 nm/189.656250 THz 3.125/6.25GHz spacing";
           }
           enum "1580.69" {
             description "1580.69 nm/189.659375 THz 3.125GHz spacing";
           }
           enum "1580.66" {
             description "1580.66 nm/189.662500 THz 3.125/6.25/12.5GHz spacing";
           }
           enum "1580.64" {
             description "1580.64 nm/189.665625 THz 3.125GHz spacing";
           }
           enum "1580.61" {
             description "1580.61 nm/189.668750 THz 3.125/6.25GHz spacing";
           }
           enum "1580.58" {
             description "1580.58 nm/189.671875 THz 3.125GHz spacing";
           }
           enum "1580.56" {
             description "1580.56 nm/189.675000 THz 3.125/6.25/12.5GHz spacing";
           }
           enum "1580.53" {
             description "1580.53 nm/189.678125 THz 3.125GHz spacing";
           }
           enum "1580.51" {
             description "1580.51 nm/189.681250 THz 3.125/6.25GHz spacing";
           }
           enum "1580.48" {
             description "1580.48 nm/189.684375 THz 3.125GHz spacing";
           }
           enum "1580.45" {
             description "1580.45 nm/189.687500 THz 3.125/6.25/12.5GHz spacing";
           }
           enum "1580.43" {
             description "1580.43 nm/189.690625 THz 3.125GHz spacing";
           }
           enum "1580.40" {
             description "1580.40 nm/189.693750 THz 3.125/6.25GHz spacing";
           }
           enum "1580.38" {
             description "1580.38 nm/189.696875 THz 3.125GHz spacing";
           }
           enum "1580.35" {
             description "1580.35 nm/189.700000 THz 3.125/6.25/12.5/100GHz spacing";
           }
           enum "1580.32" {
             description "1580.32 nm/189.703125 THz 3.125GHz spacing";
           }
           enum "1580.30" {
             description "1580.30 nm/189.706250 THz 3.125/6.25GHz spacing";
           }
           enum "1580.27" {
             description "1580.27 nm/189.709375 THz 3.125GHz spacing";
           }
           enum "1580.25" {
             description "1580.25 nm/189.712500 THz 3.125/6.25/12.5GHz spacing";
           }
           enum "1580.22" {
             description "1580.22 nm/189.715625 THz 3.125GHz spacing";
           }
           enum "1580.19" {
             description "1580.19 nm/189.718750 THz 3.125/6.25GHz spacing";
           }
           enum "1580.17" {
             description "1580.17 nm/189.721875 THz 3.125GHz spacing";
           }
           enum "1580.14" {
             description "1580.14 nm/189.725000 THz 3.125/6.25/12.5/75GHz spacing";
           }
           enum "1580.12" {
             description "1580.12 nm/189.728125 THz 3.125GHz spacing";
           }
           enum "1580.09" {
             description "1580.09 nm/189.731250 THz 3.125/6.25GHz spacing";
           }
           enum "1580.06" {
             description "1580.06 nm/189.734375 THz 3.125GHz spacing";
           }
           enum "1580.04" {
             description "1580.04 nm/189.737500 THz 3.125/6.25/12.5GHz spacing";
           }
           enum "1580.01" {
             description "1580.01 nm/189.740625 THz 3.125GHz spacing";
           }
           enum "1579.99" {
             description "1579.99 nm/189.743750 THz 3.125/6.25GHz spacing";
           }
           enum "1579.96" {
             description "1579.96 nm/189.746875 THz 3.125GHz spacing";
           }
           enum "1579.93" {
             description "1579.93 nm/189.750000 THz 3.125/6.25/12.5/50GHz spacing";
           }
           enum "1579.91" {
             description "1579.91 nm/189.753125 THz 3.125GHz spacing";
           }
           enum "1579.88" {
             description "1579.88 nm/189.756250 THz 3.125/6.25GHz spacing";
           }
           enum "1579.86" {
             description "1579.86 nm/189.759375 THz 3.125GHz spacing";
           }
           enum "1579.83" {
             description "1579.83 nm/189.762500 THz 3.125/6.25/12.5GHz spacing";
           }
           enum "1579.80" {
             description "1579.80 nm/189.765625 THz 3.125GHz spacing";
           }
           enum "1579.78" {
             description "1579.78 nm/189.768750 THz 3.125/6.25GHz spacing";
           }
           enum "1579.75" {
             description "1579.75 nm/189.771875 THz 3.125GHz spacing";
           }
           enum "1579.73" {
             description "1579.73 nm/189.775000 THz 3.125/6.25/12.5GHz spacing";
           }
           enum "1579.70" {
             description "1579.70 nm/189.778125 THz 3.125GHz spacing";
           }
           enum "1579.67" {
             description "1579.67 nm/189.781250 THz 3.125/6.25GHz spacing";
           }
           enum "1579.65" {
             description "1579.65 nm/189.784375 THz 3.125GHz spacing";
           }
           enum "1579.62" {
             description "1579.62 nm/189.787500 THz 3.125/6.25/12.5GHz spacing";
           }
           enum "1579.60" {
             description "1579.60 nm/189.790625 THz 3.125GHz spacing";
           }
           enum "1579.57" {
             description "1579.57 nm/189.793750 THz 3.125/6.25GHz spacing";
           }
           enum "1579.54" {
             description "1579.54 nm/189.796875 THz 3.125GHz spacing";
           }
           enum "1579.52" {
             description "1579.52 nm/189.800000 THz 3.125/6.25/12.5/100GHz spacing";
           }
           enum "1579.49" {
             description "1579.49 nm/189.803125 THz 3.125GHz spacing";
           }
           enum "1579.47" {
             description "1579.47 nm/189.806250 THz 3.125/6.25GHz spacing";
           }
           enum "1579.44" {
             description "1579.44 nm/189.809375 THz 3.125GHz spacing";
           }
           enum "1579.41" {
             description "1579.41 nm/189.812500 THz 3.125/6.25/12.5GHz spacing";
           }
           enum "1579.39" {
             description "1579.39 nm/189.815625 THz 3.125GHz spacing";
           }
           enum "1579.36" {
             description "1579.36 nm/189.818750 THz 3.125/6.25GHz spacing";
           }
           enum "1579.34" {
             description "1579.34 nm/189.821875 THz 3.125GHz spacing";
           }
           enum "1579.31" {
             description "1579.31 nm/189.825000 THz 3.125/6.25/12.5GHz spacing";
           }
           enum "1579.28" {
             description "1579.28 nm/189.828125 THz 3.125GHz spacing";
           }
           enum "1579.26" {
             description "1579.26 nm/189.831250 THz 3.125/6.25GHz spacing";
           }
           enum "1579.23" {
             description "1579.23 nm/189.834375 THz 3.125GHz spacing";
           }
           enum "1579.21" {
             description "1579.21 nm/189.837500 THz 3.125/6.25/12.5GHz spacing";
           }
           enum "1579.18" {
             description "1579.18 nm/189.840625 THz 3.125GHz spacing";
           }
           enum "1579.15" {
             description "1579.15 nm/189.843750 THz 3.125/6.25GHz spacing";
           }
           enum "1579.13" {
             description "1579.13 nm/189.846875 THz 3.125GHz spacing";
           }
           enum "1579.10" {
             description "1579.10 nm/189.850000 THz 3.125/6.25/12.5/50GHz spacing";
           }
           enum "1579.08" {
             description "1579.08 nm/189.853125 THz 3.125GHz spacing";
           }
           enum "1579.05" {
             description "1579.05 nm/189.856250 THz 3.125/6.25GHz spacing";
           }
           enum "1579.02" {
             description "1579.02 nm/189.859375 THz 3.125GHz spacing";
           }
           enum "1579.00" {
             description "1579.00 nm/189.862500 THz 3.125/6.25/12.5GHz spacing";
           }
           enum "1578.97" {
             description "1578.97 nm/189.865625 THz 3.125GHz spacing";
           }
           enum "1578.95" {
             description "1578.95 nm/189.868750 THz 3.125/6.25GHz spacing";
           }
           enum "1578.92" {
             description "1578.92 nm/189.871875 THz 3.125GHz spacing";
           }
           enum "1578.89" {
             description "1578.89 nm/189.875000 THz 3.125/6.25/12.5/75GHz spacing";
           }
           enum "1578.87" {
             description "1578.87 nm/189.878125 THz 3.125GHz spacing";
           }
           enum "1578.84" {
             description "1578.84 nm/189.881250 THz 3.125/6.25GHz spacing";
           }
           enum "1578.82" {
             description "1578.82 nm/189.884375 THz 3.125GHz spacing";
           }
           enum "1578.79" {
             description "1578.79 nm/189.887500 THz 3.125/6.25/12.5GHz spacing";
           }
           enum "1578.76" {
             description "1578.76 nm/189.890625 THz 3.125GHz spacing";
           }
           enum "1578.74" {
             description "1578.74 nm/189.893750 THz 3.125/6.25GHz spacing";
           }
           enum "1578.71" {
             description "1578.71 nm/189.896875 THz 3.125GHz spacing";
           }
           enum "1578.69" {
             description "1578.69 nm/189.900000 THz 3.125/6.25/12.5/50/75/100GHz spacing";
           }
           enum "1578.66" {
             description "1578.66 nm/189.903125 THz 3.125GHz spacing";
           }
           enum "1578.63" {
             description "1578.63 nm/189.906250 THz 3.125/6.25GHz spacing";
           }
           enum "1578.61" {
             description "1578.61 nm/189.909375 THz 3.125GHz spacing";
           }
           enum "1578.58" {
             description "1578.58 nm/189.912500 THz 3.125/6.25/12.5GHz spacing";
           }
           enum "1578.56" {
             description "1578.56 nm/189.915625 THz 3.125GHz spacing";
           }
           enum "1578.53" {
             description "1578.53 nm/189.918750 THz 3.125/6.25GHz spacing";
           }
           enum "1578.50" {
             description "1578.50 nm/189.921875 THz 3.125GHz spacing";
           }
           enum "1578.48" {
             description "1578.48 nm/189.925000 THz 3.125/6.25/12.5GHz spacing";
           }
           enum "1578.45" {
             description "1578.45 nm/189.928125 THz 3.125GHz spacing";
           }
           enum "1578.43" {
             description "1578.43 nm/189.931250 THz 3.125/6.25GHz spacing";
           }
           enum "1578.40" {
             description "1578.40 nm/189.934375 THz 3.125GHz spacing";
           }
           enum "1578.37" {
             description "1578.37 nm/189.937500 THz 3.125/6.25/12.5GHz spacing";
           }
           enum "1578.35" {
             description "1578.35 nm/189.940625 THz 3.125GHz spacing";
           }
           enum "1578.32" {
             description "1578.32 nm/189.943750 THz 3.125/6.25GHz spacing";
           }
           enum "1578.30" {
             description "1578.30 nm/189.946875 THz 3.125GHz spacing";
           }
           enum "1578.27" {
             description "1578.27 nm/189.950000 THz 3.125/6.25/12.5/50/75GHz spacing";
           }
           enum "1578.24" {
             description "1578.24 nm/189.953125 THz 3.125GHz spacing";
           }
           enum "1578.22" {
             description "1578.22 nm/189.956250 THz 3.125/6.25GHz spacing";
           }
           enum "1578.19" {
             description "1578.19 nm/189.959375 THz 3.125GHz spacing";
           }
           enum "1578.17" {
             description "1578.17 nm/189.962500 THz 3.125/6.25/12.5GHz spacing";
           }
           enum "1578.14" {
             description "1578.14 nm/189.965625 THz 3.125GHz spacing";
           }
           enum "1578.11" {
             description "1578.11 nm/189.968750 THz 3.125/6.25GHz spacing";
           }
           enum "1578.09" {
             description "1578.09 nm/189.971875 THz 3.125GHz spacing";
           }
           enum "1578.06" {
             description "1578.06 nm/189.975000 THz 3.125/6.25/12.5GHz spacing";
           }
           enum "1578.04" {
             description "1578.04 nm/189.978125 THz 3.125GHz spacing";
           }
           enum "1578.01" {
             description "1578.01 nm/189.981250 THz 3.125/6.25GHz spacing";
           }
           enum "1577.98" {
             description "1577.98 nm/189.984375 THz 3.125GHz spacing";
           }
           enum "1577.96" {
             description "1577.96 nm/189.987500 THz 3.125/6.25/12.5GHz spacing";
           }
           enum "1577.93" {
             description "1577.93 nm/189.990625 THz 3.125GHz spacing";
           }
           enum "1577.91" {
             description "1577.91 nm/189.993750 THz 3.125/6.25GHz spacing";
           }
           enum "1577.88" {
             description "1577.88 nm/189.996875 THz 3.125GHz spacing";
           }
           enum "1577.86" {
             description "1577.86 nm/190.000000 THz 3.125/6.25/12.5/100GHz spacing";
           }
           enum "1577.83" {
             description "1577.83 nm/190.003125 THz 3.125GHz spacing";
           }
           enum "1577.80" {
             description "1577.80 nm/190.006250 THz 3.125/6.25GHz spacing";
           }
           enum "1577.78" {
             description "1577.78 nm/190.009375 THz 3.125GHz spacing";
           }
           enum "1577.75" {
             description "1577.75 nm/190.012500 THz 3.125/6.25/12.5GHz spacing";
           }
           enum "1577.73" {
             description "1577.73 nm/190.015625 THz 3.125GHz spacing";
           }
           enum "1577.70" {
             description "1577.70 nm/190.018750 THz 3.125/6.25GHz spacing";
           }
           enum "1577.67" {
             description "1577.67 nm/190.021875 THz 3.125GHz spacing";
           }
           enum "1577.65" {
             description "1577.65 nm/190.025000 THz 3.125/6.25/12.5/75GHz spacing";
           }
           enum "1577.62" {
             description "1577.62 nm/190.028125 THz 3.125GHz spacing";
           }
           enum "1577.60" {
             description "1577.60 nm/190.031250 THz 3.125/6.25GHz spacing";
           }
           enum "1577.57" {
             description "1577.57 nm/190.034375 THz 3.125GHz spacing";
           }
           enum "1577.54" {
             description "1577.54 nm/190.037500 THz 3.125/6.25/12.5GHz spacing";
           }
           enum "1577.52" {
             description "1577.52 nm/190.040625 THz 3.125GHz spacing";
           }
           enum "1577.49" {
             description "1577.49 nm/190.043750 THz 3.125/6.25GHz spacing";
           }
           enum "1577.47" {
             description "1577.47 nm/190.046875 THz 3.125GHz spacing";
           }
           enum "1577.44" {
             description "1577.44 nm/190.050000 THz 3.125/6.25/12.5/50GHz spacing";
           }
           enum "1577.41" {
             description "1577.41 nm/190.053125 THz 3.125GHz spacing";
           }
           enum "1577.39" {
             description "1577.39 nm/190.056250 THz 3.125/6.25GHz spacing";
           }
           enum "1577.36" {
             description "1577.36 nm/190.059375 THz 3.125GHz spacing";
           }
           enum "1577.34" {
             description "1577.34 nm/190.062500 THz 3.125/6.25/12.5GHz spacing";
           }
           enum "1577.31" {
             description "1577.31 nm/190.065625 THz 3.125GHz spacing";
           }
           enum "1577.28" {
             description "1577.28 nm/190.068750 THz 3.125/6.25GHz spacing";
           }
           enum "1577.26" {
             description "1577.26 nm/190.071875 THz 3.125GHz spacing";
           }
           enum "1577.23" {
             description "1577.23 nm/190.075000 THz 3.125/6.25/12.5GHz spacing";
           }
           enum "1577.21" {
             description "1577.21 nm/190.078125 THz 3.125GHz spacing";
           }
           enum "1577.18" {
             description "1577.18 nm/190.081250 THz 3.125/6.25GHz spacing";
           }
           enum "1577.15" {
             description "1577.15 nm/190.084375 THz 3.125GHz spacing";
           }
           enum "1577.13" {
             description "1577.13 nm/190.087500 THz 3.125/6.25/12.5GHz spacing";
           }
           enum "1577.10" {
             description "1577.10 nm/190.090625 THz 3.125GHz spacing";
           }
           enum "1577.08" {
             description "1577.08 nm/190.093750 THz 3.125/6.25GHz spacing";
           }
           enum "1577.05" {
             description "1577.05 nm/190.096875 THz 3.125GHz spacing";
           }
           enum "1577.03" {
             description "1577.03 nm/190.100000 THz 3.125/6.25/12.5/100GHz spacing";
           }
           enum "1577.00" {
             description "1577.00 nm/190.103125 THz 3.125GHz spacing";
           }
           enum "1576.97" {
             description "1576.97 nm/190.106250 THz 3.125/6.25GHz spacing";
           }
           enum "1576.95" {
             description "1576.95 nm/190.109375 THz 3.125GHz spacing";
           }
           enum "1576.92" {
             description "1576.92 nm/190.112500 THz 3.125/6.25/12.5GHz spacing";
           }
           enum "1576.90" {
             description "1576.90 nm/190.115625 THz 3.125GHz spacing";
           }
           enum "1576.87" {
             description "1576.87 nm/190.118750 THz 3.125/6.25GHz spacing";
           }
           enum "1576.84" {
             description "1576.84 nm/190.121875 THz 3.125GHz spacing";
           }
           enum "1576.82" {
             description "1576.82 nm/190.125000 THz 3.125/6.25/12.5GHz spacing";
           }
           enum "1576.79" {
             description "1576.79 nm/190.128125 THz 3.125GHz spacing";
           }
           enum "1576.77" {
             description "1576.77 nm/190.131250 THz 3.125/6.25GHz spacing";
           }
           enum "1576.74" {
             description "1576.74 nm/190.134375 THz 3.125GHz spacing";
           }
           enum "1576.71" {
             description "1576.71 nm/190.137500 THz 3.125/6.25/12.5GHz spacing";
           }
           enum "1576.69" {
             description "1576.69 nm/190.140625 THz 3.125GHz spacing";
           }
           enum "1576.66" {
             description "1576.66 nm/190.143750 THz 3.125/6.25GHz spacing";
           }
           enum "1576.64" {
             description "1576.64 nm/190.146875 THz 3.125GHz spacing";
           }
           enum "1576.61" {
             description "1576.61 nm/190.150000 THz 3.125/6.25/12.5/50GHz spacing";
           }
           enum "1576.58" {
             description "1576.58 nm/190.153125 THz 3.125GHz spacing";
           }
           enum "1576.56" {
             description "1576.56 nm/190.156250 THz 3.125/6.25GHz spacing";
           }
           enum "1576.53" {
             description "1576.53 nm/190.159375 THz 3.125GHz spacing";
           }
           enum "1576.51" {
             description "1576.51 nm/190.162500 THz 3.125/6.25/12.5GHz spacing";
           }
           enum "1576.48" {
             description "1576.48 nm/190.165625 THz 3.125GHz spacing";
           }
           enum "1576.45" {
             description "1576.45 nm/190.168750 THz 3.125/6.25GHz spacing";
           }
           enum "1576.43" {
             description "1576.43 nm/190.171875 THz 3.125GHz spacing";
           }
           enum "1576.40" {
             description "1576.40 nm/190.175000 THz 3.125/6.25/12.5/75GHz spacing";
           }
           enum "1576.38" {
             description "1576.38 nm/190.178125 THz 3.125GHz spacing";
           }
           enum "1576.35" {
             description "1576.35 nm/190.181250 THz 3.125/6.25GHz spacing";
           }
           enum "1576.33" {
             description "1576.33 nm/190.184375 THz 3.125GHz spacing";
           }
           enum "1576.30" {
             description "1576.30 nm/190.187500 THz 3.125/6.25/12.5GHz spacing";
           }
           enum "1576.27" {
             description "1576.27 nm/190.190625 THz 3.125GHz spacing";
           }
           enum "1576.25" {
             description "1576.25 nm/190.193750 THz 3.125/6.25GHz spacing";
           }
           enum "1576.22" {
             description "1576.22 nm/190.196875 THz 3.125GHz spacing";
           }
           enum "1576.20" {
             description "1576.20 nm/190.200000 THz 3.125/6.25/12.5/50/75/100GHz spacing";
           }
           enum "1576.17" {
             description "1576.17 nm/190.203125 THz 3.125GHz spacing";
           }
           enum "1576.14" {
             description "1576.14 nm/190.206250 THz 3.125/6.25GHz spacing";
           }
           enum "1576.12" {
             description "1576.12 nm/190.209375 THz 3.125GHz spacing";
           }
           enum "1576.09" {
             description "1576.09 nm/190.212500 THz 3.125/6.25/12.5GHz spacing";
           }
           enum "1576.07" {
             description "1576.07 nm/190.215625 THz 3.125GHz spacing";
           }
           enum "1576.04" {
             description "1576.04 nm/190.218750 THz 3.125/6.25GHz spacing";
           }
           enum "1576.01" {
             description "1576.01 nm/190.221875 THz 3.125GHz spacing";
           }
           enum "1575.99" {
             description "1575.99 nm/190.225000 THz 3.125/6.25/12.5GHz spacing";
           }
           enum "1575.96" {
             description "1575.96 nm/190.228125 THz 3.125GHz spacing";
           }
           enum "1575.94" {
             description "1575.94 nm/190.231250 THz 3.125/6.25GHz spacing";
           }
           enum "1575.91" {
             description "1575.91 nm/190.234375 THz 3.125GHz spacing";
           }
           enum "1575.89" {
             description "1575.89 nm/190.237500 THz 3.125/6.25/12.5GHz spacing";
           }
           enum "1575.86" {
             description "1575.86 nm/190.240625 THz 3.125GHz spacing";
           }
           enum "1575.83" {
             description "1575.83 nm/190.243750 THz 3.125/6.25GHz spacing";
           }
           enum "1575.81" {
             description "1575.81 nm/190.246875 THz 3.125GHz spacing";
           }
           enum "1575.78" {
             description "1575.78 nm/190.250000 THz 3.125/6.25/12.5/50/75GHz spacing";
           }
           enum "1575.76" {
             description "1575.76 nm/190.253125 THz 3.125GHz spacing";
           }
           enum "1575.73" {
             description "1575.73 nm/190.256250 THz 3.125/6.25GHz spacing";
           }
           enum "1575.70" {
             description "1575.70 nm/190.259375 THz 3.125GHz spacing";
           }
           enum "1575.68" {
             description "1575.68 nm/190.262500 THz 3.125/6.25/12.5GHz spacing";
           }
           enum "1575.65" {
             description "1575.65 nm/190.265625 THz 3.125GHz spacing";
           }
           enum "1575.63" {
             description "1575.63 nm/190.268750 THz 3.125/6.25GHz spacing";
           }
           enum "1575.60" {
             description "1575.60 nm/190.271875 THz 3.125GHz spacing";
           }
           enum "1575.57" {
             description "1575.57 nm/190.275000 THz 3.125/6.25/12.5GHz spacing";
           }
           enum "1575.55" {
             description "1575.55 nm/190.278125 THz 3.125GHz spacing";
           }
           enum "1575.52" {
             description "1575.52 nm/190.281250 THz 3.125/6.25GHz spacing";
           }
           enum "1575.50" {
             description "1575.50 nm/190.284375 THz 3.125GHz spacing";
           }
           enum "1575.47" {
             description "1575.47 nm/190.287500 THz 3.125/6.25/12.5GHz spacing";
           }
           enum "1575.45" {
             description "1575.45 nm/190.290625 THz 3.125GHz spacing";
           }
           enum "1575.42" {
             description "1575.42 nm/190.293750 THz 3.125/6.25GHz spacing";
           }
           enum "1575.39" {
             description "1575.39 nm/190.296875 THz 3.125GHz spacing";
           }
           enum "1575.37" {
             description "1575.37 nm/190.300000 THz 3.125/6.25/12.5/100GHz spacing";
           }
           enum "1575.34" {
             description "1575.34 nm/190.303125 THz 3.125GHz spacing";
           }
           enum "1575.32" {
             description "1575.32 nm/190.306250 THz 3.125/6.25GHz spacing";
           }
           enum "1575.29" {
             description "1575.29 nm/190.309375 THz 3.125GHz spacing";
           }
           enum "1575.26" {
             description "1575.26 nm/190.312500 THz 3.125/6.25/12.5GHz spacing";
           }
           enum "1575.24" {
             description "1575.24 nm/190.315625 THz 3.125GHz spacing";
           }
           enum "1575.21" {
             description "1575.21 nm/190.318750 THz 3.125/6.25GHz spacing";
           }
           enum "1575.19" {
             description "1575.19 nm/190.321875 THz 3.125GHz spacing";
           }
           enum "1575.16" {
             description "1575.16 nm/190.325000 THz 3.125/6.25/12.5/75GHz spacing";
           }
           enum "1575.13" {
             description "1575.13 nm/190.328125 THz 3.125GHz spacing";
           }
           enum "1575.11" {
             description "1575.11 nm/190.331250 THz 3.125/6.25GHz spacing";
           }
           enum "1575.08" {
             description "1575.08 nm/190.334375 THz 3.125GHz spacing";
           }
           enum "1575.06" {
             description "1575.06 nm/190.337500 THz 3.125/6.25/12.5GHz spacing";
           }
           enum "1575.03" {
             description "1575.03 nm/190.340625 THz 3.125GHz spacing";
           }
           enum "1575.01" {
             description "1575.01 nm/190.343750 THz 3.125/6.25GHz spacing";
           }
           enum "1574.98" {
             description "1574.98 nm/190.346875 THz 3.125GHz spacing";
           }
           enum "1574.95" {
             description "1574.95 nm/190.350000 THz 3.125/6.25/12.5/50GHz spacing";
           }
           enum "1574.93" {
             description "1574.93 nm/190.353125 THz 3.125GHz spacing";
           }
           enum "1574.90" {
             description "1574.90 nm/190.356250 THz 3.125/6.25GHz spacing";
           }
           enum "1574.88" {
             description "1574.88 nm/190.359375 THz 3.125GHz spacing";
           }
           enum "1574.85" {
             description "1574.85 nm/190.362500 THz 3.125/6.25/12.5GHz spacing";
           }
           enum "1574.82" {
             description "1574.82 nm/190.365625 THz 3.125GHz spacing";
           }
           enum "1574.80" {
             description "1574.80 nm/190.368750 THz 3.125/6.25GHz spacing";
           }
           enum "1574.77" {
             description "1574.77 nm/190.371875 THz 3.125GHz spacing";
           }
           enum "1574.75" {
             description "1574.75 nm/190.375000 THz 3.125/6.25/12.5GHz spacing";
           }
           enum "1574.72" {
             description "1574.72 nm/190.378125 THz 3.125GHz spacing";
           }
           enum "1574.70" {
             description "1574.70 nm/190.381250 THz 3.125/6.25GHz spacing";
           }
           enum "1574.67" {
             description "1574.67 nm/190.384375 THz 3.125GHz spacing";
           }
           enum "1574.64" {
             description "1574.64 nm/190.387500 THz 3.125/6.25/12.5GHz spacing";
           }
           enum "1574.62" {
             description "1574.62 nm/190.390625 THz 3.125GHz spacing";
           }
           enum "1574.59" {
             description "1574.59 nm/190.393750 THz 3.125/6.25GHz spacing";
           }
           enum "1574.57" {
             description "1574.57 nm/190.396875 THz 3.125GHz spacing";
           }
           enum "1574.54" {
             description "1574.54 nm/190.400000 THz 3.125/6.25/12.5/100GHz spacing";
           }
           enum "1574.51" {
             description "1574.51 nm/190.403125 THz 3.125GHz spacing";
           }
           enum "1574.49" {
             description "1574.49 nm/190.406250 THz 3.125/6.25GHz spacing";
           }
           enum "1574.46" {
             description "1574.46 nm/190.409375 THz 3.125GHz spacing";
           }
           enum "1574.44" {
             description "1574.44 nm/190.412500 THz 3.125/6.25/12.5GHz spacing";
           }
           enum "1574.41" {
             description "1574.41 nm/190.415625 THz 3.125GHz spacing";
           }
           enum "1574.39" {
             description "1574.39 nm/190.418750 THz 3.125/6.25GHz spacing";
           }
           enum "1574.36" {
             description "1574.36 nm/190.421875 THz 3.125GHz spacing";
           }
           enum "1574.33" {
             description "1574.33 nm/190.425000 THz 3.125/6.25/12.5GHz spacing";
           }
           enum "1574.31" {
             description "1574.31 nm/190.428125 THz 3.125GHz spacing";
           }
           enum "1574.28" {
             description "1574.28 nm/190.431250 THz 3.125/6.25GHz spacing";
           }
           enum "1574.26" {
             description "1574.26 nm/190.434375 THz 3.125GHz spacing";
           }
           enum "1574.23" {
             description "1574.23 nm/190.437500 THz 3.125/6.25/12.5GHz spacing";
           }
           enum "1574.20" {
             description "1574.20 nm/190.440625 THz 3.125GHz spacing";
           }
           enum "1574.18" {
             description "1574.18 nm/190.443750 THz 3.125/6.25GHz spacing";
           }
           enum "1574.15" {
             description "1574.15 nm/190.446875 THz 3.125GHz spacing";
           }
           enum "1574.13" {
             description "1574.13 nm/190.450000 THz 3.125/6.25/12.5/50GHz spacing";
           }
           enum "1574.10" {
             description "1574.10 nm/190.453125 THz 3.125GHz spacing";
           }
           enum "1574.08" {
             description "1574.08 nm/190.456250 THz 3.125/6.25GHz spacing";
           }
           enum "1574.05" {
             description "1574.05 nm/190.459375 THz 3.125GHz spacing";
           }
           enum "1574.02" {
             description "1574.02 nm/190.462500 THz 3.125/6.25/12.5GHz spacing";
           }
           enum "1574.00" {
             description "1574.00 nm/190.465625 THz 3.125GHz spacing";
           }
           enum "1573.97" {
             description "1573.97 nm/190.468750 THz 3.125/6.25GHz spacing";
           }
           enum "1573.95" {
             description "1573.95 nm/190.471875 THz 3.125GHz spacing";
           }
           enum "1573.92" {
             description "1573.92 nm/190.475000 THz 3.125/6.25/12.5/75GHz spacing";
           }
           enum "1573.89" {
             description "1573.89 nm/190.478125 THz 3.125GHz spacing";
           }
           enum "1573.87" {
             description "1573.87 nm/190.481250 THz 3.125/6.25GHz spacing";
           }
           enum "1573.84" {
             description "1573.84 nm/190.484375 THz 3.125GHz spacing";
           }
           enum "1573.82" {
             description "1573.82 nm/190.487500 THz 3.125/6.25/12.5GHz spacing";
           }
           enum "1573.79" {
             description "1573.79 nm/190.490625 THz 3.125GHz spacing";
           }
           enum "1573.77" {
             description "1573.77 nm/190.493750 THz 3.125/6.25GHz spacing";
           }
           enum "1573.74" {
             description "1573.74 nm/190.496875 THz 3.125GHz spacing";
           }
           enum "1573.71" {
             description "1573.71 nm/190.500000 THz 3.125/6.25/12.5/50/75/100GHz spacing";
           }
           enum "1573.69" {
             description "1573.69 nm/190.503125 THz 3.125GHz spacing";
           }
           enum "1573.66" {
             description "1573.66 nm/190.506250 THz 3.125/6.25GHz spacing";
           }
           enum "1573.64" {
             description "1573.64 nm/190.509375 THz 3.125GHz spacing";
           }
           enum "1573.61" {
             description "1573.61 nm/190.512500 THz 3.125/6.25/12.5GHz spacing";
           }
           enum "1573.58" {
             description "1573.58 nm/190.515625 THz 3.125GHz spacing";
           }
           enum "1573.56" {
             description "1573.56 nm/190.518750 THz 3.125/6.25GHz spacing";
           }
           enum "1573.53" {
             description "1573.53 nm/190.521875 THz 3.125GHz spacing";
           }
           enum "1573.51" {
             description "1573.51 nm/190.525000 THz 3.125/6.25/12.5GHz spacing";
           }
           enum "1573.48" {
             description "1573.48 nm/190.528125 THz 3.125GHz spacing";
           }
           enum "1573.46" {
             description "1573.46 nm/190.531250 THz 3.125/6.25GHz spacing";
           }
           enum "1573.43" {
             description "1573.43 nm/190.534375 THz 3.125GHz spacing";
           }
           enum "1573.40" {
             description "1573.40 nm/190.537500 THz 3.125/6.25/12.5GHz spacing";
           }
           enum "1573.38" {
             description "1573.38 nm/190.540625 THz 3.125GHz spacing";
           }
           enum "1573.35" {
             description "1573.35 nm/190.543750 THz 3.125/6.25GHz spacing";
           }
           enum "1573.33" {
             description "1573.33 nm/190.546875 THz 3.125GHz spacing";
           }
           enum "1573.30" {
             description "1573.30 nm/190.550000 THz 3.125/6.25/12.5/50/75GHz spacing";
           }
           enum "1573.27" {
             description "1573.27 nm/190.553125 THz 3.125GHz spacing";
           }
           enum "1573.25" {
             description "1573.25 nm/190.556250 THz 3.125/6.25GHz spacing";
           }
           enum "1573.22" {
             description "1573.22 nm/190.559375 THz 3.125GHz spacing";
           }
           enum "1573.20" {
             description "1573.20 nm/190.562500 THz 3.125/6.25/12.5GHz spacing";
           }
           enum "1573.17" {
             description "1573.17 nm/190.565625 THz 3.125GHz spacing";
           }
           enum "1573.15" {
             description "1573.15 nm/190.568750 THz 3.125/6.25GHz spacing";
           }
           enum "1573.12" {
             description "1573.12 nm/190.571875 THz 3.125GHz spacing";
           }
           enum "1573.09" {
             description "1573.09 nm/190.575000 THz 3.125/6.25/12.5GHz spacing";
           }
           enum "1573.07" {
             description "1573.07 nm/190.578125 THz 3.125GHz spacing";
           }
           enum "1573.04" {
             description "1573.04 nm/190.581250 THz 3.125/6.25GHz spacing";
           }
           enum "1573.02" {
             description "1573.02 nm/190.584375 THz 3.125GHz spacing";
           }
           enum "1572.99" {
             description "1572.99 nm/190.587500 THz 3.125/6.25/12.5GHz spacing";
           }
           enum "1572.97" {
             description "1572.97 nm/190.590625 THz 3.125GHz spacing";
           }
           enum "1572.94" {
             description "1572.94 nm/190.593750 THz 3.125/6.25GHz spacing";
           }
           enum "1572.91" {
             description "1572.91 nm/190.596875 THz 3.125GHz spacing";
           }
           enum "1572.89" {
             description "1572.89 nm/190.600000 THz 3.125/6.25/12.5/100GHz spacing";
           }
           enum "1572.86" {
             description "1572.86 nm/190.603125 THz 3.125GHz spacing";
           }
           enum "1572.84" {
             description "1572.84 nm/190.606250 THz 3.125/6.25GHz spacing";
           }
           enum "1572.81" {
             description "1572.81 nm/190.609375 THz 3.125GHz spacing";
           }
           enum "1572.78" {
             description "1572.78 nm/190.612500 THz 3.125/6.25/12.5GHz spacing";
           }
           enum "1572.76" {
             description "1572.76 nm/190.615625 THz 3.125GHz spacing";
           }
           enum "1572.73" {
             description "1572.73 nm/190.618750 THz 3.125/6.25GHz spacing";
           }
           enum "1572.71" {
             description "1572.71 nm/190.621875 THz 3.125GHz spacing";
           }
           enum "1572.68" {
             description "1572.68 nm/190.625000 THz 3.125/6.25/12.5/75GHz spacing";
           }
           enum "1572.66" {
             description "1572.66 nm/190.628125 THz 3.125GHz spacing";
           }
           enum "1572.63" {
             description "1572.63 nm/190.631250 THz 3.125/6.25GHz spacing";
           }
           enum "1572.60" {
             description "1572.60 nm/190.634375 THz 3.125GHz spacing";
           }
           enum "1572.58" {
             description "1572.58 nm/190.637500 THz 3.125/6.25/12.5GHz spacing";
           }
           enum "1572.55" {
             description "1572.55 nm/190.640625 THz 3.125GHz spacing";
           }
           enum "1572.53" {
             description "1572.53 nm/190.643750 THz 3.125/6.25GHz spacing";
           }
           enum "1572.50" {
             description "1572.50 nm/190.646875 THz 3.125GHz spacing";
           }
           enum "1572.48" {
             description "1572.48 nm/190.650000 THz 3.125/6.25/12.5/50GHz spacing";
           }
           enum "1572.45" {
             description "1572.45 nm/190.653125 THz 3.125GHz spacing";
           }
           enum "1572.42" {
             description "1572.42 nm/190.656250 THz 3.125/6.25GHz spacing";
           }
           enum "1572.40" {
             description "1572.40 nm/190.659375 THz 3.125GHz spacing";
           }
           enum "1572.37" {
             description "1572.37 nm/190.662500 THz 3.125/6.25/12.5GHz spacing";
           }
           enum "1572.35" {
             description "1572.35 nm/190.665625 THz 3.125GHz spacing";
           }
           enum "1572.32" {
             description "1572.32 nm/190.668750 THz 3.125/6.25GHz spacing";
           }
           enum "1572.30" {
             description "1572.30 nm/190.671875 THz 3.125GHz spacing";
           }
           enum "1572.27" {
             description "1572.27 nm/190.675000 THz 3.125/6.25/12.5GHz spacing";
           }
           enum "1572.24" {
             description "1572.24 nm/190.678125 THz 3.125GHz spacing";
           }
           enum "1572.22" {
             description "1572.22 nm/190.681250 THz 3.125/6.25GHz spacing";
           }
           enum "1572.19" {
             description "1572.19 nm/190.684375 THz 3.125GHz spacing";
           }
           enum "1572.17" {
             description "1572.17 nm/190.687500 THz 3.125/6.25/12.5GHz spacing";
           }
           enum "1572.14" {
             description "1572.14 nm/190.690625 THz 3.125GHz spacing";
           }
           enum "1572.11" {
             description "1572.11 nm/190.693750 THz 3.125/6.25GHz spacing";
           }
           enum "1572.09" {
             description "1572.09 nm/190.696875 THz 3.125GHz spacing";
           }
           enum "1572.06" {
             description "1572.06 nm/190.700000 THz 3.125/6.25/12.5/100GHz spacing";
           }
           enum "1572.04" {
             description "1572.04 nm/190.703125 THz 3.125GHz spacing";
           }
           enum "1572.01" {
             description "1572.01 nm/190.706250 THz 3.125/6.25GHz spacing";
           }
           enum "1571.99" {
             description "1571.99 nm/190.709375 THz 3.125GHz spacing";
           }
           enum "1571.96" {
             description "1571.96 nm/190.712500 THz 3.125/6.25/12.5GHz spacing";
           }
           enum "1571.93" {
             description "1571.93 nm/190.715625 THz 3.125GHz spacing";
           }
           enum "1571.91" {
             description "1571.91 nm/190.718750 THz 3.125/6.25GHz spacing";
           }
           enum "1571.88" {
             description "1571.88 nm/190.721875 THz 3.125GHz spacing";
           }
           enum "1571.86" {
             description "1571.86 nm/190.725000 THz 3.125/6.25/12.5GHz spacing";
           }
           enum "1571.83" {
             description "1571.83 nm/190.728125 THz 3.125GHz spacing";
           }
           enum "1571.81" {
             description "1571.81 nm/190.731250 THz 3.125/6.25GHz spacing";
           }
           enum "1571.78" {
             description "1571.78 nm/190.734375 THz 3.125GHz spacing";
           }
           enum "1571.75" {
             description "1571.75 nm/190.737500 THz 3.125/6.25/12.5GHz spacing";
           }
           enum "1571.73" {
             description "1571.73 nm/190.740625 THz 3.125GHz spacing";
           }
           enum "1571.70" {
             description "1571.70 nm/190.743750 THz 3.125/6.25GHz spacing";
           }
           enum "1571.68" {
             description "1571.68 nm/190.746875 THz 3.125GHz spacing";
           }
           enum "1571.65" {
             description "1571.65 nm/190.750000 THz 3.125/6.25/12.5/50GHz spacing";
           }
           enum "1571.63" {
             description "1571.63 nm/190.753125 THz 3.125GHz spacing";
           }
           enum "1571.60" {
             description "1571.60 nm/190.756250 THz 3.125/6.25GHz spacing";
           }
           enum "1571.57" {
             description "1571.57 nm/190.759375 THz 3.125GHz spacing";
           }
           enum "1571.55" {
             description "1571.55 nm/190.762500 THz 3.125/6.25/12.5GHz spacing";
           }
           enum "1571.52" {
             description "1571.52 nm/190.765625 THz 3.125GHz spacing";
           }
           enum "1571.50" {
             description "1571.50 nm/190.768750 THz 3.125/6.25GHz spacing";
           }
           enum "1571.47" {
             description "1571.47 nm/190.771875 THz 3.125GHz spacing";
           }
           enum "1571.45" {
             description "1571.45 nm/190.775000 THz 3.125/6.25/12.5/75GHz spacing";
           }
           enum "1571.42" {
             description "1571.42 nm/190.778125 THz 3.125GHz spacing";
           }
           enum "1571.39" {
             description "1571.39 nm/190.781250 THz 3.125/6.25GHz spacing";
           }
           enum "1571.37" {
             description "1571.37 nm/190.784375 THz 3.125GHz spacing";
           }
           enum "1571.34" {
             description "1571.34 nm/190.787500 THz 3.125/6.25/12.5GHz spacing";
           }
           enum "1571.32" {
             description "1571.32 nm/190.790625 THz 3.125GHz spacing";
           }
           enum "1571.29" {
             description "1571.29 nm/190.793750 THz 3.125/6.25GHz spacing";
           }
           enum "1571.27" {
             description "1571.27 nm/190.796875 THz 3.125GHz spacing";
           }
           enum "1571.24" {
             description "1571.24 nm/190.800000 THz 3.125/6.25/12.5/50/75/100GHz spacing";
           }
           enum "1571.21" {
             description "1571.21 nm/190.803125 THz 3.125GHz spacing";
           }
           enum "1571.19" {
             description "1571.19 nm/190.806250 THz 3.125/6.25GHz spacing";
           }
           enum "1571.16" {
             description "1571.16 nm/190.809375 THz 3.125GHz spacing";
           }
           enum "1571.14" {
             description "1571.14 nm/190.812500 THz 3.125/6.25/12.5GHz spacing";
           }
           enum "1571.11" {
             description "1571.11 nm/190.815625 THz 3.125GHz spacing";
           }
           enum "1571.08" {
             description "1571.08 nm/190.818750 THz 3.125/6.25GHz spacing";
           }
           enum "1571.06" {
             description "1571.06 nm/190.821875 THz 3.125GHz spacing";
           }
           enum "1571.03" {
             description "1571.03 nm/190.825000 THz 3.125/6.25/12.5GHz spacing";
           }
           enum "1571.01" {
             description "1571.01 nm/190.828125 THz 3.125GHz spacing";
           }
           enum "1570.98" {
             description "1570.98 nm/190.831250 THz 3.125/6.25GHz spacing";
           }
           enum "1570.96" {
             description "1570.96 nm/190.834375 THz 3.125GHz spacing";
           }
           enum "1570.93" {
             description "1570.93 nm/190.837500 THz 3.125/6.25/12.5GHz spacing";
           }
           enum "1570.90" {
             description "1570.90 nm/190.840625 THz 3.125GHz spacing";
           }
           enum "1570.88" {
             description "1570.88 nm/190.843750 THz 3.125/6.25GHz spacing";
           }
           enum "1570.85" {
             description "1570.85 nm/190.846875 THz 3.125GHz spacing";
           }
           enum "1570.83" {
             description "1570.83 nm/190.850000 THz 3.125/6.25/12.5/50/75GHz spacing";
           }
           enum "1570.80" {
             description "1570.80 nm/190.853125 THz 3.125GHz spacing";
           }
           enum "1570.78" {
             description "1570.78 nm/190.856250 THz 3.125/6.25GHz spacing";
           }
           enum "1570.75" {
             description "1570.75 nm/190.859375 THz 3.125GHz spacing";
           }
           enum "1570.72" {
             description "1570.72 nm/190.862500 THz 3.125/6.25/12.5GHz spacing";
           }
           enum "1570.70" {
             description "1570.70 nm/190.865625 THz 3.125GHz spacing";
           }
           enum "1570.67" {
             description "1570.67 nm/190.868750 THz 3.125/6.25GHz spacing";
           }
           enum "1570.65" {
             description "1570.65 nm/190.871875 THz 3.125GHz spacing";
           }
           enum "1570.62" {
             description "1570.62 nm/190.875000 THz 3.125/6.25/12.5GHz spacing";
           }
           enum "1570.60" {
             description "1570.60 nm/190.878125 THz 3.125GHz spacing";
           }
           enum "1570.57" {
             description "1570.57 nm/190.881250 THz 3.125/6.25GHz spacing";
           }
           enum "1570.54" {
             description "1570.54 nm/190.884375 THz 3.125GHz spacing";
           }
           enum "1570.52" {
             description "1570.52 nm/190.887500 THz 3.125/6.25/12.5GHz spacing";
           }
           enum "1570.49" {
             description "1570.49 nm/190.890625 THz 3.125GHz spacing";
           }
           enum "1570.47" {
             description "1570.47 nm/190.893750 THz 3.125/6.25GHz spacing";
           }
           enum "1570.44" {
             description "1570.44 nm/190.896875 THz 3.125GHz spacing";
           }
           enum "1570.42" {
             description "1570.42 nm/190.900000 THz 3.125/6.25/12.5/100GHz spacing";
           }
           enum "1570.39" {
             description "1570.39 nm/190.903125 THz 3.125GHz spacing";
           }
           enum "1570.36" {
             description "1570.36 nm/190.906250 THz 3.125/6.25GHz spacing";
           }
           enum "1570.34" {
             description "1570.34 nm/190.909375 THz 3.125GHz spacing";
           }
           enum "1570.31" {
             description "1570.31 nm/190.912500 THz 3.125/6.25/12.5GHz spacing";
           }
           enum "1570.29" {
             description "1570.29 nm/190.915625 THz 3.125GHz spacing";
           }
           enum "1570.26" {
             description "1570.26 nm/190.918750 THz 3.125/6.25GHz spacing";
           }
           enum "1570.24" {
             description "1570.24 nm/190.921875 THz 3.125GHz spacing";
           }
           enum "1570.21" {
             description "1570.21 nm/190.925000 THz 3.125/6.25/12.5/75GHz spacing";
           }
           enum "1570.18" {
             description "1570.18 nm/190.928125 THz 3.125GHz spacing";
           }
           enum "1570.16" {
             description "1570.16 nm/190.931250 THz 3.125/6.25GHz spacing";
           }
           enum "1570.13" {
             description "1570.13 nm/190.934375 THz 3.125GHz spacing";
           }
           enum "1570.11" {
             description "1570.11 nm/190.937500 THz 3.125/6.25/12.5GHz spacing";
           }
           enum "1570.08" {
             description "1570.08 nm/190.940625 THz 3.125GHz spacing";
           }
           enum "1570.06" {
             description "1570.06 nm/190.943750 THz 3.125/6.25GHz spacing";
           }
           enum "1570.03" {
             description "1570.03 nm/190.946875 THz 3.125GHz spacing";
           }
           enum "1570.01" {
             description "1570.01 nm/190.950000 THz 3.125/6.25/12.5/50GHz spacing";
           }
           enum "1569.98" {
             description "1569.98 nm/190.953125 THz 3.125GHz spacing";
           }
           enum "1569.95" {
             description "1569.95 nm/190.956250 THz 3.125/6.25GHz spacing";
           }
           enum "1569.93" {
             description "1569.93 nm/190.959375 THz 3.125GHz spacing";
           }
           enum "1569.90" {
             description "1569.90 nm/190.962500 THz 3.125/6.25/12.5GHz spacing";
           }
           enum "1569.88" {
             description "1569.88 nm/190.965625 THz 3.125GHz spacing";
           }
           enum "1569.85" {
             description "1569.85 nm/190.968750 THz 3.125/6.25GHz spacing";
           }
           enum "1569.83" {
             description "1569.83 nm/190.971875 THz 3.125GHz spacing";
           }
           enum "1569.80" {
             description "1569.80 nm/190.975000 THz 3.125/6.25/12.5GHz spacing";
           }
           enum "1569.77" {
             description "1569.77 nm/190.978125 THz 3.125GHz spacing";
           }
           enum "1569.75" {
             description "1569.75 nm/190.981250 THz 3.125/6.25GHz spacing";
           }
           enum "1569.72" {
             description "1569.72 nm/190.984375 THz 3.125GHz spacing";
           }
           enum "1569.70" {
             description "1569.70 nm/190.987500 THz 3.125/6.25/12.5GHz spacing";
           }
           enum "1569.67" {
             description "1569.67 nm/190.990625 THz 3.125GHz spacing";
           }
           enum "1569.65" {
             description "1569.65 nm/190.993750 THz 3.125/6.25GHz spacing";
           }
           enum "1569.62" {
             description "1569.62 nm/190.996875 THz 3.125GHz spacing";
           }
           enum "1569.59" {
             description "1569.59 nm/191.000000 THz 3.125/6.25/12.5/100GHz spacing";
           }
           enum "1568.77" {
             description "1568.77 nm/191.1003 THz 50/100Ghz spacing";
           }
           enum "1568.36" {
             description "1568.36 nm/191.150000 THz 3.125/6.25/12.5/50/75GHz spacing";
           }
           enum "1568.34" {
             description "1568.34 nm/191.153125 THz 3.125GHz spacing";
           }
           enum "1568.31" {
             description "1568.31 nm/191.156250 THz 3.125/6.25GHz spacing";
           }
           enum "1568.29" {
             description "1568.29 nm/191.159375 THz 3.125GHz spacing";
           }
           enum "1568.26" {
             description "1568.26 nm/191.162500 THz 3.125/6.25/12.5GHz spacing";
           }
           enum "1568.23" {
             description "1568.23 nm/191.165625 THz 3.125GHz spacing";
           }
           enum "1568.21" {
             description "1568.21 nm/191.168750 THz 3.125/6.25GHz spacing";
           }
           enum "1568.18" {
             description "1568.18 nm/191.171875 THz 3.125GHz spacing";
           }
           enum "1568.16" {
             description "1568.16 nm/191.175000 THz 3.125/6.25/12.5/75GHz spacing";
           }
           enum "1568.13" {
             description "1568.13 nm/191.178125 THz 3.125GHz spacing";
           }
           enum "1568.11" {
             description "1568.11 nm/191.181250 THz 3.125/6.25GHz spacing";
           }
           enum "1568.08" {
             description "1568.08 nm/191.184375 THz 3.125GHz spacing";
           }
           enum "1568.05" {
             description "1568.05 nm/191.187500 THz 3.125/6.25/12.5GHz spacing";
           }
           enum "1568.03" {
             description "1568.03 nm/191.190625 THz 3.125GHz spacing";
           }
           enum "1568.00" {
             description "1568.00 nm/191.193750 THz 3.125/6.25GHz spacing";
           }
           enum "1567.98" {
             description "1567.98 nm/191.196875 THz 3.125GHz spacing";
           }
           enum "1567.95" {
             description "1567.95 nm/191.200000 THz 3.125/6.25/12.5/100GHz spacing";
           }
           enum "1567.93" {
             description "1567.93 nm/191.203125 THz 3.125GHz spacing";
           }
           enum "1567.90" {
             description "1567.90 nm/191.206250 THz 3.125/6.25GHz spacing";
           }
           enum "1567.88" {
             description "1567.88 nm/191.209375 THz 3.125GHz spacing";
           }
           enum "1567.85" {
             description "1567.85 nm/191.212500 THz 3.125/6.25/12.5GHz spacing";
           }
           enum "1567.82" {
             description "1567.82 nm/191.215625 THz 3.125GHz spacing";
           }
           enum "1567.80" {
             description "1567.80 nm/191.218750 THz 3.125/6.25GHz spacing";
           }
           enum "1567.77" {
             description "1567.77 nm/191.221875 THz 3.125GHz spacing";
           }
           enum "1567.75" {
             description "1567.75 nm/191.225000 THz 3.125/6.25/12.5/75GHz spacing";
           }
           enum "1567.72" {
             description "1567.72 nm/191.228125 THz 3.125GHz spacing";
           }
           enum "1567.70" {
             description "1567.70 nm/191.231250 THz 3.125/6.25GHz spacing";
           }
           enum "1567.67" {
             description "1567.67 nm/191.234375 THz 3.125GHz spacing";
           }
           enum "1567.64" {
             description "1567.64 nm/191.237500 THz 3.125/6.25/12.5GHz spacing";
           }
           enum "1567.62" {
             description "1567.62 nm/191.240625 THz 3.125GHz spacing";
           }
           enum "1567.59" {
             description "1567.59 nm/191.243750 THz 3.125/6.25GHz spacing";
           }
           enum "1567.57" {
             description "1567.57 nm/191.246875 THz 3.125GHz spacing";
           }
           enum "1567.54" {
             description "1567.54 nm/191.250000 THz 3.125/6.25/12.5/50/75GHz spacing";
           }
           enum "1567.52" {
             description "1567.52 nm/191.253125 THz 3.125GHz spacing";
           }
           enum "1567.49" {
             description "1567.49 nm/191.256250 THz 3.125/6.25GHz spacing";
           }
           enum "1567.47" {
             description "1567.47 nm/191.259375 THz 3.125GHz spacing";
           }
           enum "1567.44" {
             description "1567.44 nm/191.262500 THz 3.125/6.25/12.5GHz spacing";
           }
           enum "1567.41" {
             description "1567.41 nm/191.265625 THz 3.125GHz spacing";
           }
           enum "1567.39" {
             description "1567.39 nm/191.268750 THz 3.125/6.25GHz spacing";
           }
           enum "1567.36" {
             description "1567.36 nm/191.271875 THz 3.125GHz spacing";
           }
           enum "1567.34" {
             description "1567.34 nm/191.275000 THz 3.125/6.25/12.5GHz spacing";
           }
           enum "1567.31" {
             description "1567.31 nm/191.278125 THz 3.125GHz spacing";
           }
           enum "1567.29" {
             description "1567.29 nm/191.281250 THz 3.125/6.25GHz spacing";
           }
           enum "1567.26" {
             description "1567.26 nm/191.284375 THz 3.125GHz spacing";
           }
           enum "1567.23" {
             description "1567.23 nm/191.287500 THz 3.125/6.25/12.5GHz spacing";
           }
           enum "1567.21" {
             description "1567.21 nm/191.290625 THz 3.125GHz spacing";
           }
           enum "1567.18" {
             description "1567.18 nm/191.293750 THz 3.125/6.25GHz spacing";
           }
           enum "1567.16" {
             description "1567.16 nm/191.296875 THz 3.125GHz spacing";
           }
           enum "1567.13" {
             description "1567.13 nm/191.300000 THz 3.125/6.25/12.5/100GHz spacing";
           }
           enum "1567.11" {
             description "1567.11 nm/191.303125 THz 3.125GHz spacing";
           }
           enum "1567.08" {
             description "1567.08 nm/191.306250 THz 3.125/6.25GHz spacing";
           }
           enum "1567.06" {
             description "1567.06 nm/191.309375 THz 3.125GHz spacing";
           }
           enum "1567.03" {
             description "1567.03 nm/191.312500 THz 3.125/6.25/12.5GHz spacing";
           }
           enum "1567.00" {
             description "1567.00 nm/191.315625 THz 3.125GHz spacing";
           }
           enum "1566.98" {
             description "1566.98 nm/191.318750 THz 3.125/6.25GHz spacing";
           }
           enum "1566.95" {
             description "1566.95 nm/191.321875 THz 3.125GHz spacing";
           }
           enum "1566.93" {
             description "1566.93 nm/191.325000 THz 3.125/6.25/12.5/75GHz spacing";
           }
           enum "1566.90" {
             description "1566.90 nm/191.328125 THz 3.125GHz spacing";
           }
           enum "1566.88" {
             description "1566.88 nm/191.331250 THz 3.125/6.25GHz spacing";
           }
           enum "1566.85" {
             description "1566.85 nm/191.334375 THz 3.125GHz spacing";
           }
           enum "1566.83" {
             description "1566.83 nm/191.337500 THz 3.125/6.25/12.5GHz spacing";
           }
           enum "1566.80" {
             description "1566.80 nm/191.340625 THz 3.125GHz spacing";
           }
           enum "1566.77" {
             description "1566.77 nm/191.343750 THz 3.125/6.25GHz spacing";
           }
           enum "1566.75" {
             description "1566.75 nm/191.346875 THz 3.125GHz spacing";
           }
           enum "1566.72" {
             description "1566.72 nm/191.350000 THz 3.125/6.25/12.5/50GHz spacing";
           }
           enum "1566.70" {
             description "1566.70 nm/191.353125 THz 3.125GHz spacing";
           }
           enum "1566.67" {
             description "1566.67 nm/191.356250 THz 3.125/6.25GHz spacing";
           }
           enum "1566.65" {
             description "1566.65 nm/191.359375 THz 3.125GHz spacing";
           }
           enum "1566.62" {
             description "1566.62 nm/191.362500 THz 3.125/6.25/12.5GHz spacing";
           }
           enum "1566.60" {
             description "1566.60 nm/191.365625 THz 3.125GHz spacing";
           }
           enum "1566.57" {
             description "1566.57 nm/191.368750 THz 3.125/6.25GHz spacing";
           }
           enum "1566.54" {
             description "1566.54 nm/191.371875 THz 3.125GHz spacing";
           }
           enum "1566.52" {
             description "1566.52 nm/191.375000 THz 3.125/6.25/12.5GHz spacing";
           }
           enum "1566.49" {
             description "1566.49 nm/191.378125 THz 3.125GHz spacing";
           }
           enum "1566.47" {
             description "1566.47 nm/191.381250 THz 3.125/6.25GHz spacing";
           }
           enum "1566.44" {
             description "1566.44 nm/191.384375 THz 3.125GHz spacing";
           }
           enum "1566.42" {
             description "1566.42 nm/191.387500 THz 3.125/6.25/12.5GHz spacing";
           }
           enum "1566.39" {
             description "1566.39 nm/191.390625 THz 3.125GHz spacing";
           }
           enum "1566.36" {
             description "1566.36 nm/191.393750 THz 3.125/6.25GHz spacing";
           }
           enum "1566.34" {
             description "1566.34 nm/191.396875 THz 3.125GHz spacing";
           }
           enum "1566.31" {
             description "1566.31 nm/191.400000 THz 3.125/6.25/12.5/50/75/100GHz spacing";
           }
           enum "1566.29" {
             description "1566.29 nm/191.403125 THz 3.125GHz spacing";
           }
           enum "1566.26" {
             description "1566.26 nm/191.406250 THz 3.125/6.25GHz spacing";
           }
           enum "1566.24" {
             description "1566.24 nm/191.409375 THz 3.125GHz spacing";
           }
           enum "1566.21" {
             description "1566.21 nm/191.412500 THz 3.125/6.25/12.5GHz spacing";
           }
           enum "1566.19" {
             description "1566.19 nm/191.415625 THz 3.125GHz spacing";
           }
           enum "1566.16" {
             description "1566.16 nm/191.418750 THz 3.125/6.25GHz spacing";
           }
           enum "1566.13" {
             description "1566.13 nm/191.421875 THz 3.125GHz spacing";
           }
           enum "1566.11" {
             description "1566.11 nm/191.425000 THz 3.125/6.25/12.5GHz spacing";
           }
           enum "1566.08" {
             description "1566.08 nm/191.428125 THz 3.125GHz spacing";
           }
           enum "1566.06" {
             description "1566.06 nm/191.431250 THz 3.125/6.25GHz spacing";
           }
           enum "1566.03" {
             description "1566.03 nm/191.434375 THz 3.125GHz spacing";
           }
           enum "1566.01" {
             description "1566.01 nm/191.437500 THz 3.125/6.25/12.5GHz spacing";
           }
           enum "1565.98" {
             description "1565.98 nm/191.440625 THz 3.125GHz spacing";
           }
           enum "1565.96" {
             description "1565.96 nm/191.443750 THz 3.125/6.25GHz spacing";
           }
           enum "1565.93" {
             description "1565.93 nm/191.446875 THz 3.125GHz spacing";
           }
           enum "1565.90" {
             description "1565.90 nm/191.450000 THz 3.125/6.25/12.5/50GHz spacing";
           }
           enum "1565.88" {
             description "1565.88 nm/191.453125 THz 3.125GHz spacing";
           }
           enum "1565.85" {
             description "1565.85 nm/191.456250 THz 3.125/6.25GHz spacing";
           }
           enum "1565.83" {
             description "1565.83 nm/191.459375 THz 3.125GHz spacing";
           }
           enum "1565.80" {
             description "1565.80 nm/191.462500 THz 3.125/6.25/12.5GHz spacing";
           }
           enum "1565.78" {
             description "1565.78 nm/191.465625 THz 3.125GHz spacing";
           }
           enum "1565.75" {
             description "1565.75 nm/191.468750 THz 3.125/6.25GHz spacing";
           }
           enum "1565.73" {
             description "1565.73 nm/191.471875 THz 3.125GHz spacing";
           }
           enum "1565.70" {
             description "1565.70 nm/191.475000 THz 3.125/6.25/12.5/75GHz spacing";
           }
           enum "1565.67" {
             description "1565.67 nm/191.478125 THz 3.125GHz spacing";
           }
           enum "1565.65" {
             description "1565.65 nm/191.481250 THz 3.125/6.25GHz spacing";
           }
           enum "1565.62" {
             description "1565.62 nm/191.484375 THz 3.125GHz spacing";
           }
           enum "1565.60" {
             description "1565.60 nm/191.487500 THz 3.125/6.25/12.5GHz spacing";
           }
           enum "1565.57" {
             description "1565.57 nm/191.490625 THz 3.125GHz spacing";
           }
           enum "1565.55" {
             description "1565.55 nm/191.493750 THz 3.125/6.25GHz spacing";
           }
           enum "1565.52" {
             description "1565.52 nm/191.496875 THz 3.125GHz spacing";
           }
           enum "1565.50" {
             description "1565.50 nm/191.500000 THz 3.125/6.25/12.5/100GHz spacing";
           }
           enum "1565.47" {
             description "1565.47 nm/191.503125 THz 3.125GHz spacing";
           }
           enum "1565.44" {
             description "1565.44 nm/191.506250 THz 3.125/6.25GHz spacing";
           }
           enum "1565.42" {
             description "1565.42 nm/191.509375 THz 3.125GHz spacing";
           }
           enum "1565.39" {
             description "1565.39 nm/191.512500 THz 3.125/6.25/12.5GHz spacing";
           }
           enum "1565.37" {
             description "1565.37 nm/191.515625 THz 3.125GHz spacing";
           }
           enum "1565.34" {
             description "1565.34 nm/191.518750 THz 3.125/6.25GHz spacing";
           }
           enum "1565.32" {
             description "1565.32 nm/191.521875 THz 3.125GHz spacing";
           }
           enum "1565.29" {
             description "1565.29 nm/191.525000 THz 3.125/6.25/12.5GHz spacing";
           }
           enum "1565.27" {
             description "1565.27 nm/191.528125 THz 3.125GHz spacing";
           }
           enum "1565.24" {
             description "1565.24 nm/191.531250 THz 3.125/6.25GHz spacing";
           }
           enum "1565.21" {
             description "1565.21 nm/191.534375 THz 3.125GHz spacing";
           }
           enum "1565.19" {
             description "1565.19 nm/191.537500 THz 3.125/6.25/12.5GHz spacing";
           }
           enum "1565.16" {
             description "1565.16 nm/191.540625 THz 3.125GHz spacing";
           }
           enum "1565.14" {
             description "1565.14 nm/191.543750 THz 3.125/6.25GHz spacing";
           }
           enum "1565.11" {
             description "1565.11 nm/191.546875 THz 3.125GHz spacing";
           }
           enum "1565.09" {
             description "1565.09 nm/191.550000 THz 3.125/6.25/12.5/50/75GHz spacing";
           }
           enum "1565.06" {
             description "1565.06 nm/191.553125 THz 3.125GHz spacing";
           }
           enum "1565.04" {
             description "1565.04 nm/191.556250 THz 3.125/6.25GHz spacing";
           }
           enum "1565.01" {
             description "1565.01 nm/191.559375 THz 3.125GHz spacing";
           }
           enum "1564.99" {
             description "1564.99 nm/191.562500 THz 3.125/6.25/12.5GHz spacing";
           }
           enum "1564.96" {
             description "1564.96 nm/191.565625 THz 3.125GHz spacing";
           }
           enum "1564.93" {
             description "1564.93 nm/191.568750 THz 3.125/6.25GHz spacing";
           }
           enum "1564.91" {
             description "1564.91 nm/191.571875 THz 3.125GHz spacing";
           }
           enum "1564.88" {
             description "1564.88 nm/191.575000 THz 3.125/6.25/12.5GHz spacing";
           }
           enum "1564.86" {
             description "1564.86 nm/191.578125 THz 3.125GHz spacing";
           }
           enum "1564.83" {
             description "1564.83 nm/191.581250 THz 3.125/6.25GHz spacing";
           }
           enum "1564.81" {
             description "1564.81 nm/191.584375 THz 3.125GHz spacing";
           }
           enum "1564.78" {
             description "1564.78 nm/191.587500 THz 3.125/6.25/12.5GHz spacing";
           }
           enum "1564.76" {
             description "1564.76 nm/191.590625 THz 3.125GHz spacing";
           }
           enum "1564.73" {
             description "1564.73 nm/191.593750 THz 3.125/6.25GHz spacing";
           }
           enum "1564.70" {
             description "1564.70 nm/191.596875 THz 3.125GHz spacing";
           }
           enum "1564.68" {
             description "1564.68 nm/191.600000 THz 3.125/6.25/12.5/100GHz spacing";
           }
           enum "1564.65" {
             description "1564.65 nm/191.603125 THz 3.125GHz spacing";
           }
           enum "1564.63" {
             description "1564.63 nm/191.606250 THz 3.125/6.25GHz spacing";
           }
           enum "1564.60" {
             description "1564.60 nm/191.609375 THz 3.125GHz spacing";
           }
           enum "1564.58" {
             description "1564.58 nm/191.612500 THz 3.125/6.25/12.5GHz spacing";
           }
           enum "1564.55" {
             description "1564.55 nm/191.615625 THz 3.125GHz spacing";
           }
           enum "1564.53" {
             description "1564.53 nm/191.618750 THz 3.125/6.25GHz spacing";
           }
           enum "1564.50" {
             description "1564.50 nm/191.621875 THz 3.125GHz spacing";
           }
           enum "1564.47" {
             description "1564.47 nm/191.625000 THz 3.125/6.25/12.5/75GHz spacing";
           }
           enum "1564.45" {
             description "1564.45 nm/191.628125 THz 3.125GHz spacing";
           }
           enum "1564.42" {
             description "1564.42 nm/191.631250 THz 3.125/6.25GHz spacing";
           }
           enum "1564.40" {
             description "1564.40 nm/191.634375 THz 3.125GHz spacing";
           }
           enum "1564.37" {
             description "1564.37 nm/191.637500 THz 3.125/6.25/12.5GHz spacing";
           }
           enum "1564.35" {
             description "1564.35 nm/191.640625 THz 3.125GHz spacing";
           }
           enum "1564.32" {
             description "1564.32 nm/191.643750 THz 3.125/6.25GHz spacing";
           }
           enum "1564.30" {
             description "1564.30 nm/191.646875 THz 3.125GHz spacing";
           }
           enum "1564.27" {
             description "1564.27 nm/191.650000 THz 3.125/6.25/12.5/50GHz spacing";
           }
           enum "1564.25" {
             description "1564.25 nm/191.653125 THz 3.125GHz spacing";
           }
           enum "1564.22" {
             description "1564.22 nm/191.656250 THz 3.125/6.25GHz spacing";
           }
           enum "1564.19" {
             description "1564.19 nm/191.659375 THz 3.125GHz spacing";
           }
           enum "1564.17" {
             description "1564.17 nm/191.662500 THz 3.125/6.25/12.5GHz spacing";
           }
           enum "1564.14" {
             description "1564.14 nm/191.665625 THz 3.125GHz spacing";
           }
           enum "1564.12" {
             description "1564.12 nm/191.668750 THz 3.125/6.25GHz spacing";
           }
           enum "1564.09" {
             description "1564.09 nm/191.671875 THz 3.125GHz spacing";
           }
           enum "1564.07" {
             description "1564.07 nm/191.675000 THz 3.125/6.25/12.5GHz spacing";
           }
           enum "1564.04" {
             description "1564.04 nm/191.678125 THz 3.125GHz spacing";
           }
           enum "1564.02" {
             description "1564.02 nm/191.681250 THz 3.125/6.25GHz spacing";
           }
           enum "1563.99" {
             description "1563.99 nm/191.684375 THz 3.125GHz spacing";
           }
           enum "1563.96" {
             description "1563.96 nm/191.687500 THz 3.125/6.25/12.5GHz spacing";
           }
           enum "1563.94" {
             description "1563.94 nm/191.690625 THz 3.125GHz spacing";
           }
           enum "1563.91" {
             description "1563.91 nm/191.693750 THz 3.125/6.25GHz spacing";
           }
           enum "1563.89" {
             description "1563.89 nm/191.696875 THz 3.125GHz spacing";
           }
           enum "1563.86" {
             description "1563.86 nm/191.700000 THz 3.125/6.25/12.5/50/75/100GHz spacing";
           }
           enum "1563.84" {
             description "1563.84 nm/191.703125 THz 3.125GHz spacing";
           }
           enum "1563.81" {
             description "1563.81 nm/191.706250 THz 3.125/6.25GHz spacing";
           }
           enum "1563.79" {
             description "1563.79 nm/191.709375 THz 3.125GHz spacing";
           }
           enum "1563.76" {
             description "1563.76 nm/191.712500 THz 3.125/6.25/12.5GHz spacing";
           }
           enum "1563.74" {
             description "1563.74 nm/191.715625 THz 3.125GHz spacing";
           }
           enum "1563.71" {
             description "1563.71 nm/191.718750 THz 3.125/6.25GHz spacing";
           }
           enum "1563.68" {
             description "1563.68 nm/191.721875 THz 3.125GHz spacing";
           }
           enum "1563.66" {
             description "1563.66 nm/191.725000 THz 3.125/6.25/12.5GHz spacing";
           }
           enum "1563.63" {
             description "1563.63 nm/191.728125 THz 3.125GHz spacing";
           }
           enum "1563.61" {
             description "1563.61 nm/191.731250 THz 3.125/6.25GHz spacing";
           }
           enum "1563.58" {
             description "1563.58 nm/191.734375 THz 3.125GHz spacing";
           }
           enum "1563.56" {
             description "1563.56 nm/191.737500 THz 3.125/6.25/12.5GHz spacing";
           }
           enum "1563.53" {
             description "1563.53 nm/191.740625 THz 3.125GHz spacing";
           }
           enum "1563.51" {
             description "1563.51 nm/191.743750 THz 3.125/6.25GHz spacing";
           }
           enum "1563.48" {
             description "1563.48 nm/191.746875 THz 3.125GHz spacing";
           }
           enum "1563.45" {
             description "1563.45 nm/191.750000 THz 3.125/6.25/12.5/50GHz spacing";
           }
           enum "1563.43" {
             description "1563.43 nm/191.753125 THz 3.125GHz spacing";
           }
           enum "1563.40" {
             description "1563.40 nm/191.756250 THz 3.125/6.25GHz spacing";
           }
           enum "1563.38" {
             description "1563.38 nm/191.759375 THz 3.125GHz spacing";
           }
           enum "1563.35" {
             description "1563.35 nm/191.762500 THz 3.125/6.25/12.5GHz spacing";
           }
           enum "1563.33" {
             description "1563.33 nm/191.765625 THz 3.125GHz spacing";
           }
           enum "1563.30" {
             description "1563.30 nm/191.768750 THz 3.125/6.25GHz spacing";
           }
           enum "1563.28" {
             description "1563.28 nm/191.771875 THz 3.125GHz spacing";
           }
           enum "1563.25" {
             description "1563.25 nm/191.775000 THz 3.125/6.25/12.5/75GHz spacing";
           }
           enum "1563.23" {
             description "1563.23 nm/191.778125 THz 3.125GHz spacing";
           }
           enum "1563.20" {
             description "1563.20 nm/191.781250 THz 3.125/6.25GHz spacing";
           }
           enum "1563.17" {
             description "1563.17 nm/191.784375 THz 3.125GHz spacing";
           }
           enum "1563.15" {
             description "1563.15 nm/191.787500 THz 3.125/6.25/12.5GHz spacing";
           }
           enum "1563.12" {
             description "1563.12 nm/191.790625 THz 3.125GHz spacing";
           }
           enum "1563.10" {
             description "1563.10 nm/191.793750 THz 3.125/6.25GHz spacing";
           }
           enum "1563.07" {
             description "1563.07 nm/191.796875 THz 3.125GHz spacing";
           }
           enum "1563.05" {
             description "1563.05 nm/191.800000 THz 3.125/6.25/12.5/100GHz spacing";
           }
           enum "1563.02" {
             description "1563.02 nm/191.803125 THz 3.125GHz spacing";
           }
           enum "1563.00" {
             description "1563.00 nm/191.806250 THz 3.125/6.25GHz spacing";
           }
           enum "1562.97" {
             description "1562.97 nm/191.809375 THz 3.125GHz spacing";
           }
           enum "1562.95" {
             description "1562.95 nm/191.812500 THz 3.125/6.25/12.5GHz spacing";
           }
           enum "1562.92" {
             description "1562.92 nm/191.815625 THz 3.125GHz spacing";
           }
           enum "1562.89" {
             description "1562.89 nm/191.818750 THz 3.125/6.25GHz spacing";
           }
           enum "1562.87" {
             description "1562.87 nm/191.821875 THz 3.125GHz spacing";
           }
           enum "1562.84" {
             description "1562.84 nm/191.825000 THz 3.125/6.25/12.5GHz spacing";
           }
           enum "1562.82" {
             description "1562.82 nm/191.828125 THz 3.125GHz spacing";
           }
           enum "1562.79" {
             description "1562.79 nm/191.831250 THz 3.125/6.25GHz spacing";
           }
           enum "1562.77" {
             description "1562.77 nm/191.834375 THz 3.125GHz spacing";
           }
           enum "1562.74" {
             description "1562.74 nm/191.837500 THz 3.125/6.25/12.5GHz spacing";
           }
           enum "1562.72" {
             description "1562.72 nm/191.840625 THz 3.125GHz spacing";
           }
           enum "1562.69" {
             description "1562.69 nm/191.843750 THz 3.125/6.25GHz spacing";
           }
           enum "1562.67" {
             description "1562.67 nm/191.846875 THz 3.125GHz spacing";
           }
           enum "1562.64" {
             description "1562.64 nm/191.850000 THz 3.125/6.25/12.5/50/75GHz spacing";
           }
           enum "1562.61" {
             description "1562.61 nm/191.853125 THz 3.125GHz spacing";
           }
           enum "1562.59" {
             description "1562.59 nm/191.856250 THz 3.125/6.25GHz spacing";
           }
           enum "1562.56" {
             description "1562.56 nm/191.859375 THz 3.125GHz spacing";
           }
           enum "1562.54" {
             description "1562.54 nm/191.862500 THz 3.125/6.25/12.5GHz spacing";
           }
           enum "1562.51" {
             description "1562.51 nm/191.865625 THz 3.125GHz spacing";
           }
           enum "1562.49" {
             description "1562.49 nm/191.868750 THz 3.125/6.25GHz spacing";
           }
           enum "1562.46" {
             description "1562.46 nm/191.871875 THz 3.125GHz spacing";
           }
           enum "1562.44" {
             description "1562.44 nm/191.875000 THz 3.125/6.25/12.5GHz spacing";
           }
           enum "1562.41" {
             description "1562.41 nm/191.878125 THz 3.125GHz spacing";
           }
           enum "1562.39" {
             description "1562.39 nm/191.881250 THz 3.125/6.25GHz spacing";
           }
           enum "1562.36" {
             description "1562.36 nm/191.884375 THz 3.125GHz spacing";
           }
           enum "1562.33" {
             description "1562.33 nm/191.887500 THz 3.125/6.25/12.5GHz spacing";
           }
           enum "1562.31" {
             description "1562.31 nm/191.890625 THz 3.125GHz spacing";
           }
           enum "1562.28" {
             description "1562.28 nm/191.893750 THz 3.125/6.25GHz spacing";
           }
           enum "1562.26" {
             description "1562.26 nm/191.896875 THz 3.125GHz spacing";
           }
           enum "1562.23" {
             description "1562.23 nm/191.900000 THz 3.125/6.25/12.5/100GHz spacing";
           }
           enum "1562.21" {
             description "1562.21 nm/191.903125 THz 3.125GHz spacing";
           }
           enum "1562.18" {
             description "1562.18 nm/191.906250 THz 3.125/6.25GHz spacing";
           }
           enum "1562.16" {
             description "1562.16 nm/191.909375 THz 3.125GHz spacing";
           }
           enum "1562.13" {
             description "1562.13 nm/191.912500 THz 3.125/6.25/12.5GHz spacing";
           }
           enum "1562.11" {
             description "1562.11 nm/191.915625 THz 3.125GHz spacing";
           }
           enum "1562.08" {
             description "1562.08 nm/191.918750 THz 3.125/6.25GHz spacing";
           }
           enum "1562.05" {
             description "1562.05 nm/191.921875 THz 3.125GHz spacing";
           }
           enum "1562.03" {
             description "1562.03 nm/191.925000 THz 3.125/6.25/12.5/75GHz spacing";
           }
           enum "1562.00" {
             description "1562.00 nm/191.928125 THz 3.125GHz spacing";
           }
           enum "1561.98" {
             description "1561.98 nm/191.931250 THz 3.125/6.25GHz spacing";
           }
           enum "1561.95" {
             description "1561.95 nm/191.934375 THz 3.125GHz spacing";
           }
           enum "1561.93" {
             description "1561.93 nm/191.937500 THz 3.125/6.25/12.5GHz spacing";
           }
           enum "1561.90" {
             description "1561.90 nm/191.940625 THz 3.125GHz spacing";
           }
           enum "1561.88" {
             description "1561.88 nm/191.943750 THz 3.125/6.25GHz spacing";
           }
           enum "1561.85" {
             description "1561.85 nm/191.946875 THz 3.125GHz spacing";
           }
           enum "1561.83" {
             description "1561.83 nm/191.950000 THz 3.125/6.25/12.5/50GHz spacing";
           }
           enum "1561.80" {
             description "1561.80 nm/191.953125 THz 3.125GHz spacing";
           }
           enum "1561.77" {
             description "1561.77 nm/191.956250 THz 3.125/6.25GHz spacing";
           }
           enum "1561.75" {
             description "1561.75 nm/191.959375 THz 3.125GHz spacing";
           }
           enum "1561.72" {
             description "1561.72 nm/191.962500 THz 3.125/6.25/12.5GHz spacing";
           }
           enum "1561.70" {
             description "1561.70 nm/191.965625 THz 3.125GHz spacing";
           }
           enum "1561.67" {
             description "1561.67 nm/191.968750 THz 3.125/6.25GHz spacing";
           }
           enum "1561.65" {
             description "1561.65 nm/191.971875 THz 3.125GHz spacing";
           }
           enum "1561.62" {
             description "1561.62 nm/191.975000 THz 3.125/6.25/12.5GHz spacing";
           }
           enum "1561.60" {
             description "1561.60 nm/191.978125 THz 3.125GHz spacing";
           }
           enum "1561.57" {
             description "1561.57 nm/191.981250 THz 3.125/6.25GHz spacing";
           }
           enum "1561.55" {
             description "1561.55 nm/191.984375 THz 3.125GHz spacing";
           }
           enum "1561.52" {
             description "1561.52 nm/191.987500 THz 3.125/6.25/12.5GHz spacing";
           }
           enum "1561.50" {
             description "1561.50 nm/191.990625 THz 3.125GHz spacing";
           }
           enum "1561.47" {
             description "1561.47 nm/191.993750 THz 3.125/6.25GHz spacing";
           }
           enum "1561.44" {
             description "1561.44 nm/191.996875 THz 3.125GHz spacing";
           }
           enum "1561.42" {
             description "1561.42 nm/192.000000 THz 3.125/6.25/12.5/50/75/100GHz spacing";
           }
           enum "1561.39" {
             description "1561.39 nm/192.003125 THz 3.125GHz spacing";
           }
           enum "1561.37" {
             description "1561.37 nm/192.006250 THz 3.125/6.25GHz spacing";
           }
           enum "1561.34" {
             description "1561.34 nm/192.009375 THz 3.125GHz spacing";
           }
           enum "1561.32" {
             description "1561.32 nm/192.012500 THz 3.125/6.25/12.5GHz spacing";
           }
           enum "1561.29" {
             description "1561.29 nm/192.015625 THz 3.125GHz spacing";
           }
           enum "1561.27" {
             description "1561.27 nm/192.018750 THz 3.125/6.25GHz spacing";
           }
           enum "1561.24" {
             description "1561.24 nm/192.021875 THz 3.125GHz spacing";
           }
           enum "1561.22" {
             description "1561.22 nm/192.025000 THz 3.125/6.25/12.5GHz spacing";
           }
           enum "1561.19" {
             description "1561.19 nm/192.028125 THz 3.125GHz spacing";
           }
           enum "1561.16" {
             description "1561.16 nm/192.031250 THz 3.125/6.25GHz spacing";
           }
           enum "1561.14" {
             description "1561.14 nm/192.034375 THz 3.125GHz spacing";
           }
           enum "1561.11" {
             description "1561.11 nm/192.037500 THz 3.125/6.25/12.5GHz spacing";
           }
           enum "1561.09" {
             description "1561.09 nm/192.040625 THz 3.125GHz spacing";
           }
           enum "1561.06" {
             description "1561.06 nm/192.043750 THz 3.125/6.25GHz spacing";
           }
           enum "1561.04" {
             description "1561.04 nm/192.046875 THz 3.125GHz spacing";
           }
           enum "1561.01" {
             description "1561.01 nm/192.050000 THz 3.125/6.25/12.5/50GHz spacing";
           }
           enum "1560.99" {
             description "1560.99 nm/192.053125 THz 3.125GHz spacing";
           }
           enum "1560.96" {
             description "1560.96 nm/192.056250 THz 3.125/6.25GHz spacing";
           }
           enum "1560.94" {
             description "1560.94 nm/192.059375 THz 3.125GHz spacing";
           }
           enum "1560.91" {
             description "1560.91 nm/192.062500 THz 3.125/6.25/12.5GHz spacing";
           }
           enum "1560.89" {
             description "1560.89 nm/192.065625 THz 3.125GHz spacing";
           }
           enum "1560.86" {
             description "1560.86 nm/192.068750 THz 3.125/6.25GHz spacing";
           }
           enum "1560.83" {
             description "1560.83 nm/192.071875 THz 3.125GHz spacing";
           }
           enum "1560.81" {
             description "1560.81 nm/192.075000 THz 3.125/6.25/12.5/75GHz spacing";
           }
           enum "1560.78" {
             description "1560.78 nm/192.078125 THz 3.125GHz spacing";
           }
           enum "1560.76" {
             description "1560.76 nm/192.081250 THz 3.125/6.25GHz spacing";
           }
           enum "1560.73" {
             description "1560.73 nm/192.084375 THz 3.125GHz spacing";
           }
           enum "1560.71" {
             description "1560.71 nm/192.087500 THz 3.125/6.25/12.5GHz spacing";
           }
           enum "1560.68" {
             description "1560.68 nm/192.090625 THz 3.125GHz spacing";
           }
           enum "1560.66" {
             description "1560.66 nm/192.093750 THz 3.125/6.25GHz spacing";
           }
           enum "1560.63" {
             description "1560.63 nm/192.096875 THz 3.125GHz spacing";
           }
           enum "1560.61" {
             description "1560.61 nm/192.100000 THz 3.125/6.25/12.5/100GHz spacing";
           }
           enum "1560.58" {
             description "1560.58 nm/192.103125 THz 3.125GHz spacing";
           }
           enum "1560.56" {
             description "1560.56 nm/192.106250 THz 3.125/6.25GHz spacing";
           }
           enum "1560.53" {
             description "1560.53 nm/192.109375 THz 3.125GHz spacing";
           }
           enum "1560.50" {
             description "1560.50 nm/192.112500 THz 3.125/6.25/12.5GHz spacing";
           }
           enum "1560.48" {
             description "1560.48 nm/192.115625 THz 3.125GHz spacing";
           }
           enum "1560.45" {
             description "1560.45 nm/192.118750 THz 3.125/6.25GHz spacing";
           }
           enum "1560.43" {
             description "1560.43 nm/192.121875 THz 3.125GHz spacing";
           }
           enum "1560.40" {
             description "1560.40 nm/192.125000 THz 3.125/6.25/12.5GHz spacing";
           }
           enum "1560.38" {
             description "1560.38 nm/192.128125 THz 3.125GHz spacing";
           }
           enum "1560.35" {
             description "1560.35 nm/192.131250 THz 3.125/6.25GHz spacing";
           }
           enum "1560.33" {
             description "1560.33 nm/192.134375 THz 3.125GHz spacing";
           }
           enum "1560.30" {
             description "1560.30 nm/192.137500 THz 3.125/6.25/12.5GHz spacing";
           }
           enum "1560.28" {
             description "1560.28 nm/192.140625 THz 3.125GHz spacing";
           }
           enum "1560.25" {
             description "1560.25 nm/192.143750 THz 3.125/6.25GHz spacing";
           }
           enum "1560.23" {
             description "1560.23 nm/192.146875 THz 3.125GHz spacing";
           }
           enum "1560.20" {
             description "1560.20 nm/192.150000 THz 3.125/6.25/12.5/50/75GHz spacing";
           }
           enum "1560.17" {
             description "1560.17 nm/192.153125 THz 3.125GHz spacing";
           }
           enum "1560.15" {
             description "1560.15 nm/192.156250 THz 3.125/6.25GHz spacing";
           }
           enum "1560.12" {
             description "1560.12 nm/192.159375 THz 3.125GHz spacing";
           }
           enum "1560.10" {
             description "1560.10 nm/192.162500 THz 3.125/6.25/12.5GHz spacing";
           }
           enum "1560.07" {
             description "1560.07 nm/192.165625 THz 3.125GHz spacing";
           }
           enum "1560.05" {
             description "1560.05 nm/192.168750 THz 3.125/6.25GHz spacing";
           }
           enum "1560.02" {
             description "1560.02 nm/192.171875 THz 3.125GHz spacing";
           }
           enum "1560.00" {
             description "1560.00 nm/192.175000 THz 3.125/6.25/12.5GHz spacing";
           }
           enum "1559.97" {
             description "1559.97 nm/192.178125 THz 3.125GHz spacing";
           }
           enum "1559.95" {
             description "1559.95 nm/192.181250 THz 3.125/6.25GHz spacing";
           }
           enum "1559.92" {
             description "1559.92 nm/192.184375 THz 3.125GHz spacing";
           }
           enum "1559.90" {
             description "1559.90 nm/192.187500 THz 3.125/6.25/12.5GHz spacing";
           }
           enum "1559.87" {
             description "1559.87 nm/192.190625 THz 3.125GHz spacing";
           }
           enum "1559.84" {
             description "1559.84 nm/192.193750 THz 3.125/6.25GHz spacing";
           }
           enum "1559.82" {
             description "1559.82 nm/192.196875 THz 3.125GHz spacing";
           }
           enum "1559.79" {
             description "1559.79 nm/192.200000 THz 3.125/6.25/12.5/100GHz spacing";
           }
           enum "1559.77" {
             description "1559.77 nm/192.203125 THz 3.125GHz spacing";
           }
           enum "1559.74" {
             description "1559.74 nm/192.206250 THz 3.125/6.25GHz spacing";
           }
           enum "1559.72" {
             description "1559.72 nm/192.209375 THz 3.125GHz spacing";
           }
           enum "1559.69" {
             description "1559.69 nm/192.212500 THz 3.125/6.25/12.5GHz spacing";
           }
           enum "1559.67" {
             description "1559.67 nm/192.215625 THz 3.125GHz spacing";
           }
           enum "1559.64" {
             description "1559.64 nm/192.218750 THz 3.125/6.25GHz spacing";
           }
           enum "1559.62" {
             description "1559.62 nm/192.221875 THz 3.125GHz spacing";
           }
           enum "1559.59" {
             description "1559.59 nm/192.225000 THz 3.125/6.25/12.5/75GHz spacing";
           }
           enum "1559.57" {
             description "1559.57 nm/192.228125 THz 3.125GHz spacing";
           }
           enum "1559.54" {
             description "1559.54 nm/192.231250 THz 3.125/6.25GHz spacing";
           }
           enum "1559.52" {
             description "1559.52 nm/192.234375 THz 3.125GHz spacing";
           }
           enum "1559.49" {
             description "1559.49 nm/192.237500 THz 3.125/6.25/12.5GHz spacing";
           }
           enum "1559.46" {
             description "1559.46 nm/192.240625 THz 3.125GHz spacing";
           }
           enum "1559.44" {
             description "1559.44 nm/192.243750 THz 3.125/6.25GHz spacing";
           }
           enum "1559.41" {
             description "1559.41 nm/192.246875 THz 3.125GHz spacing";
           }
           enum "1559.39" {
             description "1559.39 nm/192.250000 THz 3.125/6.25/12.5/50GHz spacing";
           }
           enum "1559.36" {
             description "1559.36 nm/192.253125 THz 3.125GHz spacing";
           }
           enum "1559.34" {
             description "1559.34 nm/192.256250 THz 3.125/6.25GHz spacing";
           }
           enum "1559.31" {
             description "1559.31 nm/192.259375 THz 3.125GHz spacing";
           }
           enum "1559.29" {
             description "1559.29 nm/192.262500 THz 3.125/6.25/12.5GHz spacing";
           }
           enum "1559.26" {
             description "1559.26 nm/192.265625 THz 3.125GHz spacing";
           }
           enum "1559.24" {
             description "1559.24 nm/192.268750 THz 3.125/6.25GHz spacing";
           }
           enum "1559.21" {
             description "1559.21 nm/192.271875 THz 3.125GHz spacing";
           }
           enum "1559.19" {
             description "1559.19 nm/192.275000 THz 3.125/6.25/12.5GHz spacing";
           }
           enum "1559.16" {
             description "1559.16 nm/192.278125 THz 3.125GHz spacing";
           }
           enum "1559.14" {
             description "1559.14 nm/192.281250 THz 3.125/6.25GHz spacing";
           }
           enum "1559.11" {
             description "1559.11 nm/192.284375 THz 3.125GHz spacing";
           }
           enum "1559.08" {
             description "1559.08 nm/192.287500 THz 3.125/6.25/12.5GHz spacing";
           }
           enum "1559.06" {
             description "1559.06 nm/192.290625 THz 3.125GHz spacing";
           }
           enum "1559.03" {
             description "1559.03 nm/192.293750 THz 3.125/6.25GHz spacing";
           }
           enum "1559.01" {
             description "1559.01 nm/192.296875 THz 3.125GHz spacing";
           }
           enum "1558.98" {
             description "1558.98 nm/192.300000 THz 3.125/6.25/12.5/50/75/100GHz spacing";
           }
           enum "1558.96" {
             description "1558.96 nm/192.303125 THz 3.125GHz spacing";
           }
           enum "1558.93" {
             description "1558.93 nm/192.306250 THz 3.125/6.25GHz spacing";
           }
           enum "1558.91" {
             description "1558.91 nm/192.309375 THz 3.125GHz spacing";
           }
           enum "1558.88" {
             description "1558.88 nm/192.312500 THz 3.125/6.25/12.5GHz spacing";
           }
           enum "1558.86" {
             description "1558.86 nm/192.315625 THz 3.125GHz spacing";
           }
           enum "1558.83" {
             description "1558.83 nm/192.318750 THz 3.125/6.25GHz spacing";
           }
           enum "1558.81" {
             description "1558.81 nm/192.321875 THz 3.125GHz spacing";
           }
           enum "1558.78" {
             description "1558.78 nm/192.325000 THz 3.125/6.25/12.5GHz spacing";
           }
           enum "1558.76" {
             description "1558.76 nm/192.328125 THz 3.125GHz spacing";
           }
           enum "1558.73" {
             description "1558.73 nm/192.331250 THz 3.125/6.25GHz spacing";
           }
           enum "1558.70" {
             description "1558.70 nm/192.334375 THz 3.125GHz spacing";
           }
           enum "1558.68" {
             description "1558.68 nm/192.337500 THz 3.125/6.25/12.5GHz spacing";
           }
           enum "1558.65" {
             description "1558.65 nm/192.340625 THz 3.125GHz spacing";
           }
           enum "1558.63" {
             description "1558.63 nm/192.343750 THz 3.125/6.25GHz spacing";
           }
           enum "1558.60" {
             description "1558.60 nm/192.346875 THz 3.125GHz spacing";
           }
           enum "1558.58" {
             description "1558.58 nm/192.350000 THz 3.125/6.25/12.5/50GHz spacing";
           }
           enum "1558.55" {
             description "1558.55 nm/192.353125 THz 3.125GHz spacing";
           }
           enum "1558.53" {
             description "1558.53 nm/192.356250 THz 3.125/6.25GHz spacing";
           }
           enum "1558.50" {
             description "1558.50 nm/192.359375 THz 3.125GHz spacing";
           }
           enum "1558.48" {
             description "1558.48 nm/192.362500 THz 3.125/6.25/12.5GHz spacing";
           }
           enum "1558.45" {
             description "1558.45 nm/192.365625 THz 3.125GHz spacing";
           }
           enum "1558.43" {
             description "1558.43 nm/192.368750 THz 3.125/6.25GHz spacing";
           }
           enum "1558.40" {
             description "1558.40 nm/192.371875 THz 3.125GHz spacing";
           }
           enum "1558.38" {
             description "1558.38 nm/192.375000 THz 3.125/6.25/12.5/75GHz spacing";
           }
           enum "1558.35" {
             description "1558.35 nm/192.378125 THz 3.125GHz spacing";
           }
           enum "1558.32" {
             description "1558.32 nm/192.381250 THz 3.125/6.25GHz spacing";
           }
           enum "1558.30" {
             description "1558.30 nm/192.384375 THz 3.125GHz spacing";
           }
           enum "1558.27" {
             description "1558.27 nm/192.387500 THz 3.125/6.25/12.5GHz spacing";
           }
           enum "1558.25" {
             description "1558.25 nm/192.390625 THz 3.125GHz spacing";
           }
           enum "1558.22" {
             description "1558.22 nm/192.393750 THz 3.125/6.25GHz spacing";
           }
           enum "1558.20" {
             description "1558.20 nm/192.396875 THz 3.125GHz spacing";
           }
           enum "1558.17" {
             description "1558.17 nm/192.400000 THz 3.125/6.25/12.5/100GHz spacing";
           }
           enum "1558.15" {
             description "1558.15 nm/192.403125 THz 3.125GHz spacing";
           }
           enum "1558.12" {
             description "1558.12 nm/192.406250 THz 3.125/6.25GHz spacing";
           }
           enum "1558.10" {
             description "1558.10 nm/192.409375 THz 3.125GHz spacing";
           }
           enum "1558.07" {
             description "1558.07 nm/192.412500 THz 3.125/6.25/12.5GHz spacing";
           }
           enum "1558.05" {
             description "1558.05 nm/192.415625 THz 3.125GHz spacing";
           }
           enum "1558.02" {
             description "1558.02 nm/192.418750 THz 3.125/6.25GHz spacing";
           }
           enum "1558.00" {
             description "1558.00 nm/192.421875 THz 3.125GHz spacing";
           }
           enum "1557.97" {
             description "1557.97 nm/192.425000 THz 3.125/6.25/12.5GHz spacing";
           }
           enum "1557.95" {
             description "1557.95 nm/192.428125 THz 3.125GHz spacing";
           }
           enum "1557.92" {
             description "1557.92 nm/192.431250 THz 3.125/6.25GHz spacing";
           }
           enum "1557.89" {
             description "1557.89 nm/192.434375 THz 3.125GHz spacing";
           }
           enum "1557.87" {
             description "1557.87 nm/192.437500 THz 3.125/6.25/12.5GHz spacing";
           }
           enum "1557.84" {
             description "1557.84 nm/192.440625 THz 3.125GHz spacing";
           }
           enum "1557.82" {
             description "1557.82 nm/192.443750 THz 3.125/6.25GHz spacing";
           }
           enum "1557.79" {
             description "1557.79 nm/192.446875 THz 3.125GHz spacing";
           }
           enum "1557.77" {
             description "1557.77 nm/192.450000 THz 3.125/6.25/12.5/50/75GHz spacing";
           }
           enum "1557.74" {
             description "1557.74 nm/192.453125 THz 3.125GHz spacing";
           }
           enum "1557.72" {
             description "1557.72 nm/192.456250 THz 3.125/6.25GHz spacing";
           }
           enum "1557.69" {
             description "1557.69 nm/192.459375 THz 3.125GHz spacing";
           }
           enum "1557.67" {
             description "1557.67 nm/192.462500 THz 3.125/6.25/12.5GHz spacing";
           }
           enum "1557.64" {
             description "1557.64 nm/192.465625 THz 3.125GHz spacing";
           }
           enum "1557.62" {
             description "1557.62 nm/192.468750 THz 3.125/6.25GHz spacing";
           }
           enum "1557.59" {
             description "1557.59 nm/192.471875 THz 3.125GHz spacing";
           }
           enum "1557.57" {
             description "1557.57 nm/192.475000 THz 3.125/6.25/12.5GHz spacing";
           }
           enum "1557.54" {
             description "1557.54 nm/192.478125 THz 3.125GHz spacing";
           }
           enum "1557.52" {
             description "1557.52 nm/192.481250 THz 3.125/6.25GHz spacing";
           }
           enum "1557.49" {
             description "1557.49 nm/192.484375 THz 3.125GHz spacing";
           }
           enum "1557.46" {
             description "1557.46 nm/192.487500 THz 3.125/6.25/12.5GHz spacing";
           }
           enum "1557.44" {
             description "1557.44 nm/192.490625 THz 3.125GHz spacing";
           }
           enum "1557.41" {
             description "1557.41 nm/192.493750 THz 3.125/6.25GHz spacing";
           }
           enum "1557.39" {
             description "1557.39 nm/192.496875 THz 3.125GHz spacing";
           }
           enum "1557.36" {
             description "1557.36 nm/192.500000 THz 3.125/6.25/12.5/100GHz spacing";
           }
           enum "1557.34" {
             description "1557.34 nm/192.503125 THz 3.125GHz spacing";
           }
           enum "1557.31" {
             description "1557.31 nm/192.506250 THz 3.125/6.25GHz spacing";
           }
           enum "1557.29" {
             description "1557.29 nm/192.509375 THz 3.125GHz spacing";
           }
           enum "1557.26" {
             description "1557.26 nm/192.512500 THz 3.125/6.25/12.5GHz spacing";
           }
           enum "1557.24" {
             description "1557.24 nm/192.515625 THz 3.125GHz spacing";
           }
           enum "1557.21" {
             description "1557.21 nm/192.518750 THz 3.125/6.25GHz spacing";
           }
           enum "1557.19" {
             description "1557.19 nm/192.521875 THz 3.125GHz spacing";
           }
           enum "1557.16" {
             description "1557.16 nm/192.525000 THz 3.125/6.25/12.5/75GHz spacing";
           }
           enum "1557.14" {
             description "1557.14 nm/192.528125 THz 3.125GHz spacing";
           }
           enum "1557.11" {
             description "1557.11 nm/192.531250 THz 3.125/6.25GHz spacing";
           }
           enum "1557.09" {
             description "1557.09 nm/192.534375 THz 3.125GHz spacing";
           }
           enum "1557.06" {
             description "1557.06 nm/192.537500 THz 3.125/6.25/12.5GHz spacing";
           }
           enum "1557.03" {
             description "1557.03 nm/192.540625 THz 3.125GHz spacing";
           }
           enum "1557.01" {
             description "1557.01 nm/192.543750 THz 3.125/6.25GHz spacing";
           }
           enum "1556.98" {
             description "1556.98 nm/192.546875 THz 3.125GHz spacing";
           }
           enum "1556.96" {
             description "1556.96 nm/192.550000 THz 3.125/6.25/12.5/50GHz spacing";
           }
           enum "1556.93" {
             description "1556.93 nm/192.553125 THz 3.125GHz spacing";
           }
           enum "1556.91" {
             description "1556.91 nm/192.556250 THz 3.125/6.25GHz spacing";
           }
           enum "1556.88" {
             description "1556.88 nm/192.559375 THz 3.125GHz spacing";
           }
           enum "1556.86" {
             description "1556.86 nm/192.562500 THz 3.125/6.25/12.5GHz spacing";
           }
           enum "1556.83" {
             description "1556.83 nm/192.565625 THz 3.125GHz spacing";
           }
           enum "1556.81" {
             description "1556.81 nm/192.568750 THz 3.125/6.25GHz spacing";
           }
           enum "1556.78" {
             description "1556.78 nm/192.571875 THz 3.125GHz spacing";
           }
           enum "1556.76" {
             description "1556.76 nm/192.575000 THz 3.125/6.25/12.5GHz spacing";
           }
           enum "1556.73" {
             description "1556.73 nm/192.578125 THz 3.125GHz spacing";
           }
           enum "1556.71" {
             description "1556.71 nm/192.581250 THz 3.125/6.25GHz spacing";
           }
           enum "1556.68" {
             description "1556.68 nm/192.584375 THz 3.125GHz spacing";
           }
           enum "1556.66" {
             description "1556.66 nm/192.587500 THz 3.125/6.25/12.5GHz spacing";
           }
           enum "1556.63" {
             description "1556.63 nm/192.590625 THz 3.125GHz spacing";
           }
           enum "1556.61" {
             description "1556.61 nm/192.593750 THz 3.125/6.25GHz spacing";
           }
           enum "1556.58" {
             description "1556.58 nm/192.596875 THz 3.125GHz spacing";
           }
           enum "1556.55" {
             description "1556.55 nm/192.600000 THz 3.125/6.25/12.5/50/75/100GHz spacing";
           }
           enum "1556.53" {
             description "1556.53 nm/192.603125 THz 3.125GHz spacing";
           }
           enum "1556.50" {
             description "1556.50 nm/192.606250 THz 3.125/6.25GHz spacing";
           }
           enum "1556.48" {
             description "1556.48 nm/192.609375 THz 3.125GHz spacing";
           }
           enum "1556.45" {
             description "1556.45 nm/192.612500 THz 3.125/6.25/12.5GHz spacing";
           }
           enum "1556.43" {
             description "1556.43 nm/192.615625 THz 3.125GHz spacing";
           }
           enum "1556.40" {
             description "1556.40 nm/192.618750 THz 3.125/6.25GHz spacing";
           }
           enum "1556.38" {
             description "1556.38 nm/192.621875 THz 3.125GHz spacing";
           }
           enum "1556.35" {
             description "1556.35 nm/192.625000 THz 3.125/6.25/12.5GHz spacing";
           }
           enum "1556.33" {
             description "1556.33 nm/192.628125 THz 3.125GHz spacing";
           }
           enum "1556.30" {
             description "1556.30 nm/192.631250 THz 3.125/6.25GHz spacing";
           }
           enum "1556.28" {
             description "1556.28 nm/192.634375 THz 3.125GHz spacing";
           }
           enum "1556.25" {
             description "1556.25 nm/192.637500 THz 3.125/6.25/12.5GHz spacing";
           }
           enum "1556.23" {
             description "1556.23 nm/192.640625 THz 3.125GHz spacing";
           }
           enum "1556.20" {
             description "1556.20 nm/192.643750 THz 3.125/6.25GHz spacing";
           }
           enum "1556.18" {
             description "1556.18 nm/192.646875 THz 3.125GHz spacing";
           }
           enum "1556.15" {
             description "1556.15 nm/192.650000 THz 3.125/6.25/12.5/50GHz spacing";
           }
           enum "1556.13" {
             description "1556.13 nm/192.653125 THz 3.125GHz spacing";
           }
           enum "1556.10" {
             description "1556.10 nm/192.656250 THz 3.125/6.25GHz spacing";
           }
           enum "1556.08" {
             description "1556.08 nm/192.659375 THz 3.125GHz spacing";
           }
           enum "1556.05" {
             description "1556.05 nm/192.662500 THz 3.125/6.25/12.5GHz spacing";
           }
           enum "1556.02" {
             description "1556.02 nm/192.665625 THz 3.125GHz spacing";
           }
           enum "1556.00" {
             description "1556.00 nm/192.668750 THz 3.125/6.25GHz spacing";
           }
           enum "1555.97" {
             description "1555.97 nm/192.671875 THz 3.125GHz spacing";
           }
           enum "1555.95" {
             description "1555.95 nm/192.675000 THz 3.125/6.25/12.5/75GHz spacing";
           }
           enum "1555.92" {
             description "1555.92 nm/192.678125 THz 3.125GHz spacing";
           }
           enum "1555.90" {
             description "1555.90 nm/192.681250 THz 3.125/6.25GHz spacing";
           }
           enum "1555.87" {
             description "1555.87 nm/192.684375 THz 3.125GHz spacing";
           }
           enum "1555.85" {
             description "1555.85 nm/192.687500 THz 3.125/6.25/12.5GHz spacing";
           }
           enum "1555.82" {
             description "1555.82 nm/192.690625 THz 3.125GHz spacing";
           }
           enum "1555.80" {
             description "1555.80 nm/192.693750 THz 3.125/6.25GHz spacing";
           }
           enum "1555.77" {
             description "1555.77 nm/192.696875 THz 3.125GHz spacing";
           }
           enum "1555.75" {
             description "1555.75 nm/192.700000 THz 3.125/6.25/12.5/100GHz spacing";
           }
           enum "1555.72" {
             description "1555.72 nm/192.703125 THz 3.125GHz spacing";
           }
           enum "1555.70" {
             description "1555.70 nm/192.706250 THz 3.125/6.25GHz spacing";
           }
           enum "1555.67" {
             description "1555.67 nm/192.709375 THz 3.125GHz spacing";
           }
           enum "1555.65" {
             description "1555.65 nm/192.712500 THz 3.125/6.25/12.5GHz spacing";
           }
           enum "1555.62" {
             description "1555.62 nm/192.715625 THz 3.125GHz spacing";
           }
           enum "1555.60" {
             description "1555.60 nm/192.718750 THz 3.125/6.25GHz spacing";
           }
           enum "1555.57" {
             description "1555.57 nm/192.721875 THz 3.125GHz spacing";
           }
           enum "1555.55" {
             description "1555.55 nm/192.725000 THz 3.125/6.25/12.5GHz spacing";
           }
           enum "1555.52" {
             description "1555.52 nm/192.728125 THz 3.125GHz spacing";
           }
           enum "1555.49" {
             description "1555.49 nm/192.731250 THz 3.125/6.25GHz spacing";
           }
           enum "1555.47" {
             description "1555.47 nm/192.734375 THz 3.125GHz spacing";
           }
           enum "1555.44" {
             description "1555.44 nm/192.737500 THz 3.125/6.25/12.5GHz spacing";
           }
           enum "1555.42" {
             description "1555.42 nm/192.740625 THz 3.125GHz spacing";
           }
           enum "1555.39" {
             description "1555.39 nm/192.743750 THz 3.125/6.25GHz spacing";
           }
           enum "1555.37" {
             description "1555.37 nm/192.746875 THz 3.125GHz spacing";
           }
           enum "1555.34" {
             description "1555.34 nm/192.750000 THz 3.125/6.25/12.5/50/75GHz spacing";
           }
           enum "1555.32" {
             description "1555.32 nm/192.753125 THz 3.125GHz spacing";
           }
           enum "1555.29" {
             description "1555.29 nm/192.756250 THz 3.125/6.25GHz spacing";
           }
           enum "1555.27" {
             description "1555.27 nm/192.759375 THz 3.125GHz spacing";
           }
           enum "1555.24" {
             description "1555.24 nm/192.762500 THz 3.125/6.25/12.5GHz spacing";
           }
           enum "1555.22" {
             description "1555.22 nm/192.765625 THz 3.125GHz spacing";
           }
           enum "1555.19" {
             description "1555.19 nm/192.768750 THz 3.125/6.25GHz spacing";
           }
           enum "1555.17" {
             description "1555.17 nm/192.771875 THz 3.125GHz spacing";
           }
           enum "1555.14" {
             description "1555.14 nm/192.775000 THz 3.125/6.25/12.5GHz spacing";
           }
           enum "1555.12" {
             description "1555.12 nm/192.778125 THz 3.125GHz spacing";
           }
           enum "1555.09" {
             description "1555.09 nm/192.781250 THz 3.125/6.25GHz spacing";
           }
           enum "1555.07" {
             description "1555.07 nm/192.784375 THz 3.125GHz spacing";
           }
           enum "1555.04" {
             description "1555.04 nm/192.787500 THz 3.125/6.25/12.5GHz spacing";
           }
           enum "1555.02" {
             description "1555.02 nm/192.790625 THz 3.125GHz spacing";
           }
           enum "1554.99" {
             description "1554.99 nm/192.793750 THz 3.125/6.25GHz spacing";
           }
           enum "1554.97" {
             description "1554.97 nm/192.796875 THz 3.125GHz spacing";
           }
           enum "1554.94" {
             description "1554.94 nm/192.800000 THz 3.125/6.25/12.5/100GHz spacing";
           }
           enum "1554.91" {
             description "1554.91 nm/192.803125 THz 3.125GHz spacing";
           }
           enum "1554.89" {
             description "1554.89 nm/192.806250 THz 3.125/6.25GHz spacing";
           }
           enum "1554.86" {
             description "1554.86 nm/192.809375 THz 3.125GHz spacing";
           }
           enum "1554.84" {
             description "1554.84 nm/192.812500 THz 3.125/6.25/12.5GHz spacing";
           }
           enum "1554.81" {
             description "1554.81 nm/192.815625 THz 3.125GHz spacing";
           }
           enum "1554.79" {
             description "1554.79 nm/192.818750 THz 3.125/6.25GHz spacing";
           }
           enum "1554.76" {
             description "1554.76 nm/192.821875 THz 3.125GHz spacing";
           }
           enum "1554.74" {
             description "1554.74 nm/192.825000 THz 3.125/6.25/12.5/75GHz spacing";
           }
           enum "1554.71" {
             description "1554.71 nm/192.828125 THz 3.125GHz spacing";
           }
           enum "1554.69" {
             description "1554.69 nm/192.831250 THz 3.125/6.25GHz spacing";
           }
           enum "1554.66" {
             description "1554.66 nm/192.834375 THz 3.125GHz spacing";
           }
           enum "1554.64" {
             description "1554.64 nm/192.837500 THz 3.125/6.25/12.5GHz spacing";
           }
           enum "1554.61" {
             description "1554.61 nm/192.840625 THz 3.125GHz spacing";
           }
           enum "1554.59" {
             description "1554.59 nm/192.843750 THz 3.125/6.25GHz spacing";
           }
           enum "1554.56" {
             description "1554.56 nm/192.846875 THz 3.125GHz spacing";
           }
           enum "1554.54" {
             description "1554.54 nm/192.850000 THz 3.125/6.25/12.5/50GHz spacing";
           }
           enum "1554.51" {
             description "1554.51 nm/192.853125 THz 3.125GHz spacing";
           }
           enum "1554.49" {
             description "1554.49 nm/192.856250 THz 3.125/6.25GHz spacing";
           }
           enum "1554.46" {
             description "1554.46 nm/192.859375 THz 3.125GHz spacing";
           }
           enum "1554.44" {
             description "1554.44 nm/192.862500 THz 3.125/6.25/12.5GHz spacing";
           }
           enum "1554.41" {
             description "1554.41 nm/192.865625 THz 3.125GHz spacing";
           }
           enum "1554.39" {
             description "1554.39 nm/192.868750 THz 3.125/6.25GHz spacing";
           }
           enum "1554.36" {
             description "1554.36 nm/192.871875 THz 3.125GHz spacing";
           }
           enum "1554.34" {
             description "1554.34 nm/192.875000 THz 3.125/6.25/12.5GHz spacing";
           }
           enum "1554.31" {
             description "1554.31 nm/192.878125 THz 3.125GHz spacing";
           }
           enum "1554.29" {
             description "1554.29 nm/192.881250 THz 3.125/6.25GHz spacing";
           }
           enum "1554.26" {
             description "1554.26 nm/192.884375 THz 3.125GHz spacing";
           }
           enum "1554.23" {
             description "1554.23 nm/192.887500 THz 3.125/6.25/12.5GHz spacing";
           }
           enum "1554.21" {
             description "1554.21 nm/192.890625 THz 3.125GHz spacing";
           }
           enum "1554.18" {
             description "1554.18 nm/192.893750 THz 3.125/6.25GHz spacing";
           }
           enum "1554.16" {
             description "1554.16 nm/192.896875 THz 3.125GHz spacing";
           }
           enum "1554.13" {
             description "1554.13 nm/192.900000 THz 3.125/6.25/12.5/50/75/100GHz spacing";
           }
           enum "1554.11" {
             description "1554.11 nm/192.903125 THz 3.125GHz spacing";
           }
           enum "1554.08" {
             description "1554.08 nm/192.906250 THz 3.125/6.25GHz spacing";
           }
           enum "1554.06" {
             description "1554.06 nm/192.909375 THz 3.125GHz spacing";
           }
           enum "1554.03" {
             description "1554.03 nm/192.912500 THz 3.125/6.25/12.5GHz spacing";
           }
           enum "1554.01" {
             description "1554.01 nm/192.915625 THz 3.125GHz spacing";
           }
           enum "1553.98" {
             description "1553.98 nm/192.918750 THz 3.125/6.25GHz spacing";
           }
           enum "1553.96" {
             description "1553.96 nm/192.921875 THz 3.125GHz spacing";
           }
           enum "1553.93" {
             description "1553.93 nm/192.925000 THz 3.125/6.25/12.5GHz spacing";
           }
           enum "1553.91" {
             description "1553.91 nm/192.928125 THz 3.125GHz spacing";
           }
           enum "1553.88" {
             description "1553.88 nm/192.931250 THz 3.125/6.25GHz spacing";
           }
           enum "1553.86" {
             description "1553.86 nm/192.934375 THz 3.125GHz spacing";
           }
           enum "1553.83" {
             description "1553.83 nm/192.937500 THz 3.125/6.25/12.5GHz spacing";
           }
           enum "1553.81" {
             description "1553.81 nm/192.940625 THz 3.125GHz spacing";
           }
           enum "1553.78" {
             description "1553.78 nm/192.943750 THz 3.125/6.25GHz spacing";
           }
           enum "1553.76" {
             description "1553.76 nm/192.946875 THz 3.125GHz spacing";
           }
           enum "1553.73" {
             description "1553.73 nm/192.950000 THz 3.125/6.25/12.5/50GHz spacing";
           }
           enum "1553.71" {
             description "1553.71 nm/192.953125 THz 3.125GHz spacing";
           }
           enum "1553.68" {
             description "1553.68 nm/192.956250 THz 3.125/6.25GHz spacing";
           }
           enum "1553.66" {
             description "1553.66 nm/192.959375 THz 3.125GHz spacing";
           }
           enum "1553.63" {
             description "1553.63 nm/192.962500 THz 3.125/6.25/12.5GHz spacing";
           }
           enum "1553.61" {
             description "1553.61 nm/192.965625 THz 3.125GHz spacing";
           }
           enum "1553.58" {
             description "1553.58 nm/192.968750 THz 3.125/6.25GHz spacing";
           }
           enum "1553.56" {
             description "1553.56 nm/192.971875 THz 3.125GHz spacing";
           }
           enum "1553.53" {
             description "1553.53 nm/192.975000 THz 3.125/6.25/12.5/75GHz spacing";
           }
           enum "1553.50" {
             description "1553.50 nm/192.978125 THz 3.125GHz spacing";
           }
           enum "1553.48" {
             description "1553.48 nm/192.981250 THz 3.125/6.25GHz spacing";
           }
           enum "1553.45" {
             description "1553.45 nm/192.984375 THz 3.125GHz spacing";
           }
           enum "1553.43" {
             description "1553.43 nm/192.987500 THz 3.125/6.25/12.5GHz spacing";
           }
           enum "1553.40" {
             description "1553.40 nm/192.990625 THz 3.125GHz spacing";
           }
           enum "1553.38" {
             description "1553.38 nm/192.993750 THz 3.125/6.25GHz spacing";
           }
           enum "1553.35" {
             description "1553.35 nm/192.996875 THz 3.125GHz spacing";
           }
           enum "1553.33" {
             description "1553.33 nm/193.000000 THz 3.125/6.25/12.5/100GHz spacing";
           }
           enum "1553.30" {
             description "1553.30 nm/193.003125 THz 3.125GHz spacing";
           }
           enum "1553.28" {
             description "1553.28 nm/193.006250 THz 3.125/6.25GHz spacing";
           }
           enum "1553.25" {
             description "1553.25 nm/193.009375 THz 3.125GHz spacing";
           }
           enum "1553.23" {
             description "1553.23 nm/193.012500 THz 3.125/6.25/12.5GHz spacing";
           }
           enum "1553.20" {
             description "1553.20 nm/193.015625 THz 3.125GHz spacing";
           }
           enum "1553.18" {
             description "1553.18 nm/193.018750 THz 3.125/6.25GHz spacing";
           }
           enum "1553.15" {
             description "1553.15 nm/193.021875 THz 3.125GHz spacing";
           }
           enum "1553.13" {
             description "1553.13 nm/193.025000 THz 3.125/6.25/12.5GHz spacing";
           }
           enum "1553.10" {
             description "1553.10 nm/193.028125 THz 3.125GHz spacing";
           }
           enum "1553.08" {
             description "1553.08 nm/193.031250 THz 3.125/6.25GHz spacing";
           }
           enum "1553.05" {
             description "1553.05 nm/193.034375 THz 3.125GHz spacing";
           }
           enum "1553.03" {
             description "1553.03 nm/193.037500 THz 3.125/6.25/12.5GHz spacing";
           }
           enum "1553.00" {
             description "1553.00 nm/193.040625 THz 3.125GHz spacing";
           }
           enum "1552.98" {
             description "1552.98 nm/193.043750 THz 3.125/6.25GHz spacing";
           }
           enum "1552.95" {
             description "1552.95 nm/193.046875 THz 3.125GHz spacing";
           }
           enum "1552.93" {
             description "1552.93 nm/193.050000 THz 3.125/6.25/12.5/50/75GHz spacing";
           }
           enum "1552.90" {
             description "1552.90 nm/193.053125 THz 3.125GHz spacing";
           }
           enum "1552.88" {
             description "1552.88 nm/193.056250 THz 3.125/6.25GHz spacing";
           }
           enum "1552.85" {
             description "1552.85 nm/193.059375 THz 3.125GHz spacing";
           }
           enum "1552.83" {
             description "1552.83 nm/193.062500 THz 3.125/6.25/12.5GHz spacing";
           }
           enum "1552.80" {
             description "1552.80 nm/193.065625 THz 3.125GHz spacing";
           }
           enum "1552.78" {
             description "1552.78 nm/193.068750 THz 3.125/6.25GHz spacing";
           }
           enum "1552.75" {
             description "1552.75 nm/193.071875 THz 3.125GHz spacing";
           }
           enum "1552.73" {
             description "1552.73 nm/193.075000 THz 3.125/6.25/12.5GHz spacing";
           }
           enum "1552.70" {
             description "1552.70 nm/193.078125 THz 3.125GHz spacing";
           }
           enum "1552.68" {
             description "1552.68 nm/193.081250 THz 3.125/6.25GHz spacing";
           }
           enum "1552.65" {
             description "1552.65 nm/193.084375 THz 3.125GHz spacing";
           }
           enum "1552.62" {
             description "1552.62 nm/193.087500 THz 3.125/6.25/12.5GHz spacing";
           }
           enum "1552.60" {
             description "1552.60 nm/193.090625 THz 3.125GHz spacing";
           }
           enum "1552.57" {
             description "1552.57 nm/193.093750 THz 3.125/6.25GHz spacing";
           }
           enum "1552.55" {
             description "1552.55 nm/193.096875 THz 3.125GHz spacing";
           }
           enum "1552.52" {
             description "1552.52 nm/193.100000 THz 3.125/6.25/12.5/100GHz spacing";
           }
           enum "1552.50" {
             description "1552.50 nm/193.103125 THz 3.125GHz spacing";
           }
           enum "1552.47" {
             description "1552.47 nm/193.106250 THz 3.125/6.25GHz spacing";
           }
           enum "1552.45" {
             description "1552.45 nm/193.109375 THz 3.125GHz spacing";
           }
           enum "1552.42" {
             description "1552.42 nm/193.112500 THz 3.125/6.25/12.5GHz spacing";
           }
           enum "1552.40" {
             description "1552.40 nm/193.115625 THz 3.125GHz spacing";
           }
           enum "1552.37" {
             description "1552.37 nm/193.118750 THz 3.125/6.25GHz spacing";
           }
           enum "1552.35" {
             description "1552.35 nm/193.121875 THz 3.125GHz spacing";
           }
           enum "1552.32" {
             description "1552.32 nm/193.125000 THz 3.125/6.25/12.5/75GHz spacing";
           }
           enum "1552.30" {
             description "1552.30 nm/193.128125 THz 3.125GHz spacing";
           }
           enum "1552.27" {
             description "1552.27 nm/193.131250 THz 3.125/6.25GHz spacing";
           }
           enum "1552.25" {
             description "1552.25 nm/193.134375 THz 3.125GHz spacing";
           }
           enum "1552.22" {
             description "1552.22 nm/193.137500 THz 3.125/6.25/12.5GHz spacing";
           }
           enum "1552.20" {
             description "1552.20 nm/193.140625 THz 3.125GHz spacing";
           }
           enum "1552.17" {
             description "1552.17 nm/193.143750 THz 3.125/6.25GHz spacing";
           }
           enum "1552.15" {
             description "1552.15 nm/193.146875 THz 3.125GHz spacing";
           }
           enum "1552.12" {
             description "1552.12 nm/193.150000 THz 3.125/6.25/12.5/50GHz spacing";
           }
           enum "1552.10" {
             description "1552.10 nm/193.153125 THz 3.125GHz spacing";
           }
           enum "1552.07" {
             description "1552.07 nm/193.156250 THz 3.125/6.25GHz spacing";
           }
           enum "1552.05" {
             description "1552.05 nm/193.159375 THz 3.125GHz spacing";
           }
           enum "1552.02" {
             description "1552.02 nm/193.162500 THz 3.125/6.25/12.5GHz spacing";
           }
           enum "1552.00" {
             description "1552.00 nm/193.165625 THz 3.125GHz spacing";
           }
           enum "1551.97" {
             description "1551.97 nm/193.168750 THz 3.125/6.25GHz spacing";
           }
           enum "1551.95" {
             description "1551.95 nm/193.171875 THz 3.125GHz spacing";
           }
           enum "1551.92" {
             description "1551.92 nm/193.175000 THz 3.125/6.25/12.5GHz spacing";
           }
           enum "1551.90" {
             description "1551.90 nm/193.178125 THz 3.125GHz spacing";
           }
           enum "1551.87" {
             description "1551.87 nm/193.181250 THz 3.125/6.25GHz spacing";
           }
           enum "1551.85" {
             description "1551.85 nm/193.184375 THz 3.125GHz spacing";
           }
           enum "1551.82" {
             description "1551.82 nm/193.187500 THz 3.125/6.25/12.5GHz spacing";
           }
           enum "1551.80" {
             description "1551.80 nm/193.190625 THz 3.125GHz spacing";
           }
           enum "1551.77" {
             description "1551.77 nm/193.193750 THz 3.125/6.25GHz spacing";
           }
           enum "1551.75" {
             description "1551.75 nm/193.196875 THz 3.125GHz spacing";
           }
           enum "1551.72" {
             description "1551.72 nm/193.200000 THz 3.125/6.25/12.5/50/75/100GHz spacing";
           }
           enum "1551.70" {
             description "1551.70 nm/193.203125 THz 3.125GHz spacing";
           }
           enum "1551.67" {
             description "1551.67 nm/193.206250 THz 3.125/6.25GHz spacing";
           }
           enum "1551.65" {
             description "1551.65 nm/193.209375 THz 3.125GHz spacing";
           }
           enum "1551.62" {
             description "1551.62 nm/193.212500 THz 3.125/6.25/12.5GHz spacing";
           }
           enum "1551.60" {
             description "1551.60 nm/193.215625 THz 3.125GHz spacing";
           }
           enum "1551.57" {
             description "1551.57 nm/193.218750 THz 3.125/6.25GHz spacing";
           }
           enum "1551.55" {
             description "1551.55 nm/193.221875 THz 3.125GHz spacing";
           }
           enum "1551.52" {
             description "1551.52 nm/193.225000 THz 3.125/6.25/12.5GHz spacing";
           }
           enum "1551.49" {
             description "1551.49 nm/193.228125 THz 3.125GHz spacing";
           }
           enum "1551.47" {
             description "1551.47 nm/193.231250 THz 3.125/6.25GHz spacing";
           }
           enum "1551.44" {
             description "1551.44 nm/193.234375 THz 3.125GHz spacing";
           }
           enum "1551.42" {
             description "1551.42 nm/193.237500 THz 3.125/6.25/12.5GHz spacing";
           }
           enum "1551.39" {
             description "1551.39 nm/193.240625 THz 3.125GHz spacing";
           }
           enum "1551.37" {
             description "1551.37 nm/193.243750 THz 3.125/6.25GHz spacing";
           }
           enum "1551.34" {
             description "1551.34 nm/193.246875 THz 3.125GHz spacing";
           }
           enum "1551.32" {
             description "1551.32 nm/193.250000 THz 3.125/6.25/12.5/50GHz spacing";
           }
           enum "1551.29" {
             description "1551.29 nm/193.253125 THz 3.125GHz spacing";
           }
           enum "1551.27" {
             description "1551.27 nm/193.256250 THz 3.125/6.25GHz spacing";
           }
           enum "1551.24" {
             description "1551.24 nm/193.259375 THz 3.125GHz spacing";
           }
           enum "1551.22" {
             description "1551.22 nm/193.262500 THz 3.125/6.25/12.5GHz spacing";
           }
           enum "1551.19" {
             description "1551.19 nm/193.265625 THz 3.125GHz spacing";
           }
           enum "1551.17" {
             description "1551.17 nm/193.268750 THz 3.125/6.25GHz spacing";
           }
           enum "1551.14" {
             description "1551.14 nm/193.271875 THz 3.125GHz spacing";
           }
           enum "1551.12" {
             description "1551.12 nm/193.275000 THz 3.125/6.25/12.5/75GHz spacing";
           }
           enum "1551.09" {
             description "1551.09 nm/193.278125 THz 3.125GHz spacing";
           }
           enum "1551.07" {
             description "1551.07 nm/193.281250 THz 3.125/6.25GHz spacing";
           }
           enum "1551.04" {
             description "1551.04 nm/193.284375 THz 3.125GHz spacing";
           }
           enum "1551.02" {
             description "1551.02 nm/193.287500 THz 3.125/6.25/12.5GHz spacing";
           }
           enum "1550.99" {
             description "1550.99 nm/193.290625 THz 3.125GHz spacing";
           }
           enum "1550.97" {
             description "1550.97 nm/193.293750 THz 3.125/6.25GHz spacing";
           }
           enum "1550.94" {
             description "1550.94 nm/193.296875 THz 3.125GHz spacing";
           }
           enum "1550.92" {
             description "1550.92 nm/193.300000 THz 3.125/6.25/12.5/100GHz spacing";
           }
           enum "1550.89" {
             description "1550.89 nm/193.303125 THz 3.125GHz spacing";
           }
           enum "1550.87" {
             description "1550.87 nm/193.306250 THz 3.125/6.25GHz spacing";
           }
           enum "1550.84" {
             description "1550.84 nm/193.309375 THz 3.125GHz spacing";
           }
           enum "1550.82" {
             description "1550.82 nm/193.312500 THz 3.125/6.25/12.5GHz spacing";
           }
           enum "1550.79" {
             description "1550.79 nm/193.315625 THz 3.125GHz spacing";
           }
           enum "1550.77" {
             description "1550.77 nm/193.318750 THz 3.125/6.25GHz spacing";
           }
           enum "1550.74" {
             description "1550.74 nm/193.321875 THz 3.125GHz spacing";
           }
           enum "1550.72" {
             description "1550.72 nm/193.325000 THz 3.125/6.25/12.5GHz spacing";
           }
           enum "1550.69" {
             description "1550.69 nm/193.328125 THz 3.125GHz spacing";
           }
           enum "1550.67" {
             description "1550.67 nm/193.331250 THz 3.125/6.25GHz spacing";
           }
           enum "1550.64" {
             description "1550.64 nm/193.334375 THz 3.125GHz spacing";
           }
           enum "1550.62" {
             description "1550.62 nm/193.337500 THz 3.125/6.25/12.5GHz spacing";
           }
           enum "1550.59" {
             description "1550.59 nm/193.340625 THz 3.125GHz spacing";
           }
           enum "1550.57" {
             description "1550.57 nm/193.343750 THz 3.125/6.25GHz spacing";
           }
           enum "1550.54" {
             description "1550.54 nm/193.346875 THz 3.125GHz spacing";
           }
           enum "1550.52" {
             description "1550.52 nm/193.350000 THz 3.125/6.25/12.5/50/75GHz spacing";
           }
           enum "1550.49" {
             description "1550.49 nm/193.353125 THz 3.125GHz spacing";
           }
           enum "1550.47" {
             description "1550.47 nm/193.356250 THz 3.125/6.25GHz spacing";
           }
           enum "1550.44" {
             description "1550.44 nm/193.359375 THz 3.125GHz spacing";
           }
           enum "1550.42" {
             description "1550.42 nm/193.362500 THz 3.125/6.25/12.5GHz spacing";
           }
           enum "1550.39" {
             description "1550.39 nm/193.365625 THz 3.125GHz spacing";
           }
           enum "1550.37" {
             description "1550.37 nm/193.368750 THz 3.125/6.25GHz spacing";
           }
           enum "1550.34" {
             description "1550.34 nm/193.371875 THz 3.125GHz spacing";
           }
           enum "1550.32" {
             description "1550.32 nm/193.375000 THz 3.125/6.25/12.5GHz spacing";
           }
           enum "1550.29" {
             description "1550.29 nm/193.378125 THz 3.125GHz spacing";
           }
           enum "1550.27" {
             description "1550.27 nm/193.381250 THz 3.125/6.25GHz spacing";
           }
           enum "1550.24" {
             description "1550.24 nm/193.384375 THz 3.125GHz spacing";
           }
           enum "1550.22" {
             description "1550.22 nm/193.387500 THz 3.125/6.25/12.5GHz spacing";
           }
           enum "1550.19" {
             description "1550.19 nm/193.390625 THz 3.125GHz spacing";
           }
           enum "1550.17" {
             description "1550.17 nm/193.393750 THz 3.125/6.25GHz spacing";
           }
           enum "1550.14" {
             description "1550.14 nm/193.396875 THz 3.125GHz spacing";
           }
           enum "1550.12" {
             description "1550.12 nm/193.400000 THz 3.125/6.25/12.5/100GHz spacing";
           }
           enum "1550.09" {
             description "1550.09 nm/193.403125 THz 3.125GHz spacing";
           }
           enum "1550.07" {
             description "1550.07 nm/193.406250 THz 3.125/6.25GHz spacing";
           }
           enum "1550.04" {
             description "1550.04 nm/193.409375 THz 3.125GHz spacing";
           }
           enum "1550.02" {
             description "1550.02 nm/193.412500 THz 3.125/6.25/12.5GHz spacing";
           }
           enum "1549.99" {
             description "1549.99 nm/193.415625 THz 3.125GHz spacing";
           }
           enum "1549.97" {
             description "1549.97 nm/193.418750 THz 3.125/6.25GHz spacing";
           }
           enum "1549.94" {
             description "1549.94 nm/193.421875 THz 3.125GHz spacing";
           }
           enum "1549.92" {
             description "1549.92 nm/193.425000 THz 3.125/6.25/12.5/75GHz spacing";
           }
           enum "1549.89" {
             description "1549.89 nm/193.428125 THz 3.125GHz spacing";
           }
           enum "1549.87" {
             description "1549.87 nm/193.431250 THz 3.125/6.25GHz spacing";
           }
           enum "1549.84" {
             description "1549.84 nm/193.434375 THz 3.125GHz spacing";
           }
           enum "1549.82" {
             description "1549.82 nm/193.437500 THz 3.125/6.25/12.5GHz spacing";
           }
           enum "1549.79" {
             description "1549.79 nm/193.440625 THz 3.125GHz spacing";
           }
           enum "1549.77" {
             description "1549.77 nm/193.443750 THz 3.125/6.25GHz spacing";
           }
           enum "1549.74" {
             description "1549.74 nm/193.446875 THz 3.125GHz spacing";
           }
           enum "1549.72" {
             description "1549.72 nm/193.450000 THz 3.125/6.25/12.5/50GHz spacing";
           }
           enum "1549.69" {
             description "1549.69 nm/193.453125 THz 3.125GHz spacing";
           }
           enum "1549.67" {
             description "1549.67 nm/193.456250 THz 3.125/6.25GHz spacing";
           }
           enum "1549.64" {
             description "1549.64 nm/193.459375 THz 3.125GHz spacing";
           }
           enum "1549.62" {
             description "1549.62 nm/193.462500 THz 3.125/6.25/12.5GHz spacing";
           }
           enum "1549.59" {
             description "1549.59 nm/193.465625 THz 3.125GHz spacing";
           }
           enum "1549.57" {
             description "1549.57 nm/193.468750 THz 3.125/6.25GHz spacing";
           }
           enum "1549.54" {
             description "1549.54 nm/193.471875 THz 3.125GHz spacing";
           }
           enum "1549.52" {
             description "1549.52 nm/193.475000 THz 3.125/6.25/12.5GHz spacing";
           }
           enum "1549.49" {
             description "1549.49 nm/193.478125 THz 3.125GHz spacing";
           }
           enum "1549.47" {
             description "1549.47 nm/193.481250 THz 3.125/6.25GHz spacing";
           }
           enum "1549.44" {
             description "1549.44 nm/193.484375 THz 3.125GHz spacing";
           }
           enum "1549.42" {
             description "1549.42 nm/193.487500 THz 3.125/6.25/12.5GHz spacing";
           }
           enum "1549.39" {
             description "1549.39 nm/193.490625 THz 3.125GHz spacing";
           }
           enum "1549.37" {
             description "1549.37 nm/193.493750 THz 3.125/6.25GHz spacing";
           }
           enum "1549.34" {
             description "1549.34 nm/193.496875 THz 3.125GHz spacing";
           }
           enum "1549.32" {
             description "1549.32 nm/193.500000 THz 3.125/6.25/12.5/50/75/100GHz spacing";
           }
           enum "1549.29" {
             description "1549.29 nm/193.503125 THz 3.125GHz spacing";
           }
           enum "1549.26" {
             description "1549.26 nm/193.506250 THz 3.125/6.25GHz spacing";
           }
           enum "1549.24" {
             description "1549.24 nm/193.509375 THz 3.125GHz spacing";
           }
           enum "1549.21" {
             description "1549.21 nm/193.512500 THz 3.125/6.25/12.5GHz spacing";
           }
           enum "1549.19" {
             description "1549.19 nm/193.515625 THz 3.125GHz spacing";
           }
           enum "1549.16" {
             description "1549.16 nm/193.518750 THz 3.125/6.25GHz spacing";
           }
           enum "1549.14" {
             description "1549.14 nm/193.521875 THz 3.125GHz spacing";
           }
           enum "1549.11" {
             description "1549.11 nm/193.525000 THz 3.125/6.25/12.5GHz spacing";
           }
           enum "1549.09" {
             description "1549.09 nm/193.528125 THz 3.125GHz spacing";
           }
           enum "1549.06" {
             description "1549.06 nm/193.531250 THz 3.125/6.25GHz spacing";
           }
           enum "1549.04" {
             description "1549.04 nm/193.534375 THz 3.125GHz spacing";
           }
           enum "1549.01" {
             description "1549.01 nm/193.537500 THz 3.125/6.25/12.5GHz spacing";
           }
           enum "1548.99" {
             description "1548.99 nm/193.540625 THz 3.125GHz spacing";
           }
           enum "1548.96" {
             description "1548.96 nm/193.543750 THz 3.125/6.25GHz spacing";
           }
           enum "1548.94" {
             description "1548.94 nm/193.546875 THz 3.125GHz spacing";
           }
           enum "1548.91" {
             description "1548.91 nm/193.550000 THz 3.125/6.25/12.5/50GHz spacing";
           }
           enum "1548.89" {
             description "1548.89 nm/193.553125 THz 3.125GHz spacing";
           }
           enum "1548.86" {
             description "1548.86 nm/193.556250 THz 3.125/6.25GHz spacing";
           }
           enum "1548.84" {
             description "1548.84 nm/193.559375 THz 3.125GHz spacing";
           }
           enum "1548.81" {
             description "1548.81 nm/193.562500 THz 3.125/6.25/12.5GHz spacing";
           }
           enum "1548.79" {
             description "1548.79 nm/193.565625 THz 3.125GHz spacing";
           }
           enum "1548.76" {
             description "1548.76 nm/193.568750 THz 3.125/6.25GHz spacing";
           }
           enum "1548.74" {
             description "1548.74 nm/193.571875 THz 3.125GHz spacing";
           }
           enum "1548.71" {
             description "1548.71 nm/193.575000 THz 3.125/6.25/12.5/75GHz spacing";
           }
           enum "1548.69" {
             description "1548.69 nm/193.578125 THz 3.125GHz spacing";
           }
           enum "1548.66" {
             description "1548.66 nm/193.581250 THz 3.125/6.25GHz spacing";
           }
           enum "1548.64" {
             description "1548.64 nm/193.584375 THz 3.125GHz spacing";
           }
           enum "1548.61" {
             description "1548.61 nm/193.587500 THz 3.125/6.25/12.5GHz spacing";
           }
           enum "1548.59" {
             description "1548.59 nm/193.590625 THz 3.125GHz spacing";
           }
           enum "1548.56" {
             description "1548.56 nm/193.593750 THz 3.125/6.25GHz spacing";
           }
           enum "1548.54" {
             description "1548.54 nm/193.596875 THz 3.125GHz spacing";
           }
           enum "1548.51" {
             description "1548.51 nm/193.600000 THz 3.125/6.25/12.5/100GHz spacing";
           }
           enum "1548.49" {
             description "1548.49 nm/193.603125 THz 3.125GHz spacing";
           }
           enum "1548.46" {
             description "1548.46 nm/193.606250 THz 3.125/6.25GHz spacing";
           }
           enum "1548.44" {
             description "1548.44 nm/193.609375 THz 3.125GHz spacing";
           }
           enum "1548.41" {
             description "1548.41 nm/193.612500 THz 3.125/6.25/12.5GHz spacing";
           }
           enum "1548.39" {
             description "1548.39 nm/193.615625 THz 3.125GHz spacing";
           }
           enum "1548.36" {
             description "1548.36 nm/193.618750 THz 3.125/6.25GHz spacing";
           }
           enum "1548.34" {
             description "1548.34 nm/193.621875 THz 3.125GHz spacing";
           }
           enum "1548.31" {
             description "1548.31 nm/193.625000 THz 3.125/6.25/12.5GHz spacing";
           }
           enum "1548.29" {
             description "1548.29 nm/193.628125 THz 3.125GHz spacing";
           }
           enum "1548.26" {
             description "1548.26 nm/193.631250 THz 3.125/6.25GHz spacing";
           }
           enum "1548.24" {
             description "1548.24 nm/193.634375 THz 3.125GHz spacing";
           }
           enum "1548.21" {
             description "1548.21 nm/193.637500 THz 3.125/6.25/12.5GHz spacing";
           }
           enum "1548.19" {
             description "1548.19 nm/193.640625 THz 3.125GHz spacing";
           }
           enum "1548.16" {
             description "1548.16 nm/193.643750 THz 3.125/6.25GHz spacing";
           }
           enum "1548.14" {
             description "1548.14 nm/193.646875 THz 3.125GHz spacing";
           }
           enum "1548.11" {
             description "1548.11 nm/193.650000 THz 3.125/6.25/12.5/50/75GHz spacing";
           }
           enum "1548.09" {
             description "1548.09 nm/193.653125 THz 3.125GHz spacing";
           }
           enum "1548.06" {
             description "1548.06 nm/193.656250 THz 3.125/6.25GHz spacing";
           }
           enum "1548.04" {
             description "1548.04 nm/193.659375 THz 3.125GHz spacing";
           }
           enum "1548.02" {
             description "1548.02 nm/193.662500 THz 3.125/6.25/12.5GHz spacing";
           }
           enum "1547.99" {
             description "1547.99 nm/193.665625 THz 3.125GHz spacing";
           }
           enum "1547.97" {
             description "1547.97 nm/193.668750 THz 3.125/6.25GHz spacing";
           }
           enum "1547.94" {
             description "1547.94 nm/193.671875 THz 3.125GHz spacing";
           }
           enum "1547.92" {
             description "1547.92 nm/193.675000 THz 3.125/6.25/12.5GHz spacing";
           }
           enum "1547.89" {
             description "1547.89 nm/193.678125 THz 3.125GHz spacing";
           }
           enum "1547.87" {
             description "1547.87 nm/193.681250 THz 3.125/6.25GHz spacing";
           }
           enum "1547.84" {
             description "1547.84 nm/193.684375 THz 3.125GHz spacing";
           }
           enum "1547.82" {
             description "1547.82 nm/193.687500 THz 3.125/6.25/12.5GHz spacing";
           }
           enum "1547.79" {
             description "1547.79 nm/193.690625 THz 3.125GHz spacing";
           }
           enum "1547.77" {
             description "1547.77 nm/193.693750 THz 3.125/6.25GHz spacing";
           }
           enum "1547.74" {
             description "1547.74 nm/193.696875 THz 3.125GHz spacing";
           }
           enum "1547.72" {
             description "1547.72 nm/193.700000 THz 3.125/6.25/12.5/100GHz spacing";
           }
           enum "1547.69" {
             description "1547.69 nm/193.703125 THz 3.125GHz spacing";
           }
           enum "1547.67" {
             description "1547.67 nm/193.706250 THz 3.125/6.25GHz spacing";
           }
           enum "1547.64" {
             description "1547.64 nm/193.709375 THz 3.125GHz spacing";
           }
           enum "1547.62" {
             description "1547.62 nm/193.712500 THz 3.125/6.25/12.5GHz spacing";
           }
           enum "1547.59" {
             description "1547.59 nm/193.715625 THz 3.125GHz spacing";
           }
           enum "1547.57" {
             description "1547.57 nm/193.718750 THz 3.125/6.25GHz spacing";
           }
           enum "1547.54" {
             description "1547.54 nm/193.721875 THz 3.125GHz spacing";
           }
           enum "1547.52" {
             description "1547.52 nm/193.725000 THz 3.125/6.25/12.5/75GHz spacing";
           }
           enum "1547.49" {
             description "1547.49 nm/193.728125 THz 3.125GHz spacing";
           }
           enum "1547.47" {
             description "1547.47 nm/193.731250 THz 3.125/6.25GHz spacing";
           }
           enum "1547.44" {
             description "1547.44 nm/193.734375 THz 3.125GHz spacing";
           }
           enum "1547.42" {
             description "1547.42 nm/193.737500 THz 3.125/6.25/12.5GHz spacing";
           }
           enum "1547.39" {
             description "1547.39 nm/193.740625 THz 3.125GHz spacing";
           }
           enum "1547.37" {
             description "1547.37 nm/193.743750 THz 3.125/6.25GHz spacing";
           }
           enum "1547.34" {
             description "1547.34 nm/193.746875 THz 3.125GHz spacing";
           }
           enum "1547.32" {
             description "1547.32 nm/193.750000 THz 3.125/6.25/12.5/50GHz spacing";
           }
           enum "1547.29" {
             description "1547.29 nm/193.753125 THz 3.125GHz spacing";
           }
           enum "1547.27" {
             description "1547.27 nm/193.756250 THz 3.125/6.25GHz spacing";
           }
           enum "1547.24" {
             description "1547.24 nm/193.759375 THz 3.125GHz spacing";
           }
           enum "1547.22" {
             description "1547.22 nm/193.762500 THz 3.125/6.25/12.5GHz spacing";
           }
           enum "1547.19" {
             description "1547.19 nm/193.765625 THz 3.125GHz spacing";
           }
           enum "1547.17" {
             description "1547.17 nm/193.768750 THz 3.125/6.25GHz spacing";
           }
           enum "1547.14" {
             description "1547.14 nm/193.771875 THz 3.125GHz spacing";
           }
           enum "1547.12" {
             description "1547.12 nm/193.775000 THz 3.125/6.25/12.5GHz spacing";
           }
           enum "1547.09" {
             description "1547.09 nm/193.778125 THz 3.125GHz spacing";
           }
           enum "1547.07" {
             description "1547.07 nm/193.781250 THz 3.125/6.25GHz spacing";
           }
           enum "1547.04" {
             description "1547.04 nm/193.784375 THz 3.125GHz spacing";
           }
           enum "1547.02" {
             description "1547.02 nm/193.787500 THz 3.125/6.25/12.5GHz spacing";
           }
           enum "1546.99" {
             description "1546.99 nm/193.790625 THz 3.125GHz spacing";
           }
           enum "1546.97" {
             description "1546.97 nm/193.793750 THz 3.125/6.25GHz spacing";
           }
           enum "1546.94" {
             description "1546.94 nm/193.796875 THz 3.125GHz spacing";
           }
           enum "1546.92" {
             description "1546.92 nm/193.800000 THz 3.125/6.25/12.5/50/75/100GHz spacing";
           }
           enum "1546.89" {
             description "1546.89 nm/193.803125 THz 3.125GHz spacing";
           }
           enum "1546.87" {
             description "1546.87 nm/193.806250 THz 3.125/6.25GHz spacing";
           }
           enum "1546.84" {
             description "1546.84 nm/193.809375 THz 3.125GHz spacing";
           }
           enum "1546.82" {
             description "1546.82 nm/193.812500 THz 3.125/6.25/12.5GHz spacing";
           }
           enum "1546.79" {
             description "1546.79 nm/193.815625 THz 3.125GHz spacing";
           }
           enum "1546.77" {
             description "1546.77 nm/193.818750 THz 3.125/6.25GHz spacing";
           }
           enum "1546.74" {
             description "1546.74 nm/193.821875 THz 3.125GHz spacing";
           }
           enum "1546.72" {
             description "1546.72 nm/193.825000 THz 3.125/6.25/12.5GHz spacing";
           }
           enum "1546.69" {
             description "1546.69 nm/193.828125 THz 3.125GHz spacing";
           }
           enum "1546.67" {
             description "1546.67 nm/193.831250 THz 3.125/6.25GHz spacing";
           }
           enum "1546.64" {
             description "1546.64 nm/193.834375 THz 3.125GHz spacing";
           }
           enum "1546.62" {
             description "1546.62 nm/193.837500 THz 3.125/6.25/12.5GHz spacing";
           }
           enum "1546.59" {
             description "1546.59 nm/193.840625 THz 3.125GHz spacing";
           }
           enum "1546.57" {
             description "1546.57 nm/193.843750 THz 3.125/6.25GHz spacing";
           }
           enum "1546.54" {
             description "1546.54 nm/193.846875 THz 3.125GHz spacing";
           }
           enum "1546.52" {
             description "1546.52 nm/193.850000 THz 3.125/6.25/12.5/50GHz spacing";
           }
           enum "1546.49" {
             description "1546.49 nm/193.853125 THz 3.125GHz spacing";
           }
           enum "1546.47" {
             description "1546.47 nm/193.856250 THz 3.125/6.25GHz spacing";
           }
           enum "1546.44" {
             description "1546.44 nm/193.859375 THz 3.125GHz spacing";
           }
           enum "1546.42" {
             description "1546.42 nm/193.862500 THz 3.125/6.25/12.5GHz spacing";
           }
           enum "1546.39" {
             description "1546.39 nm/193.865625 THz 3.125GHz spacing";
           }
           enum "1546.37" {
             description "1546.37 nm/193.868750 THz 3.125/6.25GHz spacing";
           }
           enum "1546.34" {
             description "1546.34 nm/193.871875 THz 3.125GHz spacing";
           }
           enum "1546.32" {
             description "1546.32 nm/193.875000 THz 3.125/6.25/12.5/75GHz spacing";
           }
           enum "1546.29" {
             description "1546.29 nm/193.878125 THz 3.125GHz spacing";
           }
           enum "1546.27" {
             description "1546.27 nm/193.881250 THz 3.125/6.25GHz spacing";
           }
           enum "1546.24" {
             description "1546.24 nm/193.884375 THz 3.125GHz spacing";
           }
           enum "1546.22" {
             description "1546.22 nm/193.887500 THz 3.125/6.25/12.5GHz spacing";
           }
           enum "1546.19" {
             description "1546.19 nm/193.890625 THz 3.125GHz spacing";
           }
           enum "1546.17" {
             description "1546.17 nm/193.893750 THz 3.125/6.25GHz spacing";
           }
           enum "1546.14" {
             description "1546.14 nm/193.896875 THz 3.125GHz spacing";
           }
           enum "1546.12" {
             description "1546.12 nm/193.900000 THz 3.125/6.25/12.5/100GHz spacing";
           }
           enum "1546.09" {
             description "1546.09 nm/193.903125 THz 3.125GHz spacing";
           }
           enum "1546.07" {
             description "1546.07 nm/193.906250 THz 3.125/6.25GHz spacing";
           }
           enum "1546.04" {
             description "1546.04 nm/193.909375 THz 3.125GHz spacing";
           }
           enum "1546.02" {
             description "1546.02 nm/193.912500 THz 3.125/6.25/12.5GHz spacing";
           }
           enum "1545.99" {
             description "1545.99 nm/193.915625 THz 3.125GHz spacing";
           }
           enum "1545.97" {
             description "1545.97 nm/193.918750 THz 3.125/6.25GHz spacing";
           }
           enum "1545.94" {
             description "1545.94 nm/193.921875 THz 3.125GHz spacing";
           }
           enum "1545.92" {
             description "1545.92 nm/193.925000 THz 3.125/6.25/12.5GHz spacing";
           }
           enum "1545.89" {
             description "1545.89 nm/193.928125 THz 3.125GHz spacing";
           }
           enum "1545.87" {
             description "1545.87 nm/193.931250 THz 3.125/6.25GHz spacing";
           }
           enum "1545.84" {
             description "1545.84 nm/193.934375 THz 3.125GHz spacing";
           }
           enum "1545.82" {
             description "1545.82 nm/193.937500 THz 3.125/6.25/12.5GHz spacing";
           }
           enum "1545.80" {
             description "1545.80 nm/193.940625 THz 3.125GHz spacing";
           }
           enum "1545.77" {
             description "1545.77 nm/193.943750 THz 3.125/6.25GHz spacing";
           }
           enum "1545.75" {
             description "1545.75 nm/193.946875 THz 3.125GHz spacing";
           }
           enum "1545.72" {
             description "1545.72 nm/193.950000 THz 3.125/6.25/12.5/50/75GHz spacing";
           }
           enum "1545.70" {
             description "1545.70 nm/193.953125 THz 3.125GHz spacing";
           }
           enum "1545.67" {
             description "1545.67 nm/193.956250 THz 3.125/6.25GHz spacing";
           }
           enum "1545.65" {
             description "1545.65 nm/193.959375 THz 3.125GHz spacing";
           }
           enum "1545.62" {
             description "1545.62 nm/193.962500 THz 3.125/6.25/12.5GHz spacing";
           }
           enum "1545.60" {
             description "1545.60 nm/193.965625 THz 3.125GHz spacing";
           }
           enum "1545.57" {
             description "1545.57 nm/193.968750 THz 3.125/6.25GHz spacing";
           }
           enum "1545.55" {
             description "1545.55 nm/193.971875 THz 3.125GHz spacing";
           }
           enum "1545.52" {
             description "1545.52 nm/193.975000 THz 3.125/6.25/12.5GHz spacing";
           }
           enum "1545.50" {
             description "1545.50 nm/193.978125 THz 3.125GHz spacing";
           }
           enum "1545.47" {
             description "1545.47 nm/193.981250 THz 3.125/6.25GHz spacing";
           }
           enum "1545.45" {
             description "1545.45 nm/193.984375 THz 3.125GHz spacing";
           }
           enum "1545.42" {
             description "1545.42 nm/193.987500 THz 3.125/6.25/12.5GHz spacing";
           }
           enum "1545.40" {
             description "1545.40 nm/193.990625 THz 3.125GHz spacing";
           }
           enum "1545.37" {
             description "1545.37 nm/193.993750 THz 3.125/6.25GHz spacing";
           }
           enum "1545.35" {
             description "1545.35 nm/193.996875 THz 3.125GHz spacing";
           }
           enum "1545.32" {
             description "1545.32 nm/194.000000 THz 3.125/6.25/12.5/100GHz spacing";
           }
           enum "1545.30" {
             description "1545.30 nm/194.003125 THz 3.125GHz spacing";
           }
           enum "1545.27" {
             description "1545.27 nm/194.006250 THz 3.125/6.25GHz spacing";
           }
           enum "1545.25" {
             description "1545.25 nm/194.009375 THz 3.125GHz spacing";
           }
           enum "1545.22" {
             description "1545.22 nm/194.012500 THz 3.125/6.25/12.5GHz spacing";
           }
           enum "1545.20" {
             description "1545.20 nm/194.015625 THz 3.125GHz spacing";
           }
           enum "1545.17" {
             description "1545.17 nm/194.018750 THz 3.125/6.25GHz spacing";
           }
           enum "1545.15" {
             description "1545.15 nm/194.021875 THz 3.125GHz spacing";
           }
           enum "1545.12" {
             description "1545.12 nm/194.025000 THz 3.125/6.25/12.5/75GHz spacing";
           }
           enum "1545.10" {
             description "1545.10 nm/194.028125 THz 3.125GHz spacing";
           }
           enum "1545.07" {
             description "1545.07 nm/194.031250 THz 3.125/6.25GHz spacing";
           }
           enum "1545.05" {
             description "1545.05 nm/194.034375 THz 3.125GHz spacing";
           }
           enum "1545.02" {
             description "1545.02 nm/194.037500 THz 3.125/6.25/12.5GHz spacing";
           }
           enum "1545.00" {
             description "1545.00 nm/194.040625 THz 3.125GHz spacing";
           }
           enum "1544.97" {
             description "1544.97 nm/194.043750 THz 3.125/6.25GHz spacing";
           }
           enum "1544.95" {
             description "1544.95 nm/194.046875 THz 3.125GHz spacing";
           }
           enum "1544.92" {
             description "1544.92 nm/194.050000 THz 3.125/6.25/12.5/50GHz spacing";
           }
           enum "1544.90" {
             description "1544.90 nm/194.053125 THz 3.125GHz spacing";
           }
           enum "1544.87" {
             description "1544.87 nm/194.056250 THz 3.125/6.25GHz spacing";
           }
           enum "1544.85" {
             description "1544.85 nm/194.059375 THz 3.125GHz spacing";
           }
           enum "1544.82" {
             description "1544.82 nm/194.062500 THz 3.125/6.25/12.5GHz spacing";
           }
           enum "1544.80" {
             description "1544.80 nm/194.065625 THz 3.125GHz spacing";
           }
           enum "1544.77" {
             description "1544.77 nm/194.068750 THz 3.125/6.25GHz spacing";
           }
           enum "1544.75" {
             description "1544.75 nm/194.071875 THz 3.125GHz spacing";
           }
           enum "1544.72" {
             description "1544.72 nm/194.075000 THz 3.125/6.25/12.5GHz spacing";
           }
           enum "1544.70" {
             description "1544.70 nm/194.078125 THz 3.125GHz spacing";
           }
           enum "1544.68" {
             description "1544.68 nm/194.081250 THz 3.125/6.25GHz spacing";
           }
           enum "1544.65" {
             description "1544.65 nm/194.084375 THz 3.125GHz spacing";
           }
           enum "1544.63" {
             description "1544.63 nm/194.087500 THz 3.125/6.25/12.5GHz spacing";
           }
           enum "1544.60" {
             description "1544.60 nm/194.090625 THz 3.125GHz spacing";
           }
           enum "1544.58" {
             description "1544.58 nm/194.093750 THz 3.125/6.25GHz spacing";
           }
           enum "1544.55" {
             description "1544.55 nm/194.096875 THz 3.125GHz spacing";
           }
           enum "1544.53" {
             description "1544.53 nm/194.100000 THz 3.125/6.25/12.5/50/75/100GHz spacing";
           }
           enum "1544.50" {
             description "1544.50 nm/194.103125 THz 3.125GHz spacing";
           }
           enum "1544.48" {
             description "1544.48 nm/194.106250 THz 3.125/6.25GHz spacing";
           }
           enum "1544.45" {
             description "1544.45 nm/194.109375 THz 3.125GHz spacing";
           }
           enum "1544.43" {
             description "1544.43 nm/194.112500 THz 3.125/6.25/12.5GHz spacing";
           }
           enum "1544.40" {
             description "1544.40 nm/194.115625 THz 3.125GHz spacing";
           }
           enum "1544.38" {
             description "1544.38 nm/194.118750 THz 3.125/6.25GHz spacing";
           }
           enum "1544.35" {
             description "1544.35 nm/194.121875 THz 3.125GHz spacing";
           }
           enum "1544.33" {
             description "1544.33 nm/194.125000 THz 3.125/6.25/12.5GHz spacing";
           }
           enum "1544.30" {
             description "1544.30 nm/194.128125 THz 3.125GHz spacing";
           }
           enum "1544.28" {
             description "1544.28 nm/194.131250 THz 3.125/6.25GHz spacing";
           }
           enum "1544.25" {
             description "1544.25 nm/194.134375 THz 3.125GHz spacing";
           }
           enum "1544.23" {
             description "1544.23 nm/194.137500 THz 3.125/6.25/12.5GHz spacing";
           }
           enum "1544.20" {
             description "1544.20 nm/194.140625 THz 3.125GHz spacing";
           }
           enum "1544.18" {
             description "1544.18 nm/194.143750 THz 3.125/6.25GHz spacing";
           }
           enum "1544.15" {
             description "1544.15 nm/194.146875 THz 3.125GHz spacing";
           }
           enum "1544.13" {
             description "1544.13 nm/194.150000 THz 3.125/6.25/12.5/50GHz spacing";
           }
           enum "1544.10" {
             description "1544.10 nm/194.153125 THz 3.125GHz spacing";
           }
           enum "1544.08" {
             description "1544.08 nm/194.156250 THz 3.125/6.25GHz spacing";
           }
           enum "1544.05" {
             description "1544.05 nm/194.159375 THz 3.125GHz spacing";
           }
           enum "1544.03" {
             description "1544.03 nm/194.162500 THz 3.125/6.25/12.5GHz spacing";
           }
           enum "1544.00" {
             description "1544.00 nm/194.165625 THz 3.125GHz spacing";
           }
           enum "1543.98" {
             description "1543.98 nm/194.168750 THz 3.125/6.25GHz spacing";
           }
           enum "1543.95" {
             description "1543.95 nm/194.171875 THz 3.125GHz spacing";
           }
           enum "1543.93" {
             description "1543.93 nm/194.175000 THz 3.125/6.25/12.5/75GHz spacing";
           }
           enum "1543.90" {
             description "1543.90 nm/194.178125 THz 3.125GHz spacing";
           }
           enum "1543.88" {
             description "1543.88 nm/194.181250 THz 3.125/6.25GHz spacing";
           }
           enum "1543.85" {
             description "1543.85 nm/194.184375 THz 3.125GHz spacing";
           }
           enum "1543.83" {
             description "1543.83 nm/194.187500 THz 3.125/6.25/12.5GHz spacing";
           }
           enum "1543.81" {
             description "1543.81 nm/194.190625 THz 3.125GHz spacing";
           }
           enum "1543.78" {
             description "1543.78 nm/194.193750 THz 3.125/6.25GHz spacing";
           }
           enum "1543.76" {
             description "1543.76 nm/194.196875 THz 3.125GHz spacing";
           }
           enum "1543.73" {
             description "1543.73 nm/194.200000 THz 3.125/6.25/12.5/100GHz spacing";
           }
           enum "1543.71" {
             description "1543.71 nm/194.203125 THz 3.125GHz spacing";
           }
           enum "1543.68" {
             description "1543.68 nm/194.206250 THz 3.125/6.25GHz spacing";
           }
           enum "1543.66" {
             description "1543.66 nm/194.209375 THz 3.125GHz spacing";
           }
           enum "1543.63" {
             description "1543.63 nm/194.212500 THz 3.125/6.25/12.5GHz spacing";
           }
           enum "1543.61" {
             description "1543.61 nm/194.215625 THz 3.125GHz spacing";
           }
           enum "1543.58" {
             description "1543.58 nm/194.218750 THz 3.125/6.25GHz spacing";
           }
           enum "1543.56" {
             description "1543.56 nm/194.221875 THz 3.125GHz spacing";
           }
           enum "1543.53" {
             description "1543.53 nm/194.225000 THz 3.125/6.25/12.5GHz spacing";
           }
           enum "1543.51" {
             description "1543.51 nm/194.228125 THz 3.125GHz spacing";
           }
           enum "1543.48" {
             description "1543.48 nm/194.231250 THz 3.125/6.25GHz spacing";
           }
           enum "1543.46" {
             description "1543.46 nm/194.234375 THz 3.125GHz spacing";
           }
           enum "1543.43" {
             description "1543.43 nm/194.237500 THz 3.125/6.25/12.5GHz spacing";
           }
           enum "1543.41" {
             description "1543.41 nm/194.240625 THz 3.125GHz spacing";
           }
           enum "1543.38" {
             description "1543.38 nm/194.243750 THz 3.125/6.25GHz spacing";
           }
           enum "1543.36" {
             description "1543.36 nm/194.246875 THz 3.125GHz spacing";
           }
           enum "1543.33" {
             description "1543.33 nm/194.250000 THz 3.125/6.25/12.5/50/75GHz spacing";
           }
           enum "1543.31" {
             description "1543.31 nm/194.253125 THz 3.125GHz spacing";
           }
           enum "1543.28" {
             description "1543.28 nm/194.256250 THz 3.125/6.25GHz spacing";
           }
           enum "1543.26" {
             description "1543.26 nm/194.259375 THz 3.125GHz spacing";
           }
           enum "1543.23" {
             description "1543.23 nm/194.262500 THz 3.125/6.25/12.5GHz spacing";
           }
           enum "1543.21" {
             description "1543.21 nm/194.265625 THz 3.125GHz spacing";
           }
           enum "1543.18" {
             description "1543.18 nm/194.268750 THz 3.125/6.25GHz spacing";
           }
           enum "1543.16" {
             description "1543.16 nm/194.271875 THz 3.125GHz spacing";
           }
           enum "1543.13" {
             description "1543.13 nm/194.275000 THz 3.125/6.25/12.5GHz spacing";
           }
           enum "1543.11" {
             description "1543.11 nm/194.278125 THz 3.125GHz spacing";
           }
           enum "1543.08" {
             description "1543.08 nm/194.281250 THz 3.125/6.25GHz spacing";
           }
           enum "1543.06" {
             description "1543.06 nm/194.284375 THz 3.125GHz spacing";
           }
           enum "1543.04" {
             description "1543.04 nm/194.287500 THz 3.125/6.25/12.5GHz spacing";
           }
           enum "1543.01" {
             description "1543.01 nm/194.290625 THz 3.125GHz spacing";
           }
           enum "1542.99" {
             description "1542.99 nm/194.293750 THz 3.125/6.25GHz spacing";
           }
           enum "1542.96" {
             description "1542.96 nm/194.296875 THz 3.125GHz spacing";
           }
           enum "1542.94" {
             description "1542.94 nm/194.300000 THz 3.125/6.25/12.5/100GHz spacing";
           }
           enum "1542.91" {
             description "1542.91 nm/194.303125 THz 3.125GHz spacing";
           }
           enum "1542.89" {
             description "1542.89 nm/194.306250 THz 3.125/6.25GHz spacing";
           }
           enum "1542.86" {
             description "1542.86 nm/194.309375 THz 3.125GHz spacing";
           }
           enum "1542.84" {
             description "1542.84 nm/194.312500 THz 3.125/6.25/12.5GHz spacing";
           }
           enum "1542.81" {
             description "1542.81 nm/194.315625 THz 3.125GHz spacing";
           }
           enum "1542.79" {
             description "1542.79 nm/194.318750 THz 3.125/6.25GHz spacing";
           }
           enum "1542.76" {
             description "1542.76 nm/194.321875 THz 3.125GHz spacing";
           }
           enum "1542.74" {
             description "1542.74 nm/194.325000 THz 3.125/6.25/12.5/75GHz spacing";
           }
           enum "1542.71" {
             description "1542.71 nm/194.328125 THz 3.125GHz spacing";
           }
           enum "1542.69" {
             description "1542.69 nm/194.331250 THz 3.125/6.25GHz spacing";
           }
           enum "1542.66" {
             description "1542.66 nm/194.334375 THz 3.125GHz spacing";
           }
           enum "1542.64" {
             description "1542.64 nm/194.337500 THz 3.125/6.25/12.5GHz spacing";
           }
           enum "1542.61" {
             description "1542.61 nm/194.340625 THz 3.125GHz spacing";
           }
           enum "1542.59" {
             description "1542.59 nm/194.343750 THz 3.125/6.25GHz spacing";
           }
           enum "1542.56" {
             description "1542.56 nm/194.346875 THz 3.125GHz spacing";
           }
           enum "1542.54" {
             description "1542.54 nm/194.350000 THz 3.125/6.25/12.5/50GHz spacing";
           }
           enum "1542.51" {
             description "1542.51 nm/194.353125 THz 3.125GHz spacing";
           }
           enum "1542.49" {
             description "1542.49 nm/194.356250 THz 3.125/6.25GHz spacing";
           }
           enum "1542.46" {
             description "1542.46 nm/194.359375 THz 3.125GHz spacing";
           }
           enum "1542.44" {
             description "1542.44 nm/194.362500 THz 3.125/6.25/12.5GHz spacing";
           }
           enum "1542.42" {
             description "1542.42 nm/194.365625 THz 3.125GHz spacing";
           }
           enum "1542.39" {
             description "1542.39 nm/194.368750 THz 3.125/6.25GHz spacing";
           }
           enum "1542.37" {
             description "1542.37 nm/194.371875 THz 3.125GHz spacing";
           }
           enum "1542.34" {
             description "1542.34 nm/194.375000 THz 3.125/6.25/12.5GHz spacing";
           }
           enum "1542.32" {
             description "1542.32 nm/194.378125 THz 3.125GHz spacing";
           }
           enum "1542.29" {
             description "1542.29 nm/194.381250 THz 3.125/6.25GHz spacing";
           }
           enum "1542.27" {
             description "1542.27 nm/194.384375 THz 3.125GHz spacing";
           }
           enum "1542.24" {
             description "1542.24 nm/194.387500 THz 3.125/6.25/12.5GHz spacing";
           }
           enum "1542.22" {
             description "1542.22 nm/194.390625 THz 3.125GHz spacing";
           }
           enum "1542.19" {
             description "1542.19 nm/194.393750 THz 3.125/6.25GHz spacing";
           }
           enum "1542.17" {
             description "1542.17 nm/194.396875 THz 3.125GHz spacing";
           }
           enum "1542.14" {
             description "1542.14 nm/194.400000 THz 3.125/6.25/12.5/50/75/100GHz spacing";
           }
           enum "1542.12" {
             description "1542.12 nm/194.403125 THz 3.125GHz spacing";
           }
           enum "1542.09" {
             description "1542.09 nm/194.406250 THz 3.125/6.25GHz spacing";
           }
           enum "1542.07" {
             description "1542.07 nm/194.409375 THz 3.125GHz spacing";
           }
           enum "1542.04" {
             description "1542.04 nm/194.412500 THz 3.125/6.25/12.5GHz spacing";
           }
           enum "1542.02" {
             description "1542.02 nm/194.415625 THz 3.125GHz spacing";
           }
           enum "1541.99" {
             description "1541.99 nm/194.418750 THz 3.125/6.25GHz spacing";
           }
           enum "1541.97" {
             description "1541.97 nm/194.421875 THz 3.125GHz spacing";
           }
           enum "1541.94" {
             description "1541.94 nm/194.425000 THz 3.125/6.25/12.5GHz spacing";
           }
           enum "1541.92" {
             description "1541.92 nm/194.428125 THz 3.125GHz spacing";
           }
           enum "1541.89" {
             description "1541.89 nm/194.431250 THz 3.125/6.25GHz spacing";
           }
           enum "1541.87" {
             description "1541.87 nm/194.434375 THz 3.125GHz spacing";
           }
           enum "1541.84" {
             description "1541.84 nm/194.437500 THz 3.125/6.25/12.5GHz spacing";
           }
           enum "1541.82" {
             description "1541.82 nm/194.440625 THz 3.125GHz spacing";
           }
           enum "1541.80" {
             description "1541.80 nm/194.443750 THz 3.125/6.25GHz spacing";
           }
           enum "1541.77" {
             description "1541.77 nm/194.446875 THz 3.125GHz spacing";
           }
           enum "1541.75" {
             description "1541.75 nm/194.450000 THz 3.125/6.25/12.5/50GHz spacing";
           }
           enum "1541.72" {
             description "1541.72 nm/194.453125 THz 3.125GHz spacing";
           }
           enum "1541.70" {
             description "1541.70 nm/194.456250 THz 3.125/6.25GHz spacing";
           }
           enum "1541.67" {
             description "1541.67 nm/194.459375 THz 3.125GHz spacing";
           }
           enum "1541.65" {
             description "1541.65 nm/194.462500 THz 3.125/6.25/12.5GHz spacing";
           }
           enum "1541.62" {
             description "1541.62 nm/194.465625 THz 3.125GHz spacing";
           }
           enum "1541.60" {
             description "1541.60 nm/194.468750 THz 3.125/6.25GHz spacing";
           }
           enum "1541.57" {
             description "1541.57 nm/194.471875 THz 3.125GHz spacing";
           }
           enum "1541.55" {
             description "1541.55 nm/194.475000 THz 3.125/6.25/12.5/75GHz spacing";
           }
           enum "1541.52" {
             description "1541.52 nm/194.478125 THz 3.125GHz spacing";
           }
           enum "1541.50" {
             description "1541.50 nm/194.481250 THz 3.125/6.25GHz spacing";
           }
           enum "1541.47" {
             description "1541.47 nm/194.484375 THz 3.125GHz spacing";
           }
           enum "1541.45" {
             description "1541.45 nm/194.487500 THz 3.125/6.25/12.5GHz spacing";
           }
           enum "1541.42" {
             description "1541.42 nm/194.490625 THz 3.125GHz spacing";
           }
           enum "1541.40" {
             description "1541.40 nm/194.493750 THz 3.125/6.25GHz spacing";
           }
           enum "1541.37" {
             description "1541.37 nm/194.496875 THz 3.125GHz spacing";
           }
           enum "1541.35" {
             description "1541.35 nm/194.500000 THz 3.125/6.25/12.5/100GHz spacing";
           }
           enum "1541.32" {
             description "1541.32 nm/194.503125 THz 3.125GHz spacing";
           }
           enum "1541.30" {
             description "1541.30 nm/194.506250 THz 3.125/6.25GHz spacing";
           }
           enum "1541.28" {
             description "1541.28 nm/194.509375 THz 3.125GHz spacing";
           }
           enum "1541.25" {
             description "1541.25 nm/194.512500 THz 3.125/6.25/12.5GHz spacing";
           }
           enum "1541.23" {
             description "1541.23 nm/194.515625 THz 3.125GHz spacing";
           }
           enum "1541.20" {
             description "1541.20 nm/194.518750 THz 3.125/6.25GHz spacing";
           }
           enum "1541.18" {
             description "1541.18 nm/194.521875 THz 3.125GHz spacing";
           }
           enum "1541.15" {
             description "1541.15 nm/194.525000 THz 3.125/6.25/12.5GHz spacing";
           }
           enum "1541.13" {
             description "1541.13 nm/194.528125 THz 3.125GHz spacing";
           }
           enum "1541.10" {
             description "1541.10 nm/194.531250 THz 3.125/6.25GHz spacing";
           }
           enum "1541.08" {
             description "1541.08 nm/194.534375 THz 3.125GHz spacing";
           }
           enum "1541.05" {
             description "1541.05 nm/194.537500 THz 3.125/6.25/12.5GHz spacing";
           }
           enum "1541.03" {
             description "1541.03 nm/194.540625 THz 3.125GHz spacing";
           }
           enum "1541.00" {
             description "1541.00 nm/194.543750 THz 3.125/6.25GHz spacing";
           }
           enum "1540.98" {
             description "1540.98 nm/194.546875 THz 3.125GHz spacing";
           }
           enum "1540.95" {
             description "1540.95 nm/194.550000 THz 3.125/6.25/12.5/50/75GHz spacing";
           }
           enum "1540.93" {
             description "1540.93 nm/194.553125 THz 3.125GHz spacing";
           }
           enum "1540.90" {
             description "1540.90 nm/194.556250 THz 3.125/6.25GHz spacing";
           }
           enum "1540.88" {
             description "1540.88 nm/194.559375 THz 3.125GHz spacing";
           }
           enum "1540.85" {
             description "1540.85 nm/194.562500 THz 3.125/6.25/12.5GHz spacing";
           }
           enum "1540.83" {
             description "1540.83 nm/194.565625 THz 3.125GHz spacing";
           }
           enum "1540.80" {
             description "1540.80 nm/194.568750 THz 3.125/6.25GHz spacing";
           }
           enum "1540.78" {
             description "1540.78 nm/194.571875 THz 3.125GHz spacing";
           }
           enum "1540.76" {
             description "1540.76 nm/194.575000 THz 3.125/6.25/12.5GHz spacing";
           }
           enum "1540.73" {
             description "1540.73 nm/194.578125 THz 3.125GHz spacing";
           }
           enum "1540.71" {
             description "1540.71 nm/194.581250 THz 3.125/6.25GHz spacing";
           }
           enum "1540.68" {
             description "1540.68 nm/194.584375 THz 3.125GHz spacing";
           }
           enum "1540.66" {
             description "1540.66 nm/194.587500 THz 3.125/6.25/12.5GHz spacing";
           }
           enum "1540.63" {
             description "1540.63 nm/194.590625 THz 3.125GHz spacing";
           }
           enum "1540.61" {
             description "1540.61 nm/194.593750 THz 3.125/6.25GHz spacing";
           }
           enum "1540.58" {
             description "1540.58 nm/194.596875 THz 3.125GHz spacing";
           }
           enum "1540.56" {
             description "1540.56 nm/194.600000 THz 3.125/6.25/12.5/100GHz spacing";
           }
           enum "1540.53" {
             description "1540.53 nm/194.603125 THz 3.125GHz spacing";
           }
           enum "1540.51" {
             description "1540.51 nm/194.606250 THz 3.125/6.25GHz spacing";
           }
           enum "1540.48" {
             description "1540.48 nm/194.609375 THz 3.125GHz spacing";
           }
           enum "1540.46" {
             description "1540.46 nm/194.612500 THz 3.125/6.25/12.5GHz spacing";
           }
           enum "1540.43" {
             description "1540.43 nm/194.615625 THz 3.125GHz spacing";
           }
           enum "1540.41" {
             description "1540.41 nm/194.618750 THz 3.125/6.25GHz spacing";
           }
           enum "1540.38" {
             description "1540.38 nm/194.621875 THz 3.125GHz spacing";
           }
           enum "1540.36" {
             description "1540.36 nm/194.625000 THz 3.125/6.25/12.5/75GHz spacing";
           }
           enum "1540.33" {
             description "1540.33 nm/194.628125 THz 3.125GHz spacing";
           }
           enum "1540.31" {
             description "1540.31 nm/194.631250 THz 3.125/6.25GHz spacing";
           }
           enum "1540.29" {
             description "1540.29 nm/194.634375 THz 3.125GHz spacing";
           }
           enum "1540.26" {
             description "1540.26 nm/194.637500 THz 3.125/6.25/12.5GHz spacing";
           }
           enum "1540.24" {
             description "1540.24 nm/194.640625 THz 3.125GHz spacing";
           }
           enum "1540.21" {
             description "1540.21 nm/194.643750 THz 3.125/6.25GHz spacing";
           }
           enum "1540.19" {
             description "1540.19 nm/194.646875 THz 3.125GHz spacing";
           }
           enum "1540.16" {
             description "1540.16 nm/194.650000 THz 3.125/6.25/12.5/50GHz spacing";
           }
           enum "1540.14" {
             description "1540.14 nm/194.653125 THz 3.125GHz spacing";
           }
           enum "1540.11" {
             description "1540.11 nm/194.656250 THz 3.125/6.25GHz spacing";
           }
           enum "1540.09" {
             description "1540.09 nm/194.659375 THz 3.125GHz spacing";
           }
           enum "1540.06" {
             description "1540.06 nm/194.662500 THz 3.125/6.25/12.5GHz spacing";
           }
           enum "1540.04" {
             description "1540.04 nm/194.665625 THz 3.125GHz spacing";
           }
           enum "1540.01" {
             description "1540.01 nm/194.668750 THz 3.125/6.25GHz spacing";
           }
           enum "1539.99" {
             description "1539.99 nm/194.671875 THz 3.125GHz spacing";
           }
           enum "1539.96" {
             description "1539.96 nm/194.675000 THz 3.125/6.25/12.5/75GHz spacing";
           }
           enum "1539.94" {
             description "1539.94 nm/194.678125 THz 3.125GHz spacing";
           }
           enum "1539.91" {
             description "1539.91 nm/194.681250 THz 3.125/6.25GHz spacing";
           }
           enum "1539.89" {
             description "1539.89 nm/194.684375 THz 3.125GHz spacing";
           }
           enum "1539.86" {
             description "1539.86 nm/194.687500 THz 3.125/6.25/12.5GHz spacing";
           }
           enum "1539.84" {
             description "1539.84 nm/194.690625 THz 3.125GHz spacing";
           }
           enum "1539.82" {
             description "1539.82 nm/194.693750 THz 3.125/6.25GHz spacing";
           }
           enum "1539.79" {
             description "1539.79 nm/194.696875 THz 3.125GHz spacing";
           }
           enum "1539.77" {
             description "1539.77 nm/194.700000 THz 3.125/6.25/12.5/50/75/100GHz spacing";
           }
           enum "1539.74" {
             description "1539.74 nm/194.703125 THz 3.125GHz spacing";
           }
           enum "1539.72" {
             description "1539.72 nm/194.706250 THz 3.125/6.25GHz spacing";
           }
           enum "1539.69" {
             description "1539.69 nm/194.709375 THz 3.125GHz spacing";
           }
           enum "1539.67" {
             description "1539.67 nm/194.712500 THz 3.125/6.25/12.5GHz spacing";
           }
           enum "1539.64" {
             description "1539.64 nm/194.715625 THz 3.125GHz spacing";
           }
           enum "1539.62" {
             description "1539.62 nm/194.718750 THz 3.125/6.25GHz spacing";
           }
           enum "1539.59" {
             description "1539.59 nm/194.721875 THz 3.125GHz spacing";
           }
           enum "1539.57" {
             description "1539.57 nm/194.725000 THz 3.125/6.25/12.5GHz spacing";
           }
           enum "1539.54" {
             description "1539.54 nm/194.728125 THz 3.125GHz spacing";
           }
           enum "1539.52" {
             description "1539.52 nm/194.731250 THz 3.125/6.25GHz spacing";
           }
           enum "1539.49" {
             description "1539.49 nm/194.734375 THz 3.125GHz spacing";
           }
           enum "1539.47" {
             description "1539.47 nm/194.737500 THz 3.125/6.25/12.5GHz spacing";
           }
           enum "1539.44" {
             description "1539.44 nm/194.740625 THz 3.125GHz spacing";
           }
           enum "1539.42" {
             description "1539.42 nm/194.743750 THz 3.125/6.25GHz spacing";
           }
           enum "1539.40" {
             description "1539.40 nm/194.746875 THz 3.125GHz spacing";
           }
           enum "1539.37" {
             description "1539.37 nm/194.750000 THz 3.125/6.25/12.5/50GHz spacing";
           }
           enum "1539.35" {
             description "1539.35 nm/194.753125 THz 3.125GHz spacing";
           }
           enum "1539.32" {
             description "1539.32 nm/194.756250 THz 3.125/6.25GHz spacing";
           }
           enum "1539.30" {
             description "1539.30 nm/194.759375 THz 3.125GHz spacing";
           }
           enum "1539.27" {
             description "1539.27 nm/194.762500 THz 3.125/6.25/12.5GHz spacing";
           }
           enum "1539.25" {
             description "1539.25 nm/194.765625 THz 3.125GHz spacing";
           }
           enum "1539.22" {
             description "1539.22 nm/194.768750 THz 3.125/6.25GHz spacing";
           }
           enum "1539.20" {
             description "1539.20 nm/194.771875 THz 3.125GHz spacing";
           }
           enum "1539.17" {
             description "1539.17 nm/194.775000 THz 3.125/6.25/12.5/75GHz spacing";
           }
           enum "1539.15" {
             description "1539.15 nm/194.778125 THz 3.125GHz spacing";
           }
           enum "1539.12" {
             description "1539.12 nm/194.781250 THz 3.125/6.25GHz spacing";
           }
           enum "1539.10" {
             description "1539.10 nm/194.784375 THz 3.125GHz spacing";
           }
           enum "1539.07" {
             description "1539.07 nm/194.787500 THz 3.125/6.25/12.5GHz spacing";
           }
           enum "1539.05" {
             description "1539.05 nm/194.790625 THz 3.125GHz spacing";
           }
           enum "1539.03" {
             description "1539.03 nm/194.793750 THz 3.125/6.25GHz spacing";
           }
           enum "1539.00" {
             description "1539.00 nm/194.796875 THz 3.125GHz spacing";
           }
           enum "1538.98" {
             description "1538.98 nm/194.800000 THz 3.125/6.25/12.5/100GHz spacing";
           }
           enum "1538.95" {
             description "1538.95 nm/194.803125 THz 3.125GHz spacing";
           }
           enum "1538.93" {
             description "1538.93 nm/194.806250 THz 3.125/6.25GHz spacing";
           }
           enum "1538.90" {
             description "1538.90 nm/194.809375 THz 3.125GHz spacing";
           }
           enum "1538.88" {
             description "1538.88 nm/194.812500 THz 3.125/6.25/12.5GHz spacing";
           }
           enum "1538.85" {
             description "1538.85 nm/194.815625 THz 3.125GHz spacing";
           }
           enum "1538.83" {
             description "1538.83 nm/194.818750 THz 3.125/6.25GHz spacing";
           }
           enum "1538.80" {
             description "1538.80 nm/194.821875 THz 3.125GHz spacing";
           }
           enum "1538.78" {
             description "1538.78 nm/194.825000 THz 3.125/6.25/12.5GHz spacing";
           }
           enum "1538.75" {
             description "1538.75 nm/194.828125 THz 3.125GHz spacing";
           }
           enum "1538.73" {
             description "1538.73 nm/194.831250 THz 3.125/6.25GHz spacing";
           }
           enum "1538.70" {
             description "1538.70 nm/194.834375 THz 3.125GHz spacing";
           }
           enum "1538.68" {
             description "1538.68 nm/194.837500 THz 3.125/6.25/12.5GHz spacing";
           }
           enum "1538.65" {
             description "1538.65 nm/194.840625 THz 3.125GHz spacing";
           }
           enum "1538.63" {
             description "1538.63 nm/194.843750 THz 3.125/6.25GHz spacing";
           }
           enum "1538.61" {
             description "1538.61 nm/194.846875 THz 3.125GHz spacing";
           }
           enum "1538.58" {
             description "1538.58 nm/194.850000 THz 3.125/6.25/12.5/50/75GHz spacing";
           }
           enum "1538.56" {
             description "1538.56 nm/194.853125 THz 3.125GHz spacing";
           }
           enum "1538.53" {
             description "1538.53 nm/194.856250 THz 3.125/6.25GHz spacing";
           }
           enum "1538.51" {
             description "1538.51 nm/194.859375 THz 3.125GHz spacing";
           }
           enum "1538.48" {
             description "1538.48 nm/194.862500 THz 3.125/6.25/12.5GHz spacing";
           }
           enum "1538.46" {
             description "1538.46 nm/194.865625 THz 3.125GHz spacing";
           }
           enum "1538.43" {
             description "1538.43 nm/194.868750 THz 3.125/6.25GHz spacing";
           }
           enum "1538.41" {
             description "1538.41 nm/194.871875 THz 3.125GHz spacing";
           }
           enum "1538.38" {
             description "1538.38 nm/194.875000 THz 3.125/6.25/12.5GHz spacing";
           }
           enum "1538.36" {
             description "1538.36 nm/194.878125 THz 3.125GHz spacing";
           }
           enum "1538.33" {
             description "1538.33 nm/194.881250 THz 3.125/6.25GHz spacing";
           }
           enum "1538.31" {
             description "1538.31 nm/194.884375 THz 3.125GHz spacing";
           }
           enum "1538.28" {
             description "1538.28 nm/194.887500 THz 3.125/6.25/12.5GHz spacing";
           }
           enum "1538.26" {
             description "1538.26 nm/194.890625 THz 3.125GHz spacing";
           }
           enum "1538.24" {
             description "1538.24 nm/194.893750 THz 3.125/6.25GHz spacing";
           }
           enum "1538.21" {
             description "1538.21 nm/194.896875 THz 3.125GHz spacing";
           }
           enum "1538.19" {
             description "1538.19 nm/194.900000 THz 3.125/6.25/12.5/100GHz spacing";
           }
           enum "1538.16" {
             description "1538.16 nm/194.903125 THz 3.125GHz spacing";
           }
           enum "1538.14" {
             description "1538.14 nm/194.906250 THz 3.125/6.25GHz spacing";
           }
           enum "1538.11" {
             description "1538.11 nm/194.909375 THz 3.125GHz spacing";
           }
           enum "1538.09" {
             description "1538.09 nm/194.912500 THz 3.125/6.25/12.5GHz spacing";
           }
           enum "1538.06" {
             description "1538.06 nm/194.915625 THz 3.125GHz spacing";
           }
           enum "1538.04" {
             description "1538.04 nm/194.918750 THz 3.125/6.25GHz spacing";
           }
           enum "1538.01" {
             description "1538.01 nm/194.921875 THz 3.125GHz spacing";
           }
           enum "1537.99" {
             description "1537.99 nm/194.925000 THz 3.125/6.25/12.5/75GHz spacing";
           }
           enum "1537.96" {
             description "1537.96 nm/194.928125 THz 3.125GHz spacing";
           }
           enum "1537.94" {
             description "1537.94 nm/194.931250 THz 3.125/6.25GHz spacing";
           }
           enum "1537.91" {
             description "1537.91 nm/194.934375 THz 3.125GHz spacing";
           }
           enum "1537.89" {
             description "1537.89 nm/194.937500 THz 3.125/6.25/12.5GHz spacing";
           }
           enum "1537.87" {
             description "1537.87 nm/194.940625 THz 3.125GHz spacing";
           }
           enum "1537.84" {
             description "1537.84 nm/194.943750 THz 3.125/6.25GHz spacing";
           }
           enum "1537.82" {
             description "1537.82 nm/194.946875 THz 3.125GHz spacing";
           }
           enum "1537.79" {
             description "1537.79 nm/194.950000 THz 3.125/6.25/12.5/50GHz spacing";
           }
           enum "1537.77" {
             description "1537.77 nm/194.953125 THz 3.125GHz spacing";
           }
           enum "1537.74" {
             description "1537.74 nm/194.956250 THz 3.125/6.25GHz spacing";
           }
           enum "1537.72" {
             description "1537.72 nm/194.959375 THz 3.125GHz spacing";
           }
           enum "1537.69" {
             description "1537.69 nm/194.962500 THz 3.125/6.25/12.5GHz spacing";
           }
           enum "1537.67" {
             description "1537.67 nm/194.965625 THz 3.125GHz spacing";
           }
           enum "1537.64" {
             description "1537.64 nm/194.968750 THz 3.125/6.25GHz spacing";
           }
           enum "1537.62" {
             description "1537.62 nm/194.971875 THz 3.125GHz spacing";
           }
           enum "1537.59" {
             description "1537.59 nm/194.975000 THz 3.125/6.25/12.5GHz spacing";
           }
           enum "1537.57" {
             description "1537.57 nm/194.978125 THz 3.125GHz spacing";
           }
           enum "1537.55" {
             description "1537.55 nm/194.981250 THz 3.125/6.25GHz spacing";
           }
           enum "1537.52" {
             description "1537.52 nm/194.984375 THz 3.125GHz spacing";
           }
           enum "1537.50" {
             description "1537.50 nm/194.987500 THz 3.125/6.25/12.5GHz spacing";
           }
           enum "1537.47" {
             description "1537.47 nm/194.990625 THz 3.125GHz spacing";
           }
           enum "1537.45" {
             description "1537.45 nm/194.993750 THz 3.125/6.25GHz spacing";
           }
           enum "1537.42" {
             description "1537.42 nm/194.996875 THz 3.125GHz spacing";
           }
           enum "1537.40" {
             description "1537.40 nm/195.000000 THz 3.125/6.25/12.5/50/75/100GHz spacing";
           }
           enum "1537.37" {
             description "1537.37 nm/195.003125 THz 3.125GHz spacing";
           }
           enum "1537.35" {
             description "1537.35 nm/195.006250 THz 3.125/6.25GHz spacing";
           }
           enum "1537.32" {
             description "1537.32 nm/195.009375 THz 3.125GHz spacing";
           }
           enum "1537.30" {
             description "1537.30 nm/195.012500 THz 3.125/6.25/12.5GHz spacing";
           }
           enum "1537.27" {
             description "1537.27 nm/195.015625 THz 3.125GHz spacing";
           }
           enum "1537.25" {
             description "1537.25 nm/195.018750 THz 3.125/6.25GHz spacing";
           }
           enum "1537.22" {
             description "1537.22 nm/195.021875 THz 3.125GHz spacing";
           }
           enum "1537.20" {
             description "1537.20 nm/195.025000 THz 3.125/6.25/12.5GHz spacing";
           }
           enum "1537.18" {
             description "1537.18 nm/195.028125 THz 3.125GHz spacing";
           }
           enum "1537.15" {
             description "1537.15 nm/195.031250 THz 3.125/6.25GHz spacing";
           }
           enum "1537.13" {
             description "1537.13 nm/195.034375 THz 3.125GHz spacing";
           }
           enum "1537.10" {
             description "1537.10 nm/195.037500 THz 3.125/6.25/12.5GHz spacing";
           }
           enum "1537.08" {
             description "1537.08 nm/195.040625 THz 3.125GHz spacing";
           }
           enum "1537.05" {
             description "1537.05 nm/195.043750 THz 3.125/6.25GHz spacing";
           }
           enum "1537.03" {
             description "1537.03 nm/195.046875 THz 3.125GHz spacing";
           }
           enum "1537.00" {
             description "1537.00 nm/195.050000 THz 3.125/6.25/12.5/50GHz spacing";
           }
           enum "1536.98" {
             description "1536.98 nm/195.053125 THz 3.125GHz spacing";
           }
           enum "1536.95" {
             description "1536.95 nm/195.056250 THz 3.125/6.25GHz spacing";
           }
           enum "1536.93" {
             description "1536.93 nm/195.059375 THz 3.125GHz spacing";
           }
           enum "1536.90" {
             description "1536.90 nm/195.062500 THz 3.125/6.25/12.5GHz spacing";
           }
           enum "1536.88" {
             description "1536.88 nm/195.065625 THz 3.125GHz spacing";
           }
           enum "1536.86" {
             description "1536.86 nm/195.068750 THz 3.125/6.25GHz spacing";
           }
           enum "1536.83" {
             description "1536.83 nm/195.071875 THz 3.125GHz spacing";
           }
           enum "1536.81" {
             description "1536.81 nm/195.075000 THz 3.125/6.25/12.5/75GHz spacing";
           }
           enum "1536.78" {
             description "1536.78 nm/195.078125 THz 3.125GHz spacing";
           }
           enum "1536.76" {
             description "1536.76 nm/195.081250 THz 3.125/6.25GHz spacing";
           }
           enum "1536.73" {
             description "1536.73 nm/195.084375 THz 3.125GHz spacing";
           }
           enum "1536.71" {
             description "1536.71 nm/195.087500 THz 3.125/6.25/12.5GHz spacing";
           }
           enum "1536.68" {
             description "1536.68 nm/195.090625 THz 3.125GHz spacing";
           }
           enum "1536.66" {
             description "1536.66 nm/195.093750 THz 3.125/6.25GHz spacing";
           }
           enum "1536.63" {
             description "1536.63 nm/195.096875 THz 3.125GHz spacing";
           }
           enum "1536.61" {
             description "1536.61 nm/195.100000 THz 3.125/6.25/12.5/100GHz spacing";
           }
           enum "1536.58" {
             description "1536.58 nm/195.103125 THz 3.125GHz spacing";
           }
           enum "1536.56" {
             description "1536.56 nm/195.106250 THz 3.125/6.25GHz spacing";
           }
           enum "1536.54" {
             description "1536.54 nm/195.109375 THz 3.125GHz spacing";
           }
           enum "1536.51" {
             description "1536.51 nm/195.112500 THz 3.125/6.25/12.5GHz spacing";
           }
           enum "1536.49" {
             description "1536.49 nm/195.115625 THz 3.125GHz spacing";
           }
           enum "1536.46" {
             description "1536.46 nm/195.118750 THz 3.125/6.25GHz spacing";
           }
           enum "1536.44" {
             description "1536.44 nm/195.121875 THz 3.125GHz spacing";
           }
           enum "1536.41" {
             description "1536.41 nm/195.125000 THz 3.125/6.25/12.5GHz spacing";
           }
           enum "1536.39" {
             description "1536.39 nm/195.128125 THz 3.125GHz spacing";
           }
           enum "1536.36" {
             description "1536.36 nm/195.131250 THz 3.125/6.25GHz spacing";
           }
           enum "1536.34" {
             description "1536.34 nm/195.134375 THz 3.125GHz spacing";
           }
           enum "1536.31" {
             description "1536.31 nm/195.137500 THz 3.125/6.25/12.5GHz spacing";
           }
           enum "1536.29" {
             description "1536.29 nm/195.140625 THz 3.125GHz spacing";
           }
           enum "1536.26" {
             description "1536.26 nm/195.143750 THz 3.125/6.25GHz spacing";
           }
           enum "1536.24" {
             description "1536.24 nm/195.146875 THz 3.125GHz spacing";
           }
           enum "1536.22" {
             description "1536.22 nm/195.150000 THz 3.125/6.25/12.5/50/75GHz spacing";
           }
           enum "1536.19" {
             description "1536.19 nm/195.153125 THz 3.125GHz spacing";
           }
           enum "1536.17" {
             description "1536.17 nm/195.156250 THz 3.125/6.25GHz spacing";
           }
           enum "1536.14" {
             description "1536.14 nm/195.159375 THz 3.125GHz spacing";
           }
           enum "1536.12" {
             description "1536.12 nm/195.162500 THz 3.125/6.25/12.5GHz spacing";
           }
           enum "1536.09" {
             description "1536.09 nm/195.165625 THz 3.125GHz spacing";
           }
           enum "1536.07" {
             description "1536.07 nm/195.168750 THz 3.125/6.25GHz spacing";
           }
           enum "1536.04" {
             description "1536.04 nm/195.171875 THz 3.125GHz spacing";
           }
           enum "1536.02" {
             description "1536.02 nm/195.175000 THz 3.125/6.25/12.5GHz spacing";
           }
           enum "1535.99" {
             description "1535.99 nm/195.178125 THz 3.125GHz spacing";
           }
           enum "1535.97" {
             description "1535.97 nm/195.181250 THz 3.125/6.25GHz spacing";
           }
           enum "1535.94" {
             description "1535.94 nm/195.184375 THz 3.125GHz spacing";
           }
           enum "1535.92" {
             description "1535.92 nm/195.187500 THz 3.125/6.25/12.5GHz spacing";
           }
           enum "1535.90" {
             description "1535.90 nm/195.190625 THz 3.125GHz spacing";
           }
           enum "1535.87" {
             description "1535.87 nm/195.193750 THz 3.125/6.25GHz spacing";
           }
           enum "1535.85" {
             description "1535.85 nm/195.196875 THz 3.125GHz spacing";
           }
           enum "1535.82" {
             description "1535.82 nm/195.200000 THz 3.125/6.25/12.5/100GHz spacing";
           }
           enum "1535.80" {
             description "1535.80 nm/195.203125 THz 3.125GHz spacing";
           }
           enum "1535.77" {
             description "1535.77 nm/195.206250 THz 3.125/6.25GHz spacing";
           }
           enum "1535.75" {
             description "1535.75 nm/195.209375 THz 3.125GHz spacing";
           }
           enum "1535.72" {
             description "1535.72 nm/195.212500 THz 3.125/6.25/12.5GHz spacing";
           }
           enum "1535.70" {
             description "1535.70 nm/195.215625 THz 3.125GHz spacing";
           }
           enum "1535.67" {
             description "1535.67 nm/195.218750 THz 3.125/6.25GHz spacing";
           }
           enum "1535.65" {
             description "1535.65 nm/195.221875 THz 3.125GHz spacing";
           }
           enum "1535.63" {
             description "1535.63 nm/195.225000 THz 3.125/6.25/12.5/75GHz spacing";
           }
           enum "1535.60" {
             description "1535.60 nm/195.228125 THz 3.125GHz spacing";
           }
           enum "1535.58" {
             description "1535.58 nm/195.231250 THz 3.125/6.25GHz spacing";
           }
           enum "1535.55" {
             description "1535.55 nm/195.234375 THz 3.125GHz spacing";
           }
           enum "1535.53" {
             description "1535.53 nm/195.237500 THz 3.125/6.25/12.5GHz spacing";
           }
           enum "1535.50" {
             description "1535.50 nm/195.240625 THz 3.125GHz spacing";
           }
           enum "1535.48" {
             description "1535.48 nm/195.243750 THz 3.125/6.25GHz spacing";
           }
           enum "1535.45" {
             description "1535.45 nm/195.246875 THz 3.125GHz spacing";
           }
           enum "1535.43" {
             description "1535.43 nm/195.250000 THz 3.125/6.25/12.5/50GHz spacing";
           }
           enum "1535.40" {
             description "1535.40 nm/195.253125 THz 3.125GHz spacing";
           }
           enum "1535.38" {
             description "1535.38 nm/195.256250 THz 3.125/6.25GHz spacing";
           }
           enum "1535.36" {
             description "1535.36 nm/195.259375 THz 3.125GHz spacing";
           }
           enum "1535.33" {
             description "1535.33 nm/195.262500 THz 3.125/6.25/12.5GHz spacing";
           }
           enum "1535.31" {
             description "1535.31 nm/195.265625 THz 3.125GHz spacing";
           }
           enum "1535.28" {
             description "1535.28 nm/195.268750 THz 3.125/6.25GHz spacing";
           }
           enum "1535.26" {
             description "1535.26 nm/195.271875 THz 3.125GHz spacing";
           }
           enum "1535.23" {
             description "1535.23 nm/195.275000 THz 3.125/6.25/12.5GHz spacing";
           }
           enum "1535.21" {
             description "1535.21 nm/195.278125 THz 3.125GHz spacing";
           }
           enum "1535.18" {
             description "1535.18 nm/195.281250 THz 3.125/6.25GHz spacing";
           }
           enum "1535.16" {
             description "1535.16 nm/195.284375 THz 3.125GHz spacing";
           }
           enum "1535.13" {
             description "1535.13 nm/195.287500 THz 3.125/6.25/12.5GHz spacing";
           }
           enum "1535.11" {
             description "1535.11 nm/195.290625 THz 3.125GHz spacing";
           }
           enum "1535.08" {
             description "1535.08 nm/195.293750 THz 3.125/6.25GHz spacing";
           }
           enum "1535.06" {
             description "1535.06 nm/195.296875 THz 3.125GHz spacing";
           }
           enum "1535.04" {
             description "1535.04 nm/195.300000 THz 3.125/6.25/12.5/50/75/100GHz spacing";
           }
           enum "1535.01" {
             description "1535.01 nm/195.303125 THz 3.125GHz spacing";
           }
           enum "1534.99" {
             description "1534.99 nm/195.306250 THz 3.125/6.25GHz spacing";
           }
           enum "1534.96" {
             description "1534.96 nm/195.309375 THz 3.125GHz spacing";
           }
           enum "1534.94" {
             description "1534.94 nm/195.312500 THz 3.125/6.25/12.5GHz spacing";
           }
           enum "1534.91" {
             description "1534.91 nm/195.315625 THz 3.125GHz spacing";
           }
           enum "1534.89" {
             description "1534.89 nm/195.318750 THz 3.125/6.25GHz spacing";
           }
           enum "1534.86" {
             description "1534.86 nm/195.321875 THz 3.125GHz spacing";
           }
           enum "1534.84" {
             description "1534.84 nm/195.325000 THz 3.125/6.25/12.5GHz spacing";
           }
           enum "1534.81" {
             description "1534.81 nm/195.328125 THz 3.125GHz spacing";
           }
           enum "1534.79" {
             description "1534.79 nm/195.331250 THz 3.125/6.25GHz spacing";
           }
           enum "1534.77" {
             description "1534.77 nm/195.334375 THz 3.125GHz spacing";
           }
           enum "1534.74" {
             description "1534.74 nm/195.337500 THz 3.125/6.25/12.5GHz spacing";
           }
           enum "1534.72" {
             description "1534.72 nm/195.340625 THz 3.125GHz spacing";
           }
           enum "1534.69" {
             description "1534.69 nm/195.343750 THz 3.125/6.25GHz spacing";
           }
           enum "1534.67" {
             description "1534.67 nm/195.346875 THz 3.125GHz spacing";
           }
           enum "1534.64" {
             description "1534.64 nm/195.350000 THz 3.125/6.25/12.5/50GHz spacing";
           }
           enum "1534.62" {
             description "1534.62 nm/195.353125 THz 3.125GHz spacing";
           }
           enum "1534.59" {
             description "1534.59 nm/195.356250 THz 3.125/6.25GHz spacing";
           }
           enum "1534.57" {
             description "1534.57 nm/195.359375 THz 3.125GHz spacing";
           }
           enum "1534.54" {
             description "1534.54 nm/195.362500 THz 3.125/6.25/12.5GHz spacing";
           }
           enum "1534.52" {
             description "1534.52 nm/195.365625 THz 3.125GHz spacing";
           }
           enum "1534.50" {
             description "1534.50 nm/195.368750 THz 3.125/6.25GHz spacing";
           }
           enum "1534.47" {
             description "1534.47 nm/195.371875 THz 3.125GHz spacing";
           }
           enum "1534.45" {
             description "1534.45 nm/195.375000 THz 3.125/6.25/12.5/75GHz spacing";
           }
           enum "1534.42" {
             description "1534.42 nm/195.378125 THz 3.125GHz spacing";
           }
           enum "1534.40" {
             description "1534.40 nm/195.381250 THz 3.125/6.25GHz spacing";
           }
           enum "1534.37" {
             description "1534.37 nm/195.384375 THz 3.125GHz spacing";
           }
           enum "1534.35" {
             description "1534.35 nm/195.387500 THz 3.125/6.25/12.5GHz spacing";
           }
           enum "1534.32" {
             description "1534.32 nm/195.390625 THz 3.125GHz spacing";
           }
           enum "1534.30" {
             description "1534.30 nm/195.393750 THz 3.125/6.25GHz spacing";
           }
           enum "1534.27" {
             description "1534.27 nm/195.396875 THz 3.125GHz spacing";
           }
           enum "1534.25" {
             description "1534.25 nm/195.400000 THz 3.125/6.25/12.5/100GHz spacing";
           }
           enum "1534.23" {
             description "1534.23 nm/195.403125 THz 3.125GHz spacing";
           }
           enum "1534.20" {
             description "1534.20 nm/195.406250 THz 3.125/6.25GHz spacing";
           }
           enum "1534.18" {
             description "1534.18 nm/195.409375 THz 3.125GHz spacing";
           }
           enum "1534.15" {
             description "1534.15 nm/195.412500 THz 3.125/6.25/12.5GHz spacing";
           }
           enum "1534.13" {
             description "1534.13 nm/195.415625 THz 3.125GHz spacing";
           }
           enum "1534.10" {
             description "1534.10 nm/195.418750 THz 3.125/6.25GHz spacing";
           }
           enum "1534.08" {
             description "1534.08 nm/195.421875 THz 3.125GHz spacing";
           }
           enum "1534.05" {
             description "1534.05 nm/195.425000 THz 3.125/6.25/12.5GHz spacing";
           }
           enum "1534.03" {
             description "1534.03 nm/195.428125 THz 3.125GHz spacing";
           }
           enum "1534.00" {
             description "1534.00 nm/195.431250 THz 3.125/6.25GHz spacing";
           }
           enum "1533.98" {
             description "1533.98 nm/195.434375 THz 3.125GHz spacing";
           }
           enum "1533.96" {
             description "1533.96 nm/195.437500 THz 3.125/6.25/12.5GHz spacing";
           }
           enum "1533.93" {
             description "1533.93 nm/195.440625 THz 3.125GHz spacing";
           }
           enum "1533.91" {
             description "1533.91 nm/195.443750 THz 3.125/6.25GHz spacing";
           }
           enum "1533.88" {
             description "1533.88 nm/195.446875 THz 3.125GHz spacing";
           }
           enum "1533.86" {
             description "1533.86 nm/195.450000 THz 3.125/6.25/12.5/50/75GHz spacing";
           }
           enum "1533.83" {
             description "1533.83 nm/195.453125 THz 3.125GHz spacing";
           }
           enum "1533.81" {
             description "1533.81 nm/195.456250 THz 3.125/6.25GHz spacing";
           }
           enum "1533.78" {
             description "1533.78 nm/195.459375 THz 3.125GHz spacing";
           }
           enum "1533.76" {
             description "1533.76 nm/195.462500 THz 3.125/6.25/12.5GHz spacing";
           }
           enum "1533.73" {
             description "1533.73 nm/195.465625 THz 3.125GHz spacing";
           }
           enum "1533.71" {
             description "1533.71 nm/195.468750 THz 3.125/6.25GHz spacing";
           }
           enum "1533.69" {
             description "1533.69 nm/195.471875 THz 3.125GHz spacing";
           }
           enum "1533.66" {
             description "1533.66 nm/195.475000 THz 3.125/6.25/12.5GHz spacing";
           }
           enum "1533.64" {
             description "1533.64 nm/195.478125 THz 3.125GHz spacing";
           }
           enum "1533.61" {
             description "1533.61 nm/195.481250 THz 3.125/6.25GHz spacing";
           }
           enum "1533.59" {
             description "1533.59 nm/195.484375 THz 3.125GHz spacing";
           }
           enum "1533.56" {
             description "1533.56 nm/195.487500 THz 3.125/6.25/12.5GHz spacing";
           }
           enum "1533.54" {
             description "1533.54 nm/195.490625 THz 3.125GHz spacing";
           }
           enum "1533.51" {
             description "1533.51 nm/195.493750 THz 3.125/6.25GHz spacing";
           }
           enum "1533.49" {
             description "1533.49 nm/195.496875 THz 3.125GHz spacing";
           }
           enum "1533.47" {
             description "1533.47 nm/195.500000 THz 3.125/6.25/12.5/100GHz spacing";
           }
           enum "1533.44" {
             description "1533.44 nm/195.503125 THz 3.125GHz spacing";
           }
           enum "1533.42" {
             description "1533.42 nm/195.506250 THz 3.125/6.25GHz spacing";
           }
           enum "1533.39" {
             description "1533.39 nm/195.509375 THz 3.125GHz spacing";
           }
           enum "1533.37" {
             description "1533.37 nm/195.512500 THz 3.125/6.25/12.5GHz spacing";
           }
           enum "1533.34" {
             description "1533.34 nm/195.515625 THz 3.125GHz spacing";
           }
           enum "1533.32" {
             description "1533.32 nm/195.518750 THz 3.125/6.25GHz spacing";
           }
           enum "1533.29" {
             description "1533.29 nm/195.521875 THz 3.125GHz spacing";
           }
           enum "1533.27" {
             description "1533.27 nm/195.525000 THz 3.125/6.25/12.5/75GHz spacing";
           }
           enum "1533.24" {
             description "1533.24 nm/195.528125 THz 3.125GHz spacing";
           }
           enum "1533.22" {
             description "1533.22 nm/195.531250 THz 3.125/6.25GHz spacing";
           }
           enum "1533.20" {
             description "1533.20 nm/195.534375 THz 3.125GHz spacing";
           }
           enum "1533.17" {
             description "1533.17 nm/195.537500 THz 3.125/6.25/12.5GHz spacing";
           }
           enum "1533.15" {
             description "1533.15 nm/195.540625 THz 3.125GHz spacing";
           }
           enum "1533.12" {
             description "1533.12 nm/195.543750 THz 3.125/6.25GHz spacing";
           }
           enum "1533.10" {
             description "1533.10 nm/195.546875 THz 3.125GHz spacing";
           }
           enum "1533.07" {
             description "1533.07 nm/195.550000 THz 3.125/6.25/12.5/50GHz spacing";
           }
           enum "1533.05" {
             description "1533.05 nm/195.553125 THz 3.125GHz spacing";
           }
           enum "1533.02" {
             description "1533.02 nm/195.556250 THz 3.125/6.25GHz spacing";
           }
           enum "1533.00" {
             description "1533.00 nm/195.559375 THz 3.125GHz spacing";
           }
           enum "1532.98" {
             description "1532.98 nm/195.562500 THz 3.125/6.25/12.5GHz spacing";
           }
           enum "1532.95" {
             description "1532.95 nm/195.565625 THz 3.125GHz spacing";
           }
           enum "1532.93" {
             description "1532.93 nm/195.568750 THz 3.125/6.25GHz spacing";
           }
           enum "1532.90" {
             description "1532.90 nm/195.571875 THz 3.125GHz spacing";
           }
           enum "1532.88" {
             description "1532.88 nm/195.575000 THz 3.125/6.25/12.5GHz spacing";
           }
           enum "1532.85" {
             description "1532.85 nm/195.578125 THz 3.125GHz spacing";
           }
           enum "1532.83" {
             description "1532.83 nm/195.581250 THz 3.125/6.25GHz spacing";
           }
           enum "1532.80" {
             description "1532.80 nm/195.584375 THz 3.125GHz spacing";
           }
           enum "1532.78" {
             description "1532.78 nm/195.587500 THz 3.125/6.25/12.5GHz spacing";
           }
           enum "1532.75" {
             description "1532.75 nm/195.590625 THz 3.125GHz spacing";
           }
           enum "1532.73" {
             description "1532.73 nm/195.593750 THz 3.125/6.25GHz spacing";
           }
           enum "1532.71" {
             description "1532.71 nm/195.596875 THz 3.125GHz spacing";
           }
           enum "1532.68" {
             description "1532.68 nm/195.600000 THz 3.125/6.25/12.5/50/75/100GHz spacing";
           }
           enum "1532.66" {
             description "1532.66 nm/195.603125 THz 3.125GHz spacing";
           }
           enum "1532.63" {
             description "1532.63 nm/195.606250 THz 3.125/6.25GHz spacing";
           }
           enum "1532.61" {
             description "1532.61 nm/195.609375 THz 3.125GHz spacing";
           }
           enum "1532.58" {
             description "1532.58 nm/195.612500 THz 3.125/6.25/12.5GHz spacing";
           }
           enum "1532.56" {
             description "1532.56 nm/195.615625 THz 3.125GHz spacing";
           }
           enum "1532.53" {
             description "1532.53 nm/195.618750 THz 3.125/6.25GHz spacing";
           }
           enum "1532.51" {
             description "1532.51 nm/195.621875 THz 3.125GHz spacing";
           }
           enum "1532.49" {
             description "1532.49 nm/195.625000 THz 3.125/6.25/12.5GHz spacing";
           }
           enum "1532.46" {
             description "1532.46 nm/195.628125 THz 3.125GHz spacing";
           }
           enum "1532.44" {
             description "1532.44 nm/195.631250 THz 3.125/6.25GHz spacing";
           }
           enum "1532.41" {
             description "1532.41 nm/195.634375 THz 3.125GHz spacing";
           }
           enum "1532.39" {
             description "1532.39 nm/195.637500 THz 3.125/6.25/12.5GHz spacing";
           }
           enum "1532.36" {
             description "1532.36 nm/195.640625 THz 3.125GHz spacing";
           }
           enum "1532.34" {
             description "1532.34 nm/195.643750 THz 3.125/6.25GHz spacing";
           }
           enum "1532.31" {
             description "1532.31 nm/195.646875 THz 3.125GHz spacing";
           }
           enum "1532.29" {
             description "1532.29 nm/195.650000 THz 3.125/6.25/12.5/50GHz spacing";
           }
           enum "1532.27" {
             description "1532.27 nm/195.653125 THz 3.125GHz spacing";
           }
           enum "1532.24" {
             description "1532.24 nm/195.656250 THz 3.125/6.25GHz spacing";
           }
           enum "1532.22" {
             description "1532.22 nm/195.659375 THz 3.125GHz spacing";
           }
           enum "1532.19" {
             description "1532.19 nm/195.662500 THz 3.125/6.25/12.5GHz spacing";
           }
           enum "1532.17" {
             description "1532.17 nm/195.665625 THz 3.125GHz spacing";
           }
           enum "1532.14" {
             description "1532.14 nm/195.668750 THz 3.125/6.25GHz spacing";
           }
           enum "1532.12" {
             description "1532.12 nm/195.671875 THz 3.125GHz spacing";
           }
           enum "1532.09" {
             description "1532.09 nm/195.675000 THz 3.125/6.25/12.5/75GHz spacing";
           }
           enum "1532.07" {
             description "1532.07 nm/195.678125 THz 3.125GHz spacing";
           }
           enum "1532.04" {
             description "1532.04 nm/195.681250 THz 3.125/6.25GHz spacing";
           }
           enum "1532.02" {
             description "1532.02 nm/195.684375 THz 3.125GHz spacing";
           }
           enum "1532.00" {
             description "1532.00 nm/195.687500 THz 3.125/6.25/12.5GHz spacing";
           }
           enum "1531.97" {
             description "1531.97 nm/195.690625 THz 3.125GHz spacing";
           }
           enum "1531.95" {
             description "1531.95 nm/195.693750 THz 3.125/6.25GHz spacing";
           }
           enum "1531.92" {
             description "1531.92 nm/195.696875 THz 3.125GHz spacing";
           }
           enum "1531.90" {
             description "1531.90 nm/195.700000 THz 3.125/6.25/12.5/100GHz spacing";
           }
           enum "1531.87" {
             description "1531.87 nm/195.703125 THz 3.125GHz spacing";
           }
           enum "1531.85" {
             description "1531.85 nm/195.706250 THz 3.125/6.25GHz spacing";
           }
           enum "1531.82" {
             description "1531.82 nm/195.709375 THz 3.125GHz spacing";
           }
           enum "1531.80" {
             description "1531.80 nm/195.712500 THz 3.125/6.25/12.5GHz spacing";
           }
           enum "1531.78" {
             description "1531.78 nm/195.715625 THz 3.125GHz spacing";
           }
           enum "1531.75" {
             description "1531.75 nm/195.718750 THz 3.125/6.25GHz spacing";
           }
           enum "1531.73" {
             description "1531.73 nm/195.721875 THz 3.125GHz spacing";
           }
           enum "1531.70" {
             description "1531.70 nm/195.725000 THz 3.125/6.25/12.5GHz spacing";
           }
           enum "1531.68" {
             description "1531.68 nm/195.728125 THz 3.125GHz spacing";
           }
           enum "1531.65" {
             description "1531.65 nm/195.731250 THz 3.125/6.25GHz spacing";
           }
           enum "1531.63" {
             description "1531.63 nm/195.734375 THz 3.125GHz spacing";
           }
           enum "1531.60" {
             description "1531.60 nm/195.737500 THz 3.125/6.25/12.5GHz spacing";
           }
           enum "1531.58" {
             description "1531.58 nm/195.740625 THz 3.125GHz spacing";
           }
           enum "1531.56" {
             description "1531.56 nm/195.743750 THz 3.125/6.25GHz spacing";
           }
           enum "1531.53" {
             description "1531.53 nm/195.746875 THz 3.125GHz spacing";
           }
           enum "1531.51" {
             description "1531.51 nm/195.750000 THz 3.125/6.25/12.5/50/75GHz spacing";
           }
           enum "1531.48" {
             description "1531.48 nm/195.753125 THz 3.125GHz spacing";
           }
           enum "1531.46" {
             description "1531.46 nm/195.756250 THz 3.125/6.25GHz spacing";
           }
           enum "1531.43" {
             description "1531.43 nm/195.759375 THz 3.125GHz spacing";
           }
           enum "1531.41" {
             description "1531.41 nm/195.762500 THz 3.125/6.25/12.5GHz spacing";
           }
           enum "1531.38" {
             description "1531.38 nm/195.765625 THz 3.125GHz spacing";
           }
           enum "1531.36" {
             description "1531.36 nm/195.768750 THz 3.125/6.25GHz spacing";
           }
           enum "1531.34" {
             description "1531.34 nm/195.771875 THz 3.125GHz spacing";
           }
           enum "1531.31" {
             description "1531.31 nm/195.775000 THz 3.125/6.25/12.5GHz spacing";
           }
           enum "1531.29" {
             description "1531.29 nm/195.778125 THz 3.125GHz spacing";
           }
           enum "1531.26" {
             description "1531.26 nm/195.781250 THz 3.125/6.25GHz spacing";
           }
           enum "1531.24" {
             description "1531.24 nm/195.784375 THz 3.125GHz spacing";
           }
           enum "1531.21" {
             description "1531.21 nm/195.787500 THz 3.125/6.25/12.5GHz spacing";
           }
           enum "1531.19" {
             description "1531.19 nm/195.790625 THz 3.125GHz spacing";
           }
           enum "1531.16" {
             description "1531.16 nm/195.793750 THz 3.125/6.25GHz spacing";
           }
           enum "1531.14" {
             description "1531.14 nm/195.796875 THz 3.125GHz spacing";
           }
           enum "1531.12" {
             description "1531.12 nm/195.800000 THz 3.125/6.25/12.5/100GHz spacing";
           }
           enum "1531.09" {
             description "1531.09 nm/195.803125 THz 3.125GHz spacing";
           }
           enum "1531.07" {
             description "1531.07 nm/195.806250 THz 3.125/6.25GHz spacing";
           }
           enum "1531.04" {
             description "1531.04 nm/195.809375 THz 3.125GHz spacing";
           }
           enum "1531.02" {
             description "1531.02 nm/195.812500 THz 3.125/6.25/12.5GHz spacing";
           }
           enum "1530.99" {
             description "1530.99 nm/195.815625 THz 3.125GHz spacing";
           }
           enum "1530.97" {
             description "1530.97 nm/195.818750 THz 3.125/6.25GHz spacing";
           }
           enum "1530.94" {
             description "1530.94 nm/195.821875 THz 3.125GHz spacing";
           }
           enum "1530.92" {
             description "1530.92 nm/195.825000 THz 3.125/6.25/12.5/75GHz spacing";
           }
           enum "1530.90" {
             description "1530.90 nm/195.828125 THz 3.125GHz spacing";
           }
           enum "1530.87" {
             description "1530.87 nm/195.831250 THz 3.125/6.25GHz spacing";
           }
           enum "1530.85" {
             description "1530.85 nm/195.834375 THz 3.125GHz spacing";
           }
           enum "1530.82" {
             description "1530.82 nm/195.837500 THz 3.125/6.25/12.5GHz spacing";
           }
           enum "1530.80" {
             description "1530.80 nm/195.840625 THz 3.125GHz spacing";
           }
           enum "1530.77" {
             description "1530.77 nm/195.843750 THz 3.125/6.25GHz spacing";
           }
           enum "1530.75" {
             description "1530.75 nm/195.846875 THz 3.125GHz spacing";
           }
           enum "1530.72" {
             description "1530.72 nm/195.850000 THz 3.125/6.25/12.5/50GHz spacing";
           }
           enum "1530.70" {
             description "1530.70 nm/195.853125 THz 3.125GHz spacing";
           }
           enum "1530.68" {
             description "1530.68 nm/195.856250 THz 3.125/6.25GHz spacing";
           }
           enum "1530.65" {
             description "1530.65 nm/195.859375 THz 3.125GHz spacing";
           }
           enum "1530.63" {
             description "1530.63 nm/195.862500 THz 3.125/6.25/12.5GHz spacing";
           }
           enum "1530.60" {
             description "1530.60 nm/195.865625 THz 3.125GHz spacing";
           }
           enum "1530.58" {
             description "1530.58 nm/195.868750 THz 3.125/6.25GHz spacing";
           }
           enum "1530.55" {
             description "1530.55 nm/195.871875 THz 3.125GHz spacing";
           }
           enum "1530.53" {
             description "1530.53 nm/195.875000 THz 3.125/6.25/12.5GHz spacing";
           }
           enum "1530.51" {
             description "1530.51 nm/195.878125 THz 3.125GHz spacing";
           }
           enum "1530.48" {
             description "1530.48 nm/195.881250 THz 3.125/6.25GHz spacing";
           }
           enum "1530.46" {
             description "1530.46 nm/195.884375 THz 3.125GHz spacing";
           }
           enum "1530.43" {
             description "1530.43 nm/195.887500 THz 3.125/6.25/12.5GHz spacing";
           }
           enum "1530.41" {
             description "1530.41 nm/195.890625 THz 3.125GHz spacing";
           }
           enum "1530.38" {
             description "1530.38 nm/195.893750 THz 3.125/6.25GHz spacing";
           }
           enum "1530.36" {
             description "1530.36 nm/195.896875 THz 3.125GHz spacing";
           }
           enum "1530.33" {
             description "1530.33 nm/195.900000 THz 3.125/6.25/12.5/50/75/100GHz spacing";
           }
           enum "1530.31" {
             description "1530.31 nm/195.903125 THz 3.125GHz spacing";
           }
           enum "1530.29" {
             description "1530.29 nm/195.906250 THz 3.125/6.25GHz spacing";
           }
           enum "1530.26" {
             description "1530.26 nm/195.909375 THz 3.125GHz spacing";
           }
           enum "1530.24" {
             description "1530.24 nm/195.912500 THz 3.125/6.25/12.5GHz spacing";
           }
           enum "1530.21" {
             description "1530.21 nm/195.915625 THz 3.125GHz spacing";
           }
           enum "1530.19" {
             description "1530.19 nm/195.918750 THz 3.125/6.25GHz spacing";
           }
           enum "1530.16" {
             description "1530.16 nm/195.921875 THz 3.125GHz spacing";
           }
           enum "1530.14" {
             description "1530.14 nm/195.925000 THz 3.125/6.25/12.5GHz spacing";
           }
           enum "1530.11" {
             description "1530.11 nm/195.928125 THz 3.125GHz spacing";
           }
           enum "1530.09" {
             description "1530.09 nm/195.931250 THz 3.125/6.25GHz spacing";
           }
           enum "1530.07" {
             description "1530.07 nm/195.934375 THz 3.125GHz spacing";
           }
           enum "1530.04" {
             description "1530.04 nm/195.937500 THz 3.125/6.25/12.5GHz spacing";
           }
           enum "1530.02" {
             description "1530.02 nm/195.940625 THz 3.125GHz spacing";
           }
           enum "1529.99" {
             description "1529.99 nm/195.943750 THz 3.125/6.25GHz spacing";
           }
           enum "1529.97" {
             description "1529.97 nm/195.946875 THz 3.125GHz spacing";
           }
           enum "1529.94" {
             description "1529.94 nm/195.950000 THz 3.125/6.25/12.5/50GHz spacing";
           }
           enum "1529.92" {
             description "1529.92 nm/195.953125 THz 3.125GHz spacing";
           }
           enum "1529.89" {
             description "1529.89 nm/195.956250 THz 3.125/6.25GHz spacing";
           }
           enum "1529.87" {
             description "1529.87 nm/195.959375 THz 3.125GHz spacing";
           }
           enum "1529.85" {
             description "1529.85 nm/195.962500 THz 3.125/6.25/12.5GHz spacing";
           }
           enum "1529.82" {
             description "1529.82 nm/195.965625 THz 3.125GHz spacing";
           }
           enum "1529.80" {
             description "1529.80 nm/195.968750 THz 3.125/6.25GHz spacing";
           }
           enum "1529.77" {
             description "1529.77 nm/195.971875 THz 3.125GHz spacing";
           }
           enum "1529.75" {
             description "1529.75 nm/195.975000 THz 3.125/6.25/12.5/75GHz spacing";
           }
           enum "1529.72" {
             description "1529.72 nm/195.978125 THz 3.125GHz spacing";
           }
           enum "1529.70" {
             description "1529.70 nm/195.981250 THz 3.125/6.25GHz spacing";
           }
           enum "1529.68" {
             description "1529.68 nm/195.984375 THz 3.125GHz spacing";
           }
           enum "1529.65" {
             description "1529.65 nm/195.987500 THz 3.125/6.25/12.5GHz spacing";
           }
           enum "1529.63" {
             description "1529.63 nm/195.990625 THz 3.125GHz spacing";
           }
           enum "1529.60" {
             description "1529.60 nm/195.993750 THz 3.125/6.25GHz spacing";
           }
           enum "1529.58" {
             description "1529.58 nm/195.996875 THz 3.125GHz spacing";
           }
           enum "1529.55" {
             description "1529.55 nm/196.000000 THz 3.125/6.25/12.5/100GHz spacing";
           }
           enum "1529.53" {
             description "1529.53 nm/196.003125 THz 3.125GHz spacing";
           }
           enum "1529.50" {
             description "1529.50 nm/196.006250 THz 3.125/6.25GHz spacing";
           }
           enum "1529.48" {
             description "1529.48 nm/196.009375 THz 3.125GHz spacing";
           }
           enum "1529.46" {
             description "1529.46 nm/196.012500 THz 3.125/6.25/12.5GHz spacing";
           }
           enum "1529.43" {
             description "1529.43 nm/196.015625 THz 3.125GHz spacing";
           }
           enum "1529.41" {
             description "1529.41 nm/196.018750 THz 3.125/6.25GHz spacing";
           }
           enum "1529.38" {
             description "1529.38 nm/196.021875 THz 3.125GHz spacing";
           }
           enum "1529.36" {
             description "1529.36 nm/196.025000 THz 3.125/6.25/12.5GHz spacing";
           }
           enum "1529.33" {
             description "1529.33 nm/196.028125 THz 3.125GHz spacing";
           }
           enum "1529.31" {
             description "1529.31 nm/196.031250 THz 3.125/6.25GHz spacing";
           }
           enum "1529.29" {
             description "1529.29 nm/196.034375 THz 3.125GHz spacing";
           }
           enum "1529.26" {
             description "1529.26 nm/196.037500 THz 3.125/6.25/12.5GHz spacing";
           }
           enum "1529.24" {
             description "1529.24 nm/196.040625 THz 3.125GHz spacing";
           }
           enum "1529.21" {
             description "1529.21 nm/196.043750 THz 3.125/6.25GHz spacing";
           }
           enum "1529.19" {
             description "1529.19 nm/196.046875 THz 3.125GHz spacing";
           }
           enum "1529.16" {
             description "1529.16 nm/196.050000 THz 3.125/6.25/12.5/50/75GHz spacing";
           }
           enum "1529.14" {
             description "1529.14 nm/196.053125 THz 3.125GHz spacing";
           }
           enum "1529.11" {
             description "1529.11 nm/196.056250 THz 3.125/6.25GHz spacing";
           }
           enum "1529.09" {
             description "1529.09 nm/196.059375 THz 3.125GHz spacing";
           }
           enum "1529.07" {
             description "1529.07 nm/196.062500 THz 3.125/6.25/12.5GHz spacing";
           }
           enum "1529.04" {
             description "1529.04 nm/196.065625 THz 3.125GHz spacing";
           }
           enum "1529.02" {
             description "1529.02 nm/196.068750 THz 3.125/6.25GHz spacing";
           }
           enum "1528.99" {
             description "1528.99 nm/196.071875 THz 3.125GHz spacing";
           }
           enum "1528.97" {
             description "1528.97 nm/196.075000 THz 3.125/6.25/12.5GHz spacing";
           }
           enum "1528.94" {
             description "1528.94 nm/196.078125 THz 3.125GHz spacing";
           }
           enum "1528.92" {
             description "1528.92 nm/196.081250 THz 3.125/6.25GHz spacing";
           }
           enum "1528.90" {
             description "1528.90 nm/196.084375 THz 3.125GHz spacing";
           }
           enum "1528.87" {
             description "1528.87 nm/196.087500 THz 3.125/6.25/12.5GHz spacing";
           }
           enum "1528.85" {
             description "1528.85 nm/196.090625 THz 3.125GHz spacing";
           }
           enum "1528.82" {
             description "1528.82 nm/196.093750 THz 3.125/6.25GHz spacing";
           }
           enum "1528.80" {
             description "1528.80 nm/196.096875 THz 3.125GHz spacing";
           }
           enum "1528.77" {
             description "1528.77 nm/196.100000 THz 3.125/6.25/12.5/50/75/100GHz spacing";
           }
           enum "1528.75" {
             description "1528.75 nm/196.103125 THz 3.125GHz spacing";
           }
           enum "1528.72" {
             description "1528.72 nm/196.106250 THz 3.125/6.25GHz spacing";
           }
           enum "1528.70" {
             description "1528.70 nm/196.109375 THz 3.125GHz spacing";
           }
           enum "1528.68" {
             description "1528.68 nm/196.112500 THz 3.125/6.25/12.5GHz spacing";
           }
           enum "1528.65" {
             description "1528.65 nm/196.115625 THz 3.125GHz spacing";
           }
           enum "1528.63" {
             description "1528.63 nm/196.118750 THz 3.125/6.25GHz spacing";
           }
           enum "1528.60" {
             description "1528.60 nm/196.121875 THz 3.125GHz spacing";
           }
           enum "1528.58" {
             description "1528.58 nm/196.125000 THz 3.125/6.25/12.5/75GHz spacing";
           }
           enum "1528.55" {
             description "1528.55 nm/196.128125 THz 3.125GHz spacing";
           }
           enum "1528.53" {
             description "1528.53 nm/196.131250 THz 3.125/6.25GHz spacing";
           }
           enum "1528.51" {
             description "1528.51 nm/196.134375 THz 3.125GHz spacing";
           }
           enum "1528.48" {
             description "1528.48 nm/196.137500 THz 3.125/6.25/12.5GHz spacing";
           }
           enum "1528.46" {
             description "1528.46 nm/196.140625 THz 3.125GHz spacing";
           }
           enum "1528.43" {
             description "1528.43 nm/196.143750 THz 3.125/6.25GHz spacing";
           }
           enum "1528.41" {
             description "1528.41 nm/196.146875 THz 3.125GHz spacing";
           }
           enum "1528.38" {
             description "1528.38 nm/196.15040 THz 50Ghz spacing";
           }
         }
       }
       leaf tx-power {
         description "Transmit laser output power";
         units "dBm";
         type string {
         }
       }
       container loopback {
         presence "enable loopback";
         description "Put the optics in loopback mode";
         uses apply-advanced;
       }
       leaf los-warning-threshold {
         description "LOS warning threshold";
         units "dBm";
         type string;
       }
       leaf los-alarm-threshold {
         description "LOS alarm threshold";
         units "dBm";
         type string;
       }
       leaf modulation-format {
         description "Type of Modulation Format";
         type enumeration {
           enum "16qam" {
             description "16-QAM Modulation Format";
           }
           enum "8qam" {
             description "8-QAM MOdulation Format";
           }
           enum "qpsk" {
             description "QPSK Modulation Format";
           }
         }
       }
       choice laser-enable-choice {
         leaf laser-enable {
           description "Enable Laser";
           type empty;
         }
         leaf no-laser-enable {
           description "Don't enable Laser";
           type empty;
         }
       }
       choice is-ma-choice {
         leaf is-ma {
           description "Link is enabled with alarms masked";
           type empty;
         }
         leaf no-is-ma {
           description "Don't link is enabled with alarms masked";
           type empty;
         }
       }
       leaf encoding {
         description "Line encoding";
         type enumeration {
           enum "differential" {
             description "Differential phase line encoding";
           }
           enum "non-differential" {
             description "Non-differential phase line encoding";
           }
         }
       }
       leaf fec {
         description "Forward Error Correction mode";
         type enumeration {
           enum "sdfec" {
             description "Sky-Compatible Soft Decision Forward Error Correction";
           }
           enum "sdfec25" {
             description "Denali-Compatible Soft Decision Forward Error Correction with 25 percent overhead";
           }
           enum "hgfec" {
             description "High Gain Forward Error Correction";
           }
           enum "sdfec15" {
             description "Soft Decision Forward Error Correction with 15 percent overhead";
           }
         }
       }
       leaf high-polarization {
         description "High polarization tracking mode";
         type empty;
       }
       container signal-degrade {
         description "Signal degrade thresholds";
         uses apply-advanced;
         leaf interval {
           description "Time interval";
           default "10";
           units "milliseconds";
           type union {
             type string {
               pattern "<.*>|$.*";
             }
             type uint32 {
               range "1 .. 1000";
             }
           }
         }
         leaf ber-threshold-clear {
           description "Ber threshold for signal degrade clear (format: xe-n, example: 4.5e-3)";
           type string {
           }
         }
         leaf ber-threshold-signal-degrade {
           description "Ber threshold for signal-degrade (format: xe-n, example: 4.5e-3)";
           type string {
           }
         }
         leaf q-threshold-signal-degrade-clear {
           description "Q threshold for signal-degrade clear (e.g. 14.26)";
           units "dB";
           type string;
         }
         leaf q-threshold-signal-degrade {
           description "Q threshold for signal-degrade (e.g. 9.26)";
           units "dB";
           type string;
         }
       }
       list alarm {
         key name;
         ordered-by user;
         description "Set optic alarms";
         leaf name {
           type enumeration {
             enum "low-light-alarm" {
               description "Enable low light alarm";
             }
           }
         }
         uses apply-advanced;
         choice actiontype {
           case case_1 {
             leaf syslog {
               type empty;
             }
           }
           case case_2 {
             leaf link-down {
               type empty;
             }
           }
         }
       }
       container tca {
         description "Set tca for optic alarms";
         uses apply-advanced;
         container tx-power-high-tca {
           description "Tx power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container tx-power-low-tca {
           description "Tx power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container rx-power-high-tca {
           description "Rx power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container rx-power-low-tca {
           description "Rx power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container rx-signal-power-high-tca {
           description "Rx signal power high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container rx-signal-power-low-tca {
           description "Rx signal power low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm";
             type string {
             }
           }
           leaf threshold-24hrs {
             description "TCA Threshold for 24-hour interval in dBm";
             type string {
             }
           }
         }
         container temperature-high-tca {
           description "Temperature high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in celsius";
             type string {
             }
           }
           leaf threshold-24hrs {
             description "TCA Threshold for 24-hour interval in celsius";
             type string {
             }
           }
         }
         container temperature-low-tca {
           description "Temperature low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in celsius";
             type string {
             }
           }
           leaf threshold-24hrs {
             description "TCA Threshold for 24-hour interval in celsius";
             type string {
             }
           }
         }
         container carrier-frequency-offset-high-tca {
           description "Carrier frequency offset high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
             }
           }
           leaf threshold-24hrs {
             description "TCA Threshold for 24-hour interval in MHz";
             type string {
             }
           }
         }
         container carrier-frequency-offset-low-tca {
           description "Carrier frequency offset low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
             }
           }
           leaf threshold-24hrs {
             description "TCA Threshold for 24-hour interval in MHz";
             type string {
             }
           }
         }
         container fec-ber {
           description "Optics Errored Seconds Threshold crossing defect trigger";
           choice enable-tca-choice {
             leaf enable-tca {
               description "Enable the Optics errored seconds threshold crossing alert";
               type empty;
             }
             leaf no-enable-tca {
               description "Don't enable the Optics errored seconds threshold crossing alert";
               type empty;
             }
           }
           leaf threshold {
             description "TCA Threshold for user-configurable interval (default 15-minutes) in exponential format";
             default "10e-3";
             type string {
             }
           }
           leaf threshold-24hrs {
             description "TCA Threshold for 24-hour interval in exponential format";
             default "10e-3";
             type string {
             }
           }
         }
         container tec-current-high-tca {
           description "TEC Current high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in mA";
             type string {
             }
           }
           leaf threshold-24hrs {
             description "TCA Threshold for 24-hour interval in mA";
             type string {
             }
           }
         }
         container tec-current-low-tca {
           description "TEC Current low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in mA";
             type string {
             }
           }
           leaf threshold-24hrs {
             description "TCA Threshold for 24-hour interval in mA";
             type string {
             }
           }
         }
         container residual-isi-high-tca {
           description "Residual ISI high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in ps/nm";
             type string {
             }
           }
           leaf threshold-24hrs {
             description "TCA Threshold for 24-hour interval in ps/nm";
             type string {
             }
           }
         }
         container residual-isi-low-tca {
           description "Residual ISI low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in ps/nm";
             type string {
             }
           }
           leaf threshold-24hrs {
             description "TCA Threshold for 24-hour interval in ps/nm";
             type string {
             }
           }
         }
         container pam-histogram-high-tca {
           description "PAM Histogram high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes)";
             type string {
             }
           }
           leaf threshold-24hrs {
             description "TCA Threshold for 24-hour interval";
             type string {
             }
           }
         }
         container snr-low-tca {
           description "SNR low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in dBm ";
             type string {
             }
           }
           leaf threshold-24hrs {
             description "TCA Threshold for 24-hour interval in dBm";
             type string {
             }
           }
         }
         container fec-corrected-errors-high-tca {
           description "FEC Corrected Error High Threshold crossing defect trigger";
           uses apply-advanced;
           choice enable-tca-choice {
             leaf enable-tca {
               description "Enable the FEC Corrected Errors threshold crossing alert";
               type empty;
             }
             leaf no-enable-tca {
               description "Don't enable the FEC Corrected Errors threshold crossing alert";
               type empty;
             }
           }
           leaf threshold {
             description "TCA Threshold for user-configurable interval (default 15-minutes) in exponential format";
             default "10e-3";
             type string {
             }
           }
           leaf threshold-24hrs {
             description "TCA Threshold for 24-hour interval in exponential format";
             default "10e-3";
             type string {
             }
           }
         }
         container fec-ucorrected-words-high-tca {
           description "FEC UCorrected Words High Threshold crossing defect trigger";
           uses apply-advanced;
           choice enable-tca-choice {
             leaf enable-tca {
               description "Enable the FEC UCorrected Words threshold crossing alert";
               type empty;
             }
             leaf no-enable-tca {
               description "Don't enable the FEC UCorrected Words threshold crossing alert";
               type empty;
             }
           }
           leaf threshold {
             description "TCA Threshold for user-configurable interval (default 15-minutes) in exponential format";
             default "10e-3";
             type string {
             }
           }
           leaf threshold-24hrs {
             description "TCA Threshold for 24-hour interval in exponential format";
             default "10e-3";
             type string {
             }
           }
         }
         container laser-frequency-error-high-tca {
           description "Laser frequency error high TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
             }
           }
           leaf threshold-24hrs {
             description "TCA Threshold for 24-hour interval in MHz";
             type string {
             }
           }
         }
         container laser-frequency-error-low-tca {
           description "Laser frequency error low TCA";
           uses apply-advanced;
           choice enable-tca-choice {
             leaf enable-tca {
               description "Enable tca";
               type empty;
             }
             leaf no-enable-tca {
               description "Don't enable tca";
               type empty;
             }
           }
           leaf threshold {
             description "TCA Threshold for user-configurable interval (default 15-minutes) in MHz";
             type string {
             }
           }
           leaf threshold-24hrs {
             description "TCA Threshold for 24-hour interval in MHz";
             type string {
             }
           }
         }
       }
       list warning {
         key name;
         ordered-by user;
         description "Set optic warnings";
         leaf name {
           type enumeration {
             enum "low-light-warning" {
               description "Enable low light warning";
             }
           }
         }
         uses apply-advanced;
         choice actiontype {
           case case_1 {
             leaf syslog {
               description "Set action as syslog";
               type empty;
             }
           }
           case case_2 {
             leaf link-down {
               description "Set action as link-down";
               type empty;
             }
           }
         }
       }
       choice lane-info {
         case case_1 {
         }
         case case_2 {
         }
       }
     }
     container och-options {
       description "Optical channel configuration options";
       uses och-attributes;
     }
     container otu-options {
       description "Optical transmission unit configuration options";
       uses otu-attributes;
     }
     container odu-options {
       description "Optical data unit configuration options";
       uses odu-attributes;
     }
     container ett-options {
       description "Transport ethernet client configuration options";
       uses ett-attributes;
     }
     container fastether-options {
       description "Fast Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf ingress-rate-limit {
         description "Ingress rate at port";
         units "megabits per second";
         type union {
           type string {
             pattern "<.*>|$.*";
           }
           type uint32 {
             range "1 .. 100";
           }
         }
       }
       list source-address-filter {
         key name;
         ordered-by user;
         description "Source address filters";
         leaf name {
           description "Remote MAC address";
           type jt:mac-addr;
         }
       }
       container ieee-802.3ad {
         description "IEEE 802.3ad";
         uses apply-advanced;
         container lacp {
           description "Link Aggregation Control Protocol configuration";
           uses apply-advanced;
           leaf port-priority {
             description "Priority of the port (0 ... 65535)";
             type union {
               type uint16;
               type string {
                 pattern "<.*>|$.*";
               }
             }
           }
         }
         leaf bundle {
           description "Join an aggregated Ethernet interface";
           type union {
             type jt:interface-device;
             type string {
               pattern "<.*>|$.*";
             }
           }
         }
         choice type {
           case case_1 {
             leaf primary {
               description "Primary interface for link-protection mode";
               type empty;
             }
           }
           case case_2 {
             leaf backup {
               description "Backup interface for link-protection mode";
               type empty;
             }
           }
         }
       }
       container mpls {
         description "MPLS options";
         uses mpls_ifd_options;
       }
       leaf ignore-l3-incompletes {
         description "Ignore L3 incomplete errors";
         type empty;
       }
     }
     container aggregated-ether-options {
       description "Aggregated Ethernet interface-specific options";
       uses apply-advanced;
       choice loopback-choice {
         leaf loopback {
           description "Enable loopback";
           type empty;
         }
         leaf no-loopback {
           description "Don't enable loopback";
           type empty;
         }
       }
       choice flow-control-choice {
         leaf flow-control {
           description "Enable flow control";
           type empty;
         }
         leaf no-flow-control {
           description "Don't enable flow control";
           type empty;
         }
       }
       choice source-filtering-choice {
         leaf source-filtering {
           description "Enable source address filtering";
           type empty;
         }
         leaf no-source-filtering {
           description "Don't enable source address filtering";
           type empty;
         }
       }
       leaf autostate-exclude {
         description "Interface will not contribute to IRB state";
         type empty;
       }
       container link-protection {
         presence "enable link-protection";
         description "Enable link protection mode";
         uses apply-advanced;
         leaf revertive {
           description "Revert back from active backup link to primary, if primary is UP";
           type empty;
         }
         leaf non-revertive {
           description "Do not revert back (default mode) from active backup link to primary, if primary is UP";
           type empty;
         }
         leaf backup-state {
           description "Link protection backup link state";
           default "accept-data";
           type enumeration {
             enum "accept-data" {
               description "Accept data on receive channel of backup link";
             }
             enum "discard-data" {
               description "Discard data on receive channel of backup link";
             }
             enum "down" {
               description "Backup link is marked down";
             }
           }
         }
         container rtg-config {
           presence "enable rtg-config";
           description "RTG enable on AE";
           uses apply-advanced;
           leaf preempt-cutover-timer {
             description "RTG preempt-cutover-timer in seconds";
             default "1";
             type union {
               type string {
                 pattern "<.*>|$.*";
               }
               type uint32 {
                 range "0 .. 255";
               }
             }
           }
         }
       }
       choice fcoe-lag-choice {
         leaf fcoe-lag {
           description "Enable FIP/FCoE LAG";
           type empty;
         }
         leaf no-fcoe-lag {
           description "Don't enable FIP/FCoE LAG";
           type empty;
         }
       }
       list source-address-filter {
         key name;
         ordered-by user;
         description "Source address filters";
         leaf name {
           description "Remote MAC address";
           type jt:mac-addr;
         }
       }
       container load-balance {
         uses aggregate-load-balance;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         container damping {
           description "BFD flap damping parameters";
           uses apply-advanced;
           leaf suppress {
             description "Suppress threshold for figure-of-merit value";
             default "5000";
             type union {
               type string {
                 pattern "<.*>|$.*";
               }
               type uint32 {
                 range "1000 .. 200000";
               }
             }
           }
           leaf reuse {
             description "Reuse threshold for figure-of-merit value";
             default "1000";
             type union {
               type string {
                 pattern "<.*>|$.*";
               }
               type uint32 {
                 range "1000 .. 200000";
               }
             }
           }
           leaf max-suppress-time {
             description "Maximum hold-down time";
             default "600";
             units "seconds";
             type union {
               type string {
                 pattern "<.*>|$.*";
               }
               type uint32 {
                 range "1 .. 20000";
               }
             }
           }
           leaf half-life-interval {
             description "Decay half life interval";
             default "30";
             units "seconds";
             type union {
               type string {
                 pattern "<.*>|$.*";
               }
               type uint32 {
                 range "1 .. 600";
               }
             }
           }
           leaf increment {
             description "Increments applied to figure-of-merit value for every flap";
             default "1000";
             type union {
               type string {
                 pattern "<.*>|$.*";
               }
               type uint32 {
                 range "1000 .. 20000";
               }
             }
           }
         }
         leaf neighbor {
           description "BFD neighbor address";
           type jt:ipaddr;
           mandatory true;
         }
         leaf local-address {
           description "BFD local address";
           type jt:ipaddr;
           mandatory true;
         }
         leaf holddown-interval {
           description "Time to hold the session-UP notification to the client";
           units "milliseconds";
           type union {
             type string {
               pattern "<.*>|$.*";
             }
             type uint32 {
               range "0 .. 255000";
             }
           }
         }
       }
       leaf minimum-links {
         description "Minimum number of aggregated links";
         type union {
           type string {
             pattern "<.*>|$.*";
           }
           type uint16;
         }
       }
       container minimum-bandwidth {
         presence "enable minimum-bandwidth";
         description "Minimum bandwidth configured for aggregated bundle";
         uses apply-advanced;
         leaf bw-value {
           description "Bandwidth value";
           default "1";
           type union {
             type uint64;
             type string {
               pattern "<.*>|$.*";
             }
           }
         }
         leaf bw-unit {
           description "Bandwidth unit";
           type enumeration {
             enum "bps" {
               description "Links are in bits per sec";
             }
             enum "kbps" {
               description "Links are in kilo bits per sec";
             }
             enum "mbps" {
               description "Links are in mega bits per sec";
             }
             enum "gbps" {
               description "Links are in giga bits per sec ";
             }
           }
         }
       }
       choice redundancy_choice {
         case case_1 {
         }
         case case_2 {
         }
       }
       container rebalance-periodic {
         uses apply-advanced;
       }
       leaf link-speed {
         description "Link speed of individual interface that joins the AE";
         type enumeration {
           enum "10m" {
             description "Links are 10M";
           }
           enum "100m" {
             description "Links are 100M";
           }
           enum "1g" {
             description "Links are 1G";
           }
           enum "2.5g" {
             description "Links are 2.5G";
           }
           enum "5g" {
             description "Links are 5G";
           }
           enum "8g" {
             description "Links are 8G";
           }
           enum "10g" {
             description "Links are 10G";
           }
           enum "25g" {
             description "Links are 25G";
           }
           enum "40g" {
             description "Links are 40G";
           }
           enum "50g" {
             description "Links are 50G";
           }
           enum "80g" {
             description "Links are 80G";
           }
           enum "100g" {
             description "Links are 100G";
           }
           enum "200g" {
             description "Links are 200G";
           }
           enum "400g" {
             description "Links are 400G";
           }
           enum "800g" {
             description "Links are 800G";
           }
           enum "oc192" {
             description "Links are OC-192";
           }
           enum "mixed" {
             description "Links are various speeds";
           }
         }
       }
       container local-bias {
         presence "enable local-bias";
         description "Turn on local bias functionality";
         uses apply-advanced;
         leaf disable {
           description "Disable local-bias";
           type empty;
         }
       }
       container lacp {
         description "Link Aggregation Control Protocol configuration";
         uses apply-advanced;
         choice mode {
           case case_1 {
             leaf active {
               description "Initiate transmission of LACP packets";
               type empty;
             }
           }
           case case_2 {
             leaf passive {
               description "Respond to LACP packets";
               type empty;
             }
           }
         }
         leaf periodic {
           description "Timer interval for periodic transmission of LACP packets";
           type enumeration {
             enum "fast" {
               description "Receive packets every second";
             }
             enum "slow" {
               description "Receive packets every 30 seconds";
             }
           }
         }
         leaf multiplier {
           description "LACP timeout detection multiplier";
           type union {
             type string {
               pattern "<.*>|$.*";
             }
             type uint32 {
               range "3 .. 30";
             }
           }
         }
         container link-protection {
           presence "enable link-protection";
           uses apply-advanced;
           leaf disable {
             description "To turn off LACP link-protection";
             type empty;
           }
           choice mode {
             case case_1 {
               leaf revertive {
                 description "Switch links when better priority link comes up";
                 type empty;
               }
             }
             case case_2 {
               leaf non-revertive {
                 description "Do not switch links when better priority link comes up";
                 type empty;
               }
             }
           }
           container rtg-config {
             presence "enable rtg-config";
             description "RTG Feature enable on AE";
             uses apply-advanced;
             leaf preempt-cutover-timer {
               description "RTG preempt-cutover-timer in seconds";
               default "1";
               type union {
                 type string {
                   pattern "<.*>|$.*";
                 }
                 type uint32 {
                   range "0 .. 255";
                 }
               }
             }
           }
         }
         leaf sync-reset {
           description "On minimum-link failure notify out of sync to peer";
           type enumeration {
             enum "disable" {
               description "To disable minimum-link failure handling at LACP level";
             }
             enum "enable" {
               description "To enable minimum-link failure handling at LACP level";
             }
           }
         }
         leaf system-priority {
           description "Priority of the system (0 ... 65535)";
           type string;
         }
         leaf system-id {
           description "Node's System ID, encoded as a MAC address";
           type jt:mac-addr;
         }
         leaf admin-key {
           description "Node's administrative key";
           type union {
             type uint16;
             type string {
               pattern "<.*>|$.*";
             }
           }
         }
       }
       list link-protection-sub-group {
         key name;
         ordered-by user;
         description "Link Protection subgroup configuration";
         leaf name {
           description "Name of the subgroup";
           type string {
             length "2 .. 64";
           }
         }
         uses apply-advanced;
         choice type {
           case case_1 {
             leaf primary {
               description "Primary subgroup for N:N link-protection mode";
               type empty;
             }
           }
           case case_2 {
             leaf backup {
               description "Backup subgroup for N:N link-protection mode";
               type empty;
             }
           }
         }
       }
       container ethernet-switch-profile {
         description "Ethernet virtual LAN/media access control-level options";
         uses apply-advanced;
         leaf-list tag-protocol-id {
           ordered-by user;
           description "IEEE 802.1q Tag Protocol Identifier values for VLAN-tagged frames";
           type string;
         }
         leaf mac-learn-enable {
           description "Learn MAC addresses dynamically";
           type empty;
         }
       }
     }
     container es-options {
       description "ES PIC interface-specific options";
       uses apply-advanced;
       leaf backup-interface {
         description "Name of backup interface";
         type union {
           type jt:interface-device;
           type string {
             pattern "<.*>|$.*";
           }
         }
       }
     }
     container vdsl-options {
       description "VDSL interface-specific options";
       uses apply-advanced;
       leaf vdsl-profile {
         description "VDSL profile";
         type enumeration {
           enum "auto" {
             description "Auto";
           }
           enum "8a" {
             description "Profile 8a";
           }
           enum "8b" {
             description "Profile 8b";
           }
           enum "8c" {
             description "Profile 8c";
           }
           enum "8d" {
             description "Profile 8d";
           }
           enum "12a" {
             description "Profile 12a";
           }
           enum "12b" {
             description "Profile 12b";
           }
           enum "17a" {
             description "Profile 17a";
           }
         }
       }
       leaf sra {
         description "DSL SRA";
         default "disable";
         type enumeration {
           enum "enable" {
             description "Enable SRA";
           }
           enum "disable" {
             description "Disable SRA";
           }
         }
       }
       leaf v43 {
         description "DSL V43 tones";
         default "enable";
         type enumeration {
           enum "enable" {
             description "Enable V43";
           }
           enum "disable" {
             description "Disable V43";
           }
         }
       }
       leaf sos {
         description "Enable SOS";
         type empty;
       }
     }
     container dsl-sfp-options {
       description "DSL SFP options";
       uses apply-advanced;
       container adsl-options {
         description "ADSL options";
         uses apply-advanced;
         leaf vpi {
           description "Virtual path identifier";
           type union {
             type string {
               pattern "<.*>|$.*";
             }
             type uint32 {
               range "0 .. 255";
             }
           }
         }
         leaf vci {
           description "Virtual circuit identifier";
           type union {
             type string {
               pattern "<.*>|$.*";
             }
             type uint32 {
               range "32 .. 65535";
             }
           }
         }
         leaf encap {
           description "Encapsulation";
           type enumeration {
             enum "bypass" {
               description "Bypass";
             }
             enum "llcsnap-bridged-802dot1q" {
               description "LLCSNAP bridged 802.1q";
             }
             enum "llcsnap-routed-ip" {
               description "LLCSNAP routed ip";
             }
             enum "vc-mux-bridged" {
               description "VC MUX bridged";
             }
             enum "vc-mux-routed-ip" {
               description "VC MUX routed ip";
             }
             enum "generic" {
               description "Generic";
             }
           }
         }
         leaf annex {
           description "Annex type";
           type enumeration {
             enum "auto" {
               description "Annex type auto";
             }
             enum "annexj-off" {
               description "Annex type annexj turn off";
             }
           }
         }
       }
       container vdsl-options {
         description "VDSL options";
         uses apply-advanced;
         leaf profile {
           description "VDSL profile";
           type enumeration {
             enum "auto" {
               description "Automatic";
             }
             enum "8a" {
               description "Profile 8a";
             }
             enum "8b" {
               description "Profile 8b";
             }
             enum "8c" {
               description "Profile 8c";
             }
             enum "8d" {
               description "Profile 8d";
             }
             enum "12a" {
               description "Profile 12a";
             }
             enum "12b" {
               description "Profile 12b";
             }
             enum "17a" {
               description "Profile 17a";
             }
             enum "30a" {
               description "Profile 30a";
             }
           }
         }
         leaf carrier {
           description "Carrier setting";
           type enumeration {
             enum "auto" {
               description "Automatic";
             }
             enum "a43" {
               description "Carrier A43";
             }
             enum "b43" {
               description "Carrier B43";
             }
           }
         }
       }
       container gfast-options {
         description "G.fast options";
         uses apply-advanced;
         leaf carrier {
           description "Carrier setting";
           type enumeration {
             enum "a43" {
               description "Carrier A43";
             }
             enum "a43c" {
               description "Carrier A43C";
             }
             enum "b43" {
               description "Carrier B43";
             }
             enum "b43c" {
               description "Carrier B43C";
             }
           }
         }
       }
     }
     container shdsl-options {
       description "SHDSL interface-specific options";
       uses apply-advanced;
       leaf annex {
         description "Type of SHDSL annex";
         default "annex-b";
         type enumeration {
           enum "annex-a" {
             description "Annex-a PIC";
           }
           enum "annex-b" {
             description "Annex-b PIC";
           }
           enum "annex-f" {
             description "Annex-f PIC";
           }
           enum "annex-g" {
             description "Annex-g PIC";
           }
           enum "annex-auto" {
             description "Annex-auto PIC";
           }
         }
       }
       leaf line-rate {
         description "SHDSL line rate";
         type string;
       }
       leaf loopback {
         description "Loopback mode";
         type enumeration {
           enum "local" {
             description "Local loopback";
           }
           enum "remote" {
             description "Remote loopback";
           }
         }
       }
       container snr-margin {
         presence "enable snr-margin";
         description "Signal to noise ratio margin";
         uses apply-advanced;
         leaf current {
           description "Current signal to noise ratio margin";
           units "dB";
           type string;
         }
         leaf snext {
           description "SNEXT signal to noise ratio margin";
           units "dB";
           type string;
         }
       }
     }
     container container-options {
       description "Container interface specific options";
       uses apply-advanced;
       container container-type {
         presence "enable container-type";
         description "Protocol type of the container interface";
         uses apply-advanced;
         choice container-type-choice {
           case case_1 {
             container aps {
               description "APS options on the container";
               presence "enable aps";
               uses aps_type;
             }
           }
         }
       }
       container member-interface-type {
         description "Link type of members of container";
         uses apply-advanced;
         choice member_interface_type_choice {
           case case_1 {
             container sonet {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                   enum "oc192" {
                     description "Links are OC-192";
                   }
                   enum "oc768" {
                     description "Links are OC-768";
                   }
                   enum "mixed" {
                     description "Links are of different speeds";
                   }
                 }
                 mandatory true;
               }
             }
           }
           case case_2 {
             container atm {
               uses apply-advanced;
               leaf member-interface-speed {
                 description "Link speed of members of container";
                 type enumeration {
                   enum "oc3" {
                     description "Links are OC-3";
                   }
                   enum "oc12" {
                     description "Links are OC-12";
                   }
                   enum "oc48" {
                     description "Links are OC-48";
                   }
                 }
                 mandatory true;
               }
             }
           }
           case case_3 {
             container channelized-sonet {
               uses apply-advanced;
               leaf member-interface-speed {
                 description "Link speed of members of container";
                 type enumeration {
                   enum "coc3" {
                     description "Links are COC-3";
                   }
                   enum "coc12" {
                     description "Links are COC-12";
                   }
                   enum "coc48" {
                     description "Links are COC-48";
                   }
                   enum "coc192" {
                     description "Links are COC-192";
                   }
                   enum "coc768" {
                     description "Links are COC-768";
                   }
                 }
                 mandatory true;
               }
             }
           }
           case case_4 {
             container channelized-sdh {
               uses apply-advanced;
               leaf member-interface-speed {
                 description "Link speed of members of container";
                 type enumeration {
                   enum "cstm1" {
                     description "Links are cstm-1";
                   }
                   enum "cstm4" {
                     description "Links are cstm-4";
                   }
                   enum "cstm16" {
                     description "Links are cstm-16";
                   }
                   enum "coc64" {
                     description "Links are cstm-64";
                   }
                   enum "cstm256" {
                     description "Links are cstm256";
                   }
                 }
                 mandatory true;
               }
             }
           }
         }
       }
       container redundancy {
         description "Container interface redundancy options";
         uses apply-advanced;
         container hold-time {
           description "Hold time for link up and link down";
           leaf up {
             description "Link up hold time";
             units "milliseconds";
             type union {
               type string {
                 pattern "<.*>|$.*";
               }
               type uint32 {
                 range "0 .. 65534";
               }
             }
             mandatory true;
           }
           leaf down {
             description "Link down hold time";
             units "milliseconds";
             type union {
               type string {
                 pattern "<.*>|$.*";
               }
               type uint32 {
                 range "0 .. 65534";
               }
             }
             mandatory true;
           }
         }
       }
       leaf-list container-list {
         ordered-by user;
         description "List of container interfaces this member link is associated to";
         type union {
           type jt:interface-device;
           type string {
             pattern "<.*>|$.*";
           }
         }
       }
       choice redundancy-type {
         case case_1 {
           choice aps-redundancy {
             case case_1 {
               leaf primary {
                 description "This member link is primary interface of the container";
                 type empty;
               }
             }
             case case_2 {
               leaf standby {
                 description "This member link is standby interface of the container";
                 type empty;
               }
             }
           }
         }
       }
       leaf fast-aps {
         description "Fast APS switch";
         type empty;
       }
       leaf allow-configuration-override {
         description "Allow physical configuration of member link to override container configuration";
         type empty;
       }
     }
     list unit {
       key name;
       description "Logical interface";
       leaf name {
         type string;
       }
       uses apply-advanced;
       leaf interface-tag {
         description "Interface tag name";
         type string {
           length "1 .. 64";
         }
       }
       leaf alias {
         description "Interface alias";
         type string;
       }
       container peer-psd {
         presence "enable peer-psd";
         description "Peer psd";
         leaf psd-name {
           description "Peer psd name";
           type string;
           mandatory true;
         }
       }
       container peer-interface {
         presence "enable peer-interface";
         description "Peer interface";
         uses apply-advanced;
         leaf interface-name {
           description "Peer interface name";
           type union {
             type jt:interface-unit;
             type string {
               pattern "<.*>|$.*";
             }
           }
         }
       }
       container interface-shared-with {
         presence "enable interface-shared-with";
         description "Specify which PSD owns this logical interface";
         uses apply-advanced;
         leaf psd-name {
           description "Name of protected system domain (psd[1-31], ex. psd2)";
           type string {
           }
           mandatory true;
         }
       }
       choice enable-disable {
         case case_1 {
           leaf disable {
             description "Disable this logical interface";
             type empty;
           }
         }
       }
       leaf extended-telemetry {
         description "Enable extended telemetry";
         type empty;
       }
       leaf passive-monitor-mode {
         description "Use interface to tap packets from another router";
         type empty;
       }
       leaf clear-dont-fragment-bit {
         description "Clear DF bit in packet (AS PIC and J-series only as well as MIF)";
         type empty;
       }
       leaf description {
         description "Text description of interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-ppp-funi" {
             description "ATM PPP over FUNI";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             type string;
           }
         }
         case case_2 {
           leaf vlan-id-range {
             description "Virtual LAN identifier range of form vid1-vid2";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
               mandatory true;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
       leaf native-inner-vlan-id {
         description "Native virtual LAN identifier for singly tagged frames";
         type union {
           type string {
             pattern "<.*>|$.*";
           }
           type uint32 {
             range "0 .. 4094";
           }
         }
       }
       container accept-source-mac {
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       choice psn_vci_type {
         case case_1 {
         }
         case case_2 {
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         description "ATM VCI range start <start-vci> end <end-vci>";
         leaf start {
           description "ATM VCI range's start value";
           type union {
             type string {
               pattern "<.*>|$.*";
             }
             type uint16 {
               range "32 .. 4094";
             }
           }
           mandatory true;
         }
         leaf end {
           description "ATM VCI range's end value";
           type union {
             type string {
               pattern "<.*>|$.*";
             }
             type uint16 {
               range "32 .. 4094";
             }
           }
           mandatory true;
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       choice keepalive_choices {
         case case_1 {
           container keepalives {
             description "Send or demand keepalive messages";
             presence "enable keepalives";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           description "Encapsulation over tunnel";
           container vxlan-gpe {
             presence "enable vxlan-gpe";
             uses apply-advanced;
             container source {
               uses apply-advanced;
               leaf address {
                 description "Interface address prefix";
                 type jt:ipv4addr;
               }
               leaf mac-address {
                 description "Interface source mac address";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 type jt:mac-addr;
               }
             }
             leaf tunnel-endpoint {
               description "Tunnel end point type";
               type enumeration {
                 enum "vxlan" {
                   description "To configure vxlan tunnel-end-point";
                 }
               }
               mandatory true;
             }
             container source-udp-port-range {
               description "Value range for source-udp-port";
               leaf min {
                 description "Minimum range value";
                 type union {
                   type string {
                     pattern "<.*>|$.*";
                   }
                   type uint32 {
                     range "1 .. 65535";
                   }
                 }
                 mandatory true;
               }
               leaf max {
                 description "Maximum range value";
                 type union {
                   type string {
                     pattern "<.*>|$.*";
                   }
                   type uint32 {
                     range "1 .. 65535";
                   }
                 }
                 mandatory true;
               }
             }
             leaf destination-udp-port {
               description "Value to write to the destination-udp-port field";
               type union {
                 type string {
                   pattern "<.*>|$.*";
                 }
                 type uint32 {
                   range "1 .. 65535";
                 }
               }
               mandatory true;
             }
             leaf vni {
               description "Value to write to the vni field";
               type union {
                 type string {
                   pattern "<.*>|$.*";
                 }
                 type uint32 {
                   range "0 .. 16777214";
                 }
               }
               mandatory true;
             }
           }
         }
         choice source_type {
           case case_1 {
             leaf source {
               description "Tunnel source address";
               type jt:ipaddr;
             }
           }
           case case_2 {
           }
           case case_3 {
           }
         }
         choice destination_type {
           case case_1 {
             leaf destination {
               description "Tunnel destination address";
               type jt:ipaddr;
             }
           }
           case case_2 {
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             type string {
             }
           }
         }
       }
       leaf compression-device {
         description "Logical interface used for compression";
         type union {
           type jt:interface-unit;
           type string {
             pattern "<.*>|$.*";
           }
         }
       }
       container layer2-policer {
         description "Layer2 policing for logical interface";
         uses apply-advanced;
         choice layer2-input-policer-choice {
           case case_1 {
             leaf input-policer {
               description "Two-color policer for received packets";
               type string;
             }
           }
           case case_2 {
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       choice virtual-gateway {
         case case_1 {
           leaf no-auto-virtual-gateway-esi {
             description "Disable auto ESI generation for virtual gateway address";
             type empty;
           }
         }
         case case_2 {
           container virtual-gateway-esi {
             description "ESI configuration of virtual gateway";
             uses apply-advanced;
             leaf identifier {
               description "ESI value for the interface";
               type jt:esi;
               mandatory true;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             type string;
             mandatory true;
           }
           uses apply-advanced;
           leaf activate-all {
             description "Activate all rules and rulebases in the pcef profile";
             type empty;
           }
           list activate {
             key name;
             ordered-by user;
             description "Name of pcef profile rule or rulebase to activate";
             leaf name {
               description "Name of pcef profile rule or rulebase to activate";
               type string;
             }
             uses apply-advanced;
           }
         }
       }
       choice generate-eui64-choice {
         leaf generate-eui64 {
           description "To generate Link Local EUI-64 addresses";
           type empty;
         }
         leaf no-generate-eui64 {
           description "Don't to generate Link Local EUI-64 addresses";
           type empty;
         }
       }
       container family {
         description "Protocol family";
         container inet {
           presence "enable inet";
           description "IPv4 parameters";
           uses apply-advanced;
           container class-based-filtering {
             description "Enable class based filter on interface";
             uses apply-advanced;
           }
           container dhcp {
             description "Dynamic Host Configuration Protocol client configuration";
             presence "enable dhcp";
             uses dhcp-client-type;
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf no-redirects {
             description "Do not redirect traffic";
             type empty;
           }
           leaf nat-outside-interface {
             description "Public interface used for NAT";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           leaf allow-filter-on-re {
             description "Enable kernel filter on network ports";
             type empty;
           }
           container filter {
             description "Packet filtering";
             uses apply-advanced;
             choice input_choice {
               case case_1 {
                 container input {
                   description "Filter to be applied to received packets";
                   leaf filter-name {
                     description "Name of the filter";
                     type string;
                     mandatory true;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                     mandatory true;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               type string;
             }
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
               mandatory true;
             }
             uses apply-advanced;
             leaf ipsec-vpn {
               description "Name of IPSec VPN";
               type string;
               mandatory true;
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address/destination prefix";
             leaf name {
               description "Interface address/destination prefix";
               type jt:ipv4prefix;
             }
             uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 type union {
                   type string {
                     pattern "<.*>|$.*";
                   }
                   type uint32 {
                     range "1 .. 4294967295";
                   }
                 }
                 mandatory true;
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 type union {
                   type string {
                     pattern "<.*>|$.*";
                   }
                   type uint32 {
                     range "1 .. 4294967295";
                   }
                 }
                 mandatory true;
               }
               leaf type {
                 description "Tag type must be [1-16]";
                 type union {
                   type string {
                     pattern "<.*>|$.*";
                   }
                   type uint32 {
                     range "1 .. 16";
                   }
                 }
               }
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
                 mandatory true;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
               leaf flood-as-unknown-unicast {
                 description "Broadcast the packet with unicast MAC";
                 type empty;
               }
             }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
               mandatory true;
             }
             leaf preferred-source-address {
               description "Preferred address on the donor interface";
               type string;
             }
             leaf destination {
               description "Destination address";
               type jt:ipv4addr;
             }
             leaf destination-profile {
               description "Profile to use for destination address";
               type string;
             }
           }
           leaf negotiate-address {
             description "Negotiate address with remote";
             type empty;
           }
           leaf destination-udp-port {
             description "Choose destination UDP port number";
             type union {
               type string {
                 pattern "<.*>|$.*";
               }
               type uint32 {
                 range "10000 .. 10009";
               }
             }
           }
           container auto-configure {
             description "Auto configuration";
             uses dynamic_ipv4_type;
           }
         }
         container mlppp {
           description "Multilink PPP protocol parameters";
           uses apply-advanced;
           leaf bundle {
             description "Logical interface name this link will join";
             type string;
             mandatory true;
           }
           choice anchor-points {
             case case_1 {
             }
             case case_2 {
             }
           }
           leaf dynamic-profile {
             description " dynamic profile for interface to use";
             type string {
               length "1 .. 80";
             }
           }
         }
         container mlfr-end-to-end {
           presence "enable mlfr-end-to-end";
           description "Multilink Frame Relay end-to-end protocol parameters";
           uses apply-advanced;
           leaf bundle {
             description "Logical interface name this link will join";
             type union {
               type jt:interface-unit;
               type string {
                 pattern "<.*>|$.*";
               }
             }
             mandatory true;
           }
         }
         container mlfr-uni-nni {
           presence "enable mlfr-uni-nni";
           description "Multilink Frame Relay UNI NNI protocol parameters";
           uses apply-advanced;
           leaf bundle {
             description "Logical interface name this link will join";
             type union {
               type jt:interface-unit;
               type string {
                 pattern "<.*>|$.*";
               }
             }
             mandatory true;
           }
         }
         container ccc {
           presence "enable ccc";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
         }
         container vpls {
           presence "enable vpls";
           description "Virtual private LAN service parameters";
           uses apply-advanced;
           leaf core-facing {
             description "Interface is core facing";
             type empty;
           }
         }
         container ethernet-switching {
           description "Ethernet switching parameters";
           presence "enable ethernet-switching";
           uses ethernet-switching-type;
         }
         container any {
           presence "enable any";
           description "Parameters for 'any' family";
           uses apply-advanced;
           container filter {
             description "Layer 2 packet filtering";
             uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         description "AMS subunit load balancing options";
         uses apply-advanced;
         leaf preferred-active {
           description "Preferred active Interface name";
           type union {
             type jt:interface-device;
             type string {
               pattern "<.*>|$.*";
             }
           }
         }
         leaf disable-hash {
           description "Hash based distribution is not needed for this subunit";
           type empty;
         }
         leaf modulo-key {
           description "Modulo based distribution";
           type enumeration {
             enum "source-ip" {
               description "Source Ip Address";
             }
             enum "destination-ip" {
               description "Destination Ip Address";
             }
           }
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           type union {
             type uint16;
             type string {
               pattern "<.*>|$.*";
             }
           }
         }
         leaf vtep-count {
           description "Minimum number of VTEP link in up state to consider IRB up";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf no-dhcp-flood {
         description "Disable dhcp flooding";
         type empty;
       }
       leaf etree-ac-role {
         description "ETREE attachment circuit role";
         type enumeration {
           enum "root" {
             description "ETREE root interface";
           }
           enum "leaf" {
             description "ETREE leaf interface";
           }
         }
       }
     }
     container no-partition {
       description "Use channelizable interface as clear channel";
       leaf interface-type {
         description "Interface type";
         type enumeration {
           enum "e1" {
             description "E1 interface";
           }
           enum "t1" {
             description "T1 interface";
           }
           enum "at" {
             description "ATM interface";
           }
           enum "t3" {
             description "T3 interface";
           }
           enum "e3" {
             description "E3 interface";
           }
           enum "ct3" {
             description "Channelized T3 interface";
           }
           enum "so" {
             description "SONET interface";
           }
           enum "cau4" {
             description "CAU4 interface";
           }
         }
       }
     }
     list partition {
       key name;
       ordered-by user;
       description "Channelized interface partition";
       leaf name {
         description "Sublevel interface partition index (for example, 1, 3-4)";
         type string;
       }
       leaf oc-slice {
         description "Range of SONET/SDH slices (for example, 1, 7-9)";
         type string;
       }
       leaf timeslots {
         description "Timeslots [(1..24) for T1, (1..31) for E1]; for example, 1-3,4,9,22-24 (no spaces)";
         type string;
       }
       leaf interface-type {
         description "Sublevel interface type";
         type enumeration {
           enum "ds" {
             description "DS0 interface";
           }
           enum "e1" {
             description "E1 interface";
           }
           enum "t1" {
             description "T1 interface";
           }
           enum "at" {
             description "ATM interface";
           }
           enum "ct1" {
             description "Channelized T1 interface";
           }
           enum "ce1" {
             description "Channelized E1 interface";
           }
           enum "t3" {
             description "T3 interface";
           }
           enum "ct3" {
             description "Channelized T3 interface";
           }
           enum "e3" {
             description "E3 interface";
           }
           enum "so" {
             description "SONET interface";
           }
           enum "coc1" {
             description "Channelized OC1 interface";
           }
           enum "cau4" {
             description "Channelized AU4 interface";
           }
           enum "dc" {
             description "D channel interface";
           }
           enum "bc" {
             description "B channel interface";
           }
         }
         mandatory true;
       }
     }
   }
   grouping jsrc-options {
     uses apply-advanced;
     list partition {
       key name;
       ordered-by user;
       description "JSRC partition definition";
       leaf name {
         description "JSRC partition name";
         type string {
           length "1 .. 63";
         }
       }
       uses apply-advanced;
       leaf diameter-instance {
         description "JSRC diameter instance";
         type string {
           length "1 .. 63";
         }
         mandatory true;
       }
       leaf destination-realm {
         description "JSRC destination realm";
         type string {
           length "1 .. 63";
         }
         mandatory true;
       }
       leaf destination-host {
         description "JSRC destination host";
         type string {
           length "1 .. 63";
         }
         mandatory true;
       }
     }
   }
   grouping juniper-class-of-service-options {
     uses apply-advanced;
     container classifiers {
       description "Classify incoming packets based on code point value";
       uses apply-advanced;
       list dscp {
         key name;
         ordered-by user;
         description "Differentiated Services code point classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list dscp-ipv6 {
         key name;
         ordered-by user;
         description "Differentiated Services code point classifier IPv6";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list exp {
         key name;
         ordered-by user;
         description "MPLS EXP classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1 {
         key name;
         ordered-by user;
         description "IEEE-802.1 classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list inet-precedence {
         key name;
         ordered-by user;
         description "IPv4 precedence classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
       list ieee-802.1ad {
         key name;
         ordered-by user;
         description "IEEE-802.1ad (DEI) classifier";
         leaf name {
           description "Classifier name";
           type string {
             length "1 .. 64";
           }
         }
         uses apply-advanced;
         leaf import {
           description "Include this classifier in this definition";
           type union {
             type string {
               pattern "default";
             }
             type string {
               length "1 .. 64";
             }
           }
         }
         list forwarding-class {
           key name;
           description "Define a classification of code point aliases";
           leaf name {
             description "Forwarding class name";
             type string {
               length "1 .. 64";
             }
           }
           uses apply-advanced;
           list loss-priority {
             key name;
             description "Classify code points to a loss priority";
             leaf name {
               type enumeration {
                 enum "low" {
                   description "Code points to classify to loss priority low";
                 }
                 enum "high" {
                   description "Code points to classify to loss priority high";
                 }
                 enum "medium-low" {
                   description "Code points to classify to loss priority medium-low";
                 }
                 enum "medium-high" {
                   description "Code points to classify to loss priority medium-high";
                 }
               }
             }
             leaf-list code-points {
               ordered-by user;
               description "List of code point aliases and/or bit strings";
               type string;
             }
           }
         }
       }
     }
     container code-point-aliases {
       description "Mapping of code point aliases to bit strings";
       uses apply-advanced;
       list dscp {
         key name;
         description "Differentiated Services code point aliases";
         leaf name {
           description "DSCP alias name";
           type string {
           }
         }
         leaf bits {
           description "DSCP 6-bit pattern";
           type string {
           }
           mandatory true;
         }
       }
       list dscp-ipv6 {
         key name;
         description "Differentiated Services code point aliases IPv6";
         leaf name {
           description "DSCP IPv6 alias name";
           type string {
           }
         }
         leaf bits {
           description "DSCP 6-bit pattern";
           type string {
           }
           mandatory true;
         }
       }
       list exp {
         key name;
         description "MPLS EXP code point aliases";
         leaf name {
           description "EXP alias name";
           type string {
           }
         }
         leaf bits {
           description "EXP 3-bit pattern";
           type string {
           }
           mandatory true;
         }
       }
       list ieee-802.1 {
         key name;
         description "IEEE-802.1 code point aliases";
         leaf name {
           description "IEEE-802.1 alias name";
           type string {
           }
         }
         leaf bits {
           description "IEEE-802.1 3-bit pattern";
           type string {
           }
           mandatory true;
         }
       }
       list inet-precedence {
         key name;
         description "IPv4 precedence code point aliases";
         leaf name {
           description "IPv4 precedence alias name";
           type string {
           }
         }
         leaf bits {
           description "IPv4 precedence 3-bit pattern";
           type string {
           }
           mandatory true;
         }
       }
       list ieee-802.1ad {
         key name;
         description "IEEE-802.1ad (DEI) code point aliases";
         leaf name {
           description "IEEE-802.1ad (DEI) alias name";
           type string {
           }
         }
         leaf bits {
           description "IEEE-802.1ad (DEI) 4-bit pattern";
           type string {
           }
           mandatory true;
         }
       }
     }
     container host-outbound-traffic {
       description "Classify and mark host traffic to forwarding engine";
       uses apply-advanced;
       leaf forwarding-class {
         description "Classification of host traffic to forwarding engine";
         type string {
           length "1 .. 64";
         }
       }
       leaf dscp-code-point {
         description "Static DSCP code point of egress host traffic";
         type string {
         }
       }
       leaf override-firewall {
         description "Override firewall filter actions for RE generated traffic";
         type empty;
       }
       container tcp {
         presence "enable tcp";
         description "Settings for host outbound TCP packets";
         uses apply-advanced;
         leaf raise-internet-control-priority {
           description "Place packets with IP Precedence set to Internet control into Q3 (network-control)";
           type empty;
         }
       }
       container protocol {
         description "Settings for specific host outbound protocol packets";
         uses apply-advanced;
         container isis-over-gre {
           description "Settings for ISIS over GRE packets";
           uses apply-advanced;
           leaf dscp-code-point {
             description "Static DSCP code point of egress host traffic";
             type string {
             }
           }
         }
       }
     }
     list drop-profiles {
       key name;
       description "Random Early Drop (RED) data point map";
       leaf name {
         description "Drop profile name";
         type string {
           length "1 .. 64";
         }
       }
       uses apply-advanced;
       list fill-level {
         key name;
         description "Fill-level value of data point";
         leaf name {
           description "Percentage the queue is full";
           type union {
             type string {
               pattern "<.*>|$.*";
             }
             type uint32 {
               range "0 .. 100";
             }
           }
         }
         leaf drop-probability {
           description "Probability packet will be dropped";
           type union {
             type string {
               pattern "<.*>|$.*";
             }
             type uint32 {
               range "0 .. 100";
             }
           }
         }
       }
       container interpolate {
         description "Data points interpolated";
         uses apply-advanced;
         leaf-list fill-level {
           ordered-by user;
           description "Data points for queue full percentage";
           type union {
             type string {
               pattern "<.*>|$.*";
             }
             type uint32 {
               range "0 .. 100";
             }
           }
         }
         leaf-list drop-probability {
           ordered-by user;
           description "Data points for packet drop probability";
           type union {
             type string {
               pattern "<.*>|$.*";
             }
             type uint32 {
               range "0 .. 100";
             }
           }
         }
       }
     }
     leaf tri-color {
       description "Enable tricolor marking";
       type empty;
     }
     container shared-buffer {
       description "Shared buffer configuration";
       uses apply-advanced;
       leaf percent {
         description "Percentage of shared buffer to be used";
         type union {
           type string {
             pattern "<.*>|$.*";
           }
           type uint32 {
             range "5 .. 100";
           }
         }
       }
     }
     container forwarding-classes {
       description "One or more mappings of forwarding class to queue number";
       uses apply-advanced;
       list class {
         key name;
         ordered-by user;
         description "Forwarding class to map to queue number";
         max-elements 16;
         leaf name {
           description "Name of forwarding class";
           type string {
             length "1 .. 64";
           }
         }
         leaf queue-num {
           description "Queue number";
           type union {
             type string {
               pattern "<.*>|$.*";
             }
             type uint32;
           }
           mandatory true;
         }
         leaf priority {
           description "Fabric priority";
           type enumeration {
             enum "low" {
               description "Low fabric priority";
             }
             enum "high" {
               description "High fabric priority";
             }
           }
         }
       }
       list queue {
         key name;
         ordered-by user;
         description "Queue number to map to forwarding class";
         leaf name {
           description "Queue number";
           type union {
             type string {
               pattern "<.*>|$.*";
             }
             type uint32;
           }
         }
         leaf class-name {
           description "Forwarding class name";
           type string {
             length "1 .. 64";
           }
           mandatory true;
         }
         leaf priority {
           description "Fabric priority";
           type enumeration {
             enum "low" {
               description "Fabric priority low";
             }
             enum "high" {
               description "Fabric priority high";
             }
           }
         }
       }
     }
     container restricted-queues {
       description "Map forwarding classes to restricted queues";
       uses apply-advanced;
       list forwarding-class {
         key name;
         description "Forwarding class to map to a restricted queue";
         leaf name {
           description "Forwarding class name";
           type string {
             length "1 .. 64";
           }
           mandatory true;
         }
         leaf rqueue-num {
           description "Restricted queue number";
           type union {
             type string {
               pattern "<.*>|$.*";
             }
             type uint32 {
               range "0 .. 3";
             }
           }
         }
       }
     }
     list traffic-control-profiles {
       key name;
       description "Traffic shaping and scheduling profiles";
       leaf name {
         description "Traffic control profile name";
         type string {
           length "1 .. 64";
         }
       }
       uses apply-advanced;
       leaf scheduler-map {
         description "Mapping of forwarding classes to packet schedulers";
         type string {
           length "1 .. 64";
         }
       }
       container shaping-rate {
         description "Shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container overhead-accounting {
         description "Overhead accounting";
         leaf mode {
           type string {
             length "1 .. 64";
           }
         }
         leaf bytes {
           description "Byte adjust value";
           type union {
             type string {
               pattern "<.*>|$.*";
             }
             type int32;
           }
         }
         leaf frame-mode-bytes {
           description "Overhead bytes when in frame-mode";
           type union {
             type string {
               pattern "<.*>|$.*";
             }
             type int32 {
               range "-120 .. 124";
             }
           }
         }
         leaf cell-mode-bytes {
           description "Overhead bytes when in cell-mode";
           type union {
             type string {
               pattern "<.*>|$.*";
             }
             type int32 {
               range "-120 .. 124";
             }
           }
         }
       }
       container guaranteed-rate {
         description "Guaranteed rate";
         choice guaranteed_rate_choice {
           case case_1 {
             leaf rate {
               description "Guaranteed rate as an absolute rate";
               units "bits per second";
               type string;
             }
           }
           case case_2 {
             leaf percent {
               description "Guaranteed rate as a percentage";
               type union {
                 type string {
                   pattern "<.*>|$.*";
                 }
                 type uint32 {
                   range "1 .. 100";
                 }
               }
             }
           }
         }
         leaf burst-size {
           description "Guaranteed rate burst size";
           units "bytes";
           type string;
         }
       }
       choice delay_buffer_sizing {
         case case_1 {
           container delay-buffer-rate {
             description "Delay buffer rate";
             choice delay_buffer_rate_choice {
               case case_1 {
                 leaf rate {
                   description "Delay buffer rate as an absolute rate";
                   units "bits per second";
                   type string;
                 }
               }
               case case_2 {
                 leaf percent {
                   description "Delay buffer rate as a percentage";
                   type union {
                     type string {
                       pattern "<.*>|$.*";
                     }
                     type uint32 {
                       range "1 .. 100";
                     }
                   }
                 }
               }
               case case_3 {
                 leaf cps {
                   description "Delay buffer rate as an absolute cells per second rate";
                   units "cells per second";
                   type string;
                 }
               }
             }
           }
         }
       }
       container adjust-minimum {
         description "Minimum shaping-rate when adjusted";
         leaf rate {
           description "Minimum shaping rate in bits per second";
           units "bits per second";
           type string;
         }
       }
     }
     list congestion-notification-profile {
       key name;
       description "Congestion notification profile";
       leaf name {
         description "Congestion notification name";
         type string {
           length "1 .. 64";
         }
       }
       uses apply-advanced;
       container input {
         description "Input congestion notification components";
         uses apply-advanced;
         container ieee-802.1 {
           description "IEEE 802.1 code point";
           uses apply-advanced;
           list code-point {
             key name;
             description "IEEE 802.1 code point";
             max-elements 8;
             leaf name {
               description "IEEE 802.1 code point";
               type string {
               }
               mandatory true;
             }
             uses apply-advanced;
             leaf pfc {
               description "PFC";
               type empty;
             }
             choice qfc-control {
               case case_1 {
               }
               case case_2 {
                 container qcn {
                   presence "enable qcn";
                   description "QCN";
                   uses apply-advanced;
                   container defense-mode-edge {
                     description "Choose the defense mode edge";
                     uses apply-advanced;
                     container alternate-priority {
                       description "Choose the alternate priority for defense mode edge";
                       uses apply-advanced;
                       leaf bits {
                         description "IEEE 802.1 code point";
                         type string {
                         }
                         mandatory true;
                       }
                     }
                   }
                 }
               }
             }
           }
         }
       }
       container output {
         description "Output congestion notification components";
         uses apply-advanced;
         list class {
           key name;
           description "Forwarding class";
           max-elements 16;
           leaf name {
             description "Class name";
             type string {
               length "1 .. 64";
             }
           }
           uses apply-advanced;
           leaf remove-cntag {
             description "Remove cntag for this forwarding class";
             type empty;
           }
         }
       }
     }
     container interfaces {
       description "Apply class-of-service options to interfaces";
       uses apply-advanced;
       list interface {
         key name;
         uses cos_interfaces_type;
       }
     }
     list routing-instances {
       key name;
       description "Apply CoS options to routing instances with VRF table label";
       leaf name {
         description "Routing instance name (or wildcard)";
         type string {
         }
       }
       uses apply-advanced;
       container classifiers {
         description "Classifiers applied to incoming packets";
         uses apply-advanced;
         leaf no-default {
           description "Do not apply default classifiers to this interface";
           type empty;
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
             mandatory true;
           }
           leaf encapsulated {
             description "Inner or outer ethernet header";
             type empty;
             mandatory true;
           }
           leaf vlan-tag {
             description "VLAN tag used for classification";
             type enumeration {
               enum "outer" {
                 description "Classification based on outer VLAN tag";
               }
               enum "inner" {
                 description "Classification based on inner VLAN tag";
               }
             }
           }
         }
         container dscp {
           description "Differentiated Services code point classifier";
           leaf classifier-name {
             description "Name of classifier to be applied";
             type union {
               type string {
                 pattern "default";
               }
               type string {
                 length "1 .. 64";
               }
             }
           }
         }
         container dscp-ipv6 {
           description "Differentiated Services code point classifier IPv6";
           leaf classifier-name {
             description "Name of classifier to be applied";
             type union {
               type string {
                 pattern "default";
               }
               type string {
                 length "1 .. 64";
               }
             }
           }
         }
       }
       container rewrite-rules {
         description "Rewrite rules applied to outgoing packets";
         uses apply-advanced;
         choice _802_rewrites {
           case case_1 {
             container ieee-802.1 {
               description "IEEE-802.1 rewrite rule";
               leaf rewrite-rule-name {
                 description "Name of rewrite rule to be applied";
                 type union {
                   type string {
                     pattern "default";
                   }
                   type string {
                     length "1 .. 64";
                   }
                 }
                 mandatory true;
               }
               leaf encapsulated {
                 description "Inner ethernet header";
                 type empty;
                 mandatory true;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
           case case_2 {
             container ieee-802.1ad {
               description "IEEE-802.1ad (DEI) rewrite rule";
               leaf rewrite-rule-name {
                 description "Name of rewrite rule to be applied";
                 type union {
                   type string {
                     pattern "default";
                   }
                   type string {
                     length "1 .. 64";
                   }
                 }
                 mandatory true;
               }
               leaf encapsulated {
                 description "Inner ethernet header";
                 type empty;
                 mandatory true;
               }
               leaf vlan-tag {
                 description "One or more VLAN tags to which rewrite rule applies";
                 type enumeration {
                   enum "outer" {
                     description "Rewrite rule applies to outer VLAN tag";
                   }
                   enum "outer-and-inner" {
                     description "Rewrite rule applies to outer and inner VLAN tag";
                   }
                 }
               }
             }
           }
         }
       }
     }
     container rewrite-rules {
       description "Write code point value of outgoing packets";
       uses apply-advanced;
       list dscp {
         key name;
         ordered-by user;
         description "Differentiated Services code point rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
       list dscp-ipv6 {
         key name;
         ordered-by user;
         description "Differentiated Services code point rewrite rule IPv6";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
       list exp {
         key name;
         ordered-by user;
         description "MPLS EXP rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
       list ieee-802.1 {
         key name;
         ordered-by user;
         description "IEEE-802.1 rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
       list inet-precedence {
         key name;
         ordered-by user;
         description "IPv4 precedence rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
       list ieee-802.1ad {
         key name;
         ordered-by user;
         description "IEEE-802.1ad (DEI) rewrite rule";
         leaf name {
           description "Rewrite rule name";
           type string {
             length "1 .. 64";
           }
         }
         uses apply-advanced;
         leaf import {
           description "Include this rewrite rule in this definition";
           type union {
             type string {
               pattern "default";
             }
             type string {
               length "1 .. 64";
             }
           }
         }
         list forwarding-class {
           key name;
           description "Markings for named forwarding class";
           leaf name {
             description "Forwarding class name";
             type string {
               length "1 .. 64";
             }
           }
           uses apply-advanced;
           list loss-priority {
             key name;
             description "Code point marking based on loss priority";
             leaf name {
               type enumeration {
                 enum "low" {
                   description "Marking when loss priority is low";
                 }
                 enum "high" {
                   description "Marking when loss priority is high";
                 }
                 enum "medium-low" {
                   description "Marking when loss priority is medium-low";
                 }
                 enum "medium-high" {
                   description "Marking when loss priority is medium-high";
                 }
               }
             }
             leaf code-point {
               description "Code point aliases or bit string";
               type string {
               }
               mandatory true;
             }
           }
         }
       }
     }
     container fabric {
       description "Define CoS parameters of switch fabric";
       uses apply-advanced;
       container scheduler-map {
         description "Mapping of fabric traffic to packet schedulers";
         uses apply-advanced;
         list priority {
           key name;
           description "Fabric traffic priority";
           leaf name {
             type enumeration {
               enum "low" {
                 description "Low priority fabric traffic";
               }
               enum "high" {
                 description "High priority fabric traffic";
               }
             }
           }
           leaf scheduler {
             description "Scheduler name";
             type string {
               length "1 .. 64";
             }
             mandatory true;
           }
         }
       }
     }
     list scheduler-maps {
       key name;
       description "Mapping of forwarding classes to packet schedulers";
       leaf name {
         description "Scheduler map name";
         type string {
           length "1 .. 64";
         }
       }
       uses apply-advanced;
       list forwarding-class {
         key name;
         description "Forwarding class name to map to scheduler";
         leaf name {
           description "Forwarding class name";
           type string {
             length "1 .. 64";
           }
         }
         leaf scheduler {
           description "Scheduler name";
           type string {
             length "1 .. 64";
           }
           mandatory true;
         }
       }
     }
     list fragmentation-maps {
       key name;
       description "Mapping of forwarding class to fragmentation options";
       leaf name {
         description "Fragmentation map name";
         type string {
           length "1 .. 64";
         }
       }
       uses apply-advanced;
       list forwarding-class {
         key name;
         description "Forwarding class name to map to fragmentation options";
         leaf name {
           description "Forwarding class name";
           type string {
             length "1 .. 64";
           }
         }
         uses apply-advanced;
         choice fragmentation-control {
           case case_1 {
             leaf fragment-threshold {
               description "Fragmentation threshold";
               units "bytes";
               type union {
                 type string {
                   pattern "<.*>|$.*";
                 }
                 type uint16 {
                   range "64 .. 9192";
                 }
               }
             }
           }
           case case_2 {
             leaf no-fragmentation {
               description "Don't allow fragmentation";
               type empty;
             }
           }
         }
         leaf multilink-class {
           description "Multilink-Class assigned to the forwarding class";
           type union {
             type string {
               pattern "<.*>|$.*";
             }
             type uint16 {
               range "0 .. 7";
             }
           }
         }
         leaf drop-timeout {
           description "Drop timeout";
           units "milliseconds";
           type union {
             type string {
               pattern "<.*>|$.*";
             }
             type uint16 {
               range "0 .. 2000";
             }
           }
         }
       }
     }
     list schedulers {
       key name;
       description "Packet schedulers";
       leaf name {
         description "Scheduler name";
         type string {
           length "1 .. 64";
         }
       }
       uses apply-advanced;
       container transmit-rate {
         description "Transmit rate";
         uses apply-advanced;
         choice transmit_rate_choice {
           case case_1 {
             leaf rate {
               description "Transmit rate as rate";
               units "bits per second";
               type string;
             }
           }
           case case_2 {
           }
           case case_3 {
             container remainder {
               presence "enable remainder";
               description "Remainder available";
               uses apply-advanced;
               leaf percent {
                 default "0";
                 type union {
                   type string {
                     pattern "<.*>|$.*";
                   }
                   type uint32 {
                     range "0 .. 100";
                   }
                 }
               }
             }
           }
         }
         choice rate_limit_choice {
           case case_1 {
             leaf exact {
               description "Enforce exact transmit rate";
               type empty;
             }
           }
           case case_2 {
             leaf rate-limit {
               description "Enforce rate limit that uses policer";
               type empty;
             }
           }
         }
       }
       container excess-rate {
         description "Excess bandwidth sharing proportion";
         choice excess_rate_choice {
           case case_1 {
             leaf proportion {
               description "Excess rate as a proportion";
               type union {
                 type string {
                   pattern "<.*>|$.*";
                 }
                 type uint32 {
                   range "0 .. 1000";
                 }
               }
             }
           }
           case case_2 {
             leaf percent {
               description "Excess rate as a percentage";
               type union {
                 type string {
                   pattern "<.*>|$.*";
                 }
                 type uint32 {
                   range "1 .. 100";
                 }
               }
             }
           }
         }
       }
       container shaping-rate {
         description "Shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "1 .. 100";
                 }
               }
             }
           }
         }
         leaf burst-size {
           description "Shaping rate burst size";
           units "bytes";
           type string;
         }
       }
       container buffer-size {
         description "Queue transmission buffer size";
         uses apply-advanced;
         choice buffer_size_choice {
           case case_1 {
             leaf percent {
               description "Buffer size as a percentage";
               type union {
                 type string {
                   pattern "<.*>|$.*";
                 }
                 type uint32 {
                   range "0 .. 100";
                 }
               }
             }
           }
           case case_2 {
             container remainder {
               presence "enable remainder";
               description "Remainder of buffer size available";
               uses apply-advanced;
               leaf percent {
                 default "0";
                 type union {
                   type string {
                     pattern "<.*>|$.*";
                   }
                   type uint32 {
                     range "0 .. 100";
                   }
                 }
               }
             }
           }
           case case_3 {
           }
           case case_4 {
             leaf temporal {
               description "Buffer size as temporal value";
               units "microseconds";
               type string;
             }
           }
           case case_5 {
           }
         }
         choice buffer_limit {
           case case_1 {
             leaf exact {
               description "Enforce exact buffer size";
               type empty;
             }
           }
         }
         container buffer-partition {
           presence "enable buffer-partition";
           description "Partition buffer size among multicast and unicast";
           uses apply-advanced;
           container multicast {
             presence "enable multicast";
             description "Specify multicast fraction of reserved buffer";
             uses apply-advanced;
             leaf percent {
               default "50";
               type union {
                 type string {
                   pattern "<.*>|$.*";
                 }
                 type uint32 {
                   range "0 .. 100";
                 }
               }
             }
           }
         }
       }
       container shared-buffer {
         description "Queue transmission shared-buffer";
         uses apply-advanced;
         container maximum {
           presence "enable maximum";
           description "Control the amount of shared buffer a given queue can consume";
           uses apply-advanced;
           leaf percent {
             description "Maximum shared buffer size as a percentage";
             default "0";
             type union {
               type string {
                 pattern "<.*>|$.*";
               }
               type uint32 {
                 range "0 .. 100";
               }
             }
           }
           container multicast {
             presence "enable multicast";
             description "Control the amount of shared buffer mcast pkts consume";
             uses apply-advanced;
             leaf percent {
               description "Maximum shared buffer size as a percentage";
               default "0";
               type union {
                 type string {
                   pattern "<.*>|$.*";
                 }
                 type uint32 {
                   range "0 .. 100";
                 }
               }
             }
           }
         }
       }
       leaf priority {
         description "Scheduling priority";
         type string {
           length "1 .. 64";
         }
       }
       leaf excess-priority {
         description "Priority in the excess region";
         type string {
           length "1 .. 64";
         }
       }
       list drop-profile-map {
         key "loss-priority protocol";
         description "Assign drop profile to a loss priority and protocol";
         leaf loss-priority {
           description "Loss priority value";
           type enumeration {
             enum "low" {
               description "Loss priority low";
             }
             enum "high" {
               description "Loss priority high";
             }
             enum "medium-low" {
               description "Loss priority medium-low";
             }
             enum "medium-high" {
               description "Loss priority medium-high";
             }
             enum "any" {
               description "Ignore loss priority when assigning drop profile";
             }
           }
         }
         leaf protocol {
           description "Protocol type";
           type enumeration {
             enum "tcp" {
               description "TCP protocol only";
             }
             enum "non-tcp" {
               description "Non-TCP protocols only";
             }
             enum "any" {
               description "Ignore protocol type when assigning drop profile";
             }
           }
         }
         leaf drop-profile {
           description "Name of drop profile to apply";
           type string {
             length "1 .. 64";
           }
           mandatory true;
         }
       }
       leaf adjust-percent {
         description "Percent of a bandwidth adjustment applied to a queue";
         units "percent";
         type union {
           type string {
             pattern "<.*>|$.*";
           }
           type uint32 {
             range "0 .. 100";
           }
         }
       }
       leaf adjust-minimum {
         description "Minimum shaping-rate when adjusted";
         units "bits per second";
         type string;
       }
     }
     container traceoptions {
       description "Trace options for class-of-service process";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace configuration processing";
             }
             enum "util" {
               description "Trace utilities";
             }
             enum "restart" {
               description "Trace restart processing";
             }
             enum "snmp" {
               description "Trace SNMP-related processing";
             }
             enum "hardware-database" {
               description "Trace chassis hardware database related processing";
             }
             enum "asynch" {
               description "Trace asynchronous configuration processing";
             }
             enum "dynamic" {
               description "Trace dynamic CoS functions";
             }
             enum "cos-adjustment" {
               description "Trace CoS rate adjustments";
             }
             enum "performance-monitor" {
               description "Trace performance monitor counters";
             }
             enum "chassis-scheduler" {
               description "Trace chassis stream scheduler processing";
             }
             enum "cn-util" {
               description "Trace utilities for congestion-notification";
             }
             enum "snmp-timeouts" {
               description "Trace SNMP COSD kernel timeouts";
             }
             enum "all" {
               description "Trace everything";
             }
             enum "feature-capability" {
               description "Trace feature capability";
             }
             enum "application" {
               description "Trace Junos application programming";
             }
             enum "jvision" {
               description "Cos Junos Jvision traces";
             }
             enum "uidebug" {
               description "Cos Junos UIDebug messages";
             }
           }
         }
       }
     }
     container multi-destination {
       description "Multicast class of service";
       uses apply-advanced;
       leaf scheduler-map {
         description "Scheduler map for multi destination";
         type string {
           length "1 .. 64";
         }
       }
       container family {
         description "Family Inet/Inet6/Ethernet";
         uses apply-advanced;
         container ethernet {
           description "Ethernet switching options";
           uses apply-advanced;
           leaf broadcast {
             description "Forwarding class to be applied to broadcast";
             type string {
               length "1 .. 64";
             }
           }
         }
         container inet {
           description "IP Multicast";
           uses apply-advanced;
           container classifier {
             description "Classifier applied to ip-multicast";
             uses apply-advanced;
             container dscp {
               description "Differentiated Services code point classifier";
               leaf classifier-name {
                 description "Name of classifier to be applied";
                 type string {
                   length "1 .. 64";
                 }
               }
             }
             container inet-precedence {
               description "IPv4 precedence classifier";
               leaf classifier-name {
                 description "Name of classifier to be applied";
                 type string {
                   length "1 .. 64";
                 }
               }
             }
           }
         }
         container inet6 {
           description "IPv6 Multicast";
           uses apply-advanced;
           container classifier {
             description "Classifier applied to ipv6-multicast";
             uses apply-advanced;
             container dscp-ipv6 {
               description "Differentiated Services code point classifier";
               leaf classifier-name {
                 description "Name of classifier to be applied";
                 type string {
                   length "1 .. 64";
                 }
               }
             }
           }
         }
       }
       container classifiers {
         description "Classifier applied to multicast traffic";
         uses apply-advanced;
         container ieee-802.1 {
           description "IEEE-802.1 classifier";
           leaf classifier-name {
             description "Name of classifier to be applied";
             type string {
               length "1 .. 64";
             }
           }
         }
         container dscp {
           description "Differentiated services code point classifier";
           leaf classifier-name {
             description "Name of classifier to be applied";
             type string {
               length "1 .. 64";
             }
           }
         }
       }
     }
     container forwarding-policy {
       description "Class-of-service forwarding policy";
       uses apply-advanced;
       list next-hop-map {
         key name;
         ordered-by user;
         description "Class-of-service next-hop map";
         leaf name {
           description "Name to identify next-hop map";
           type string {
           }
         }
         uses apply-advanced;
         list forwarding-class {
           key name;
           ordered-by user;
           description "Forwarding class from which to map";
           leaf name {
             description "Forwarding class";
             type string {
             }
           }
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list color {
               key name;
               ordered-by user;
               description "Transport class color";
               leaf name {
                 description "Transport class color";
                 type union {
                   type uint32;
                   type string {
                     pattern "<.*>|$.*";
                   }
                 }
               }
               uses apply-advanced;
             }
           }
         }
         container forwarding-class-default {
           description "Next Hop For traffic which does not meet any FC in the next-hop-map";
           uses apply-advanced;
           leaf-list next-hop {
             ordered-by user;
             description "Next-hop identifier to which to map";
             type union {
               type jt:ipaddr-or-interface;
               type string {
                 pattern "<.*>|$.*";
               }
             }
           }
           leaf-list lsp-next-hop {
             ordered-by user;
             description "Regular expression for LSP next hop";
             type string;
           }
           leaf non-lsp-next-hop {
             description "Any non-RSVP LSP next hop";
             type empty;
           }
           leaf non-labelled-next-hop {
             description "Any non-labelled next hop";
             type empty;
           }
           leaf discard {
             description "Discard next hop";
             type empty;
           }
           container transport-class {
             description "Transport class to be mapped with forwarding class";
             uses apply-advanced;
             list name {
               key name;
               ordered-by user;
               description "Transport class name";
               leaf name {
                 description "Transport class name";
                 type string;
               }
               uses apply-advanced;
             }
             list color {
               key name;
               ordered-by user;
               description "Transport class color";
               leaf name {
                 description "Transport class color";
                 type union {
                   type uint32;
                   type string {
                     pattern "<.*>|$.*";
                   }
                 }
               }
               uses apply-advanced;
             }
           }
         }
       }
       list class {
         key name;
         ordered-by user;
         description "Class-of-service description";
         leaf name {
           description "Name to identify class of service";
           type string {
           }
         }
         uses apply-advanced;
         container classification-override {
           description "Define classification overrides";
           uses apply-advanced;
           leaf forwarding-class {
             description "Forwarding class name";
             type string {
             }
           }
         }
       }
     }
   }
   grouping cos_interfaces_type {
     description "Physical interface";
     leaf name {
       description "Interface name (or wildcard)";
       type union {
         type jt:interface-device-wildcard;
         type string {
           pattern "<.*>|$.*";
         }
       }
     }
     uses apply-advanced;
     leaf congestion-notification-profile {
       description "Congestion notification profile for the interface";
       type string {
         length "1 .. 64";
       }
     }
     leaf scheduler-map {
       description "Output scheduler map";
       type string {
         length "1 .. 64";
       }
     }
     leaf input-scheduler-map {
       description "Input scheduler map";
       type string {
         length "1 .. 64";
       }
     }
     leaf scheduler-map-chassis {
       description "Scheduler map applied to chassis queues (not PIC queues)";
       type union {
         type string {
           pattern "derived";
         }
         type string {
           length "1 .. 64";
         }
       }
     }
     container shaping-rate {
       description "Output shaping rate";
       leaf rate {
         description "Shaping rate as an absolute rate";
         units "bits per second";
         type string;
       }
     }
     container input-shaping-rate {
       description "Input shaping rate";
       leaf rate {
         description "Input shaping rate as an absolute rate";
         units "bits per second";
         type string;
         mandatory true;
       }
     }
     container input-traffic-control-profile {
       description "Input traffic control profile";
       leaf profile-name {
         description "Name of the traffic control profile";
         type string {
           length "1 .. 64";
         }
         mandatory true;
       }
     }
     container input-traffic-control-profile-remaining {
       description "Input traffic control profile for remaining traffic on the ifd";
       leaf profile-name {
         description "Name of the traffic control profile";
         type string {
           length "1 .. 64";
         }
         mandatory true;
       }
     }
     container monitoring-profile {
       description "Monitoring profile";
       leaf profile-name {
         description "Name of the monitoring profile";
         type string {
           length "1 .. 64";
         }
         mandatory true;
       }
     }
     container member-link-scheduler {
       description "Scheduler parameter model for member link";
       choice model {
         case case_1 {
           leaf scale {
             description "Scale scheduler parameters on aggregate interface";
             type empty;
           }
         }
         case case_2 {
           leaf replicate {
             description "Copy scheduler parameters from aggregate interface";
             type empty;
           }
         }
       }
     }
     container exclude-queue-overhead-bytes {
       presence "enable exclude-queue-overhead-bytes";
       description "Exclude the overhead bytes from the queue statistics";
       uses apply-advanced;
       leaf include-hierarchy {
         description "Perform overhead adjustment on IFD and all children";
         type empty;
       }
     }
     container logical-interface-aggregate-statistics {
       presence "enable logical-interface-aggregate-statistics";
       description "Logical interface aggregate queue statistics";
     }
     list unit {
       key name;
       description "Logical interface unit (or wildcard)";
       leaf name {
         description "Logical unit number";
         type union {
           type string {
             pattern "\*";
           }
           type union {
             type string {
               pattern "<.*>|$.*";
             }
             type uint32 {
               range "0 .. 1073741823";
             }
           }
         }
       }
       uses apply-advanced;
       leaf service-accounting {
         description "Cos service accounting";
         type empty;
       }
       leaf forwarding-class {
         description "Forwarding class assigned to incoming packets";
         type string {
           length "1 .. 64";
         }
       }
       leaf scheduler-map {
         description "Output scheduler map";
         type string {
           length "1 .. 64";
         }
       }
       leaf input-scheduler-map {
         description "Input scheduler map";
         type string {
           length "1 .. 64";
         }
       }
       leaf fragmentation-map {
         description "Fragmentation map applied to this logical interface";
         type string {
           length "1 .. 64";
         }
       }
       container shaping-rate {
         presence "enable shaping-rate";
         description "Output shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-shaping-rate {
         description "Input shaping rate";
         choice shaping_rate_choice {
           case case_1 {
             leaf rate {
               description "Shaping rate as an absolute rate";
               units "bits per second";
               type string;
             }
           }
           case case_2 {
             leaf percent {
               description "Shaping rate as a percentage";
               type union {
                 type string {
                   pattern "<.*>|$.*";
                 }
                 type uint32 {
                   range "0 .. 100";
                 }
               }
             }
           }
         }
       }
       container input-traffic-control-profile {
         description "Input traffic control profile";
         leaf profile-name {
           description "Name of traffic control profile";
           type string {
             length "1 .. 64";
           }
           mandatory true;
         }
         leaf shared-instance {
           description "Name of the shared instance";
           type string {
             length "1 .. 64";
           }
         }
       }
       container output-traffic-control-profile {
         description "Output traffic control profile";
         leaf profile-name {
           description "Name of the traffic control profile";
           type string {
             length "1 .. 64";
           }
           mandatory true;
         }
         leaf shared-instance {
           description "Name of the shared instance";
           type string {
             length "1 .. 64";
           }
         }
       }
       container report-ingress-shaping-rate {
         description "Report ingress shaping rate";
         choice report_ingress_shaping_rate_choice {
           case case_1 {
             leaf rate {
               description "Ingress shaping rate as an absolute value";
               units "bits per second";
               type string;
             }
           }
         }
       }
       container classifiers {
         description "Classifiers applied to incoming packets";
         uses apply-advanced;
         leaf no-default {
           description "Do not apply default classifiers to this interface";
           type empty;
         }
         list dscp {
           key name;
           description "Differentiated Services code point classifier";
           leaf name {
             description "Name of classifier to be applied";
             type union {
               type string {
                 pattern "default";
               }
               type string {
                 length "1 .. 64";
               }
             }
           }
           uses apply-advanced;
           leaf-list family {
             ordered-by user;
             description "Family for DSCP classifier";
             type string;
           }
         }
         list dscp-ipv6 {
           key name;
           description "Differentiated Services code point classifier IPv6";
           leaf name {
             description "Name of classifier to be applied";
             type union {
               type string {
                 pattern "default";
               }
               type string {
                 length "1 .. 64";
               }
             }
           }
           uses apply-advanced;
           leaf-list family {
             ordered-by user;
             description "Family for DSCP Ipv6 classifier";
             type string;
           }
         }
         container exp {
           description "EXP classifier";
           leaf classifier-name {
             description "Name of classifier to be applied";
             type union {
               type string {
                 pattern "default";
               }
               type string {
                 length "1 .. 64";
               }
             }
           }
         }
         container ieee-802.1 {
           description "IEEE-802.1 classifier";
           leaf classifier-name {
             description "Name of classifier to be applied";
             type union {
               type string {
                 pattern "default";
               }
               type string {
                 length "1 .. 64";
               }
             }
             mandatory true;
           }
           leaf vlan-tag {
             description "VLAN tag used for classification";
             type enumeration {
               enum "outer" {
                 description "Classification based on outer VLAN tag";
               }
               enum "inner" {
                 description "Classification based on inner VLAN tag";
               }
               enum "transparent" {
                 description "Classification based on hidden VLAN tag";
               }
             }
           }
         }
         container inet-precedence {
           description "IPv4 precedence classifier";
           leaf classifier-name {
             description "Name of classifier to be applied";
             type union {
               type string {
                 pattern "default";
               }
               type string {
                 length "1 .. 64";
               }
             }
           }
         }
         container ieee-802.1ad {
           description "IEEE-802.1ad (DEI) classifier";
           leaf classifier-name {
             description "Name of classifier to be applied";
             type union {
               type string {
                 pattern "default";
               }
               type string {
                 length "1 .. 64";
               }
             }
             mandatory true;
           }
           leaf vlan-tag {
             description "VLAN tag used for classification";
             type enumeration {
               enum "outer" {
                 description "Classification based on outer VLAN tag";
               }
               enum "inner" {
                 description "Classification based on inner VLAN tag";
               }
             }
           }
         }
       }
       container rewrite-rules {
         description "Rewrite rules applied to outgoing packets";
         uses apply-advanced;
         list dscp {
           key name;
           description "Differentiated Services code point rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         list dscp-ipv6 {
           key name;
           description "Differentiated Services code point rewrite rule IPv6";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv6 packets entering MPLS tunnel";
               }
               enum "gtp-inet-outer" {
                 description "Apply to outer IP header";
               }
               enum "gtp-inet-both" {
                 description "Apply to both IP header";
               }
             }
           }
         }
         list exp {
           key name;
           description "EXP rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls-any" {
                 description "Apply to MPLS packets, write MPLS header only";
               }
               enum "mpls-inet-both" {
                 description "Apply to IPv4 MPLS packets, write MPLS and IPv4 header";
               }
               enum "mpls-inet-both-non-vpn" {
                 description "Apply to IPv4 MPLS packets, write MPLS and IPv4 header for only non VPN traffic";
               }
             }
           }
         }
         container ieee-802.1 {
           description "IEEE-802.1 rewrite rule";
           leaf rewrite-rule-name {
             description "Name of rewrite rule to be applied";
             type union {
               type string {
                 pattern "default";
               }
               type string {
                 length "1 .. 64";
               }
             }
             mandatory true;
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
         list inet-precedence {
           key name;
           description "IPv4 precedence rewrite rule";
           leaf name {
             description "Name of rewrite rule to be applied";
             type union {
               type string {
                 pattern "default";
               }
               type string {
                 length "1 .. 64";
               }
             }
           }
           leaf-list protocol {
             ordered-by user;
             description "Specify protocol matching criteria";
             type enumeration {
               enum "mpls" {
                 description "Apply to IPv4 packets entering MPLS tunnel";
               }
               enum "gtp-inet-outer" {
                 description "Apply to outer IP header";
               }
               enum "gtp-inet-both" {
                 description "Apply to both IP header";
               }
               enum "inet-outer" {
                 description "Apply to outer IP header";
               }
               enum "inet-both" {
                 description "Apply to both IP header";
               }
             }
           }
         }
         container ieee-802.1ad {
           description "IEEE-802.1ad (DEI) rewrite rule";
           uses apply-advanced;
           leaf rewrite-rule-name {
             description "Name of rewrite rule to be applied";
             type union {
               type string {
                 pattern "default";
               }
               type string {
                 length "1 .. 64";
               }
             }
             mandatory true;
           }
           leaf vlan-tag {
             description "One or more VLAN tags to which rewrite rule applies";
             type enumeration {
               enum "outer" {
                 description "Rewrite rule applies to outer VLAN tag";
               }
               enum "outer-and-inner" {
                 description "Rewrite rule applies to both outer and inner VLAN tags";
               }
             }
           }
         }
       }
     }
   }
   grouping juniper-def-rtb-switch-options {
     description "Bridge option configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-mac-ip-learning {
       description "Disable dynamic MAC IP address learning";
       type empty;
     }
     leaf no-normalization {
       description "Disable vlan id normalization for interfaces";
       type empty;
     }
     container port-extender {
       presence "enable port-extender";
       description "Configure port-extender";
       uses apply-advanced;
       leaf mode {
         description "Configure port-extender mode";
         type enumeration {
           enum "aggregation-device" {
             description "Aggregation Device";
           }
           enum "satellite-device" {
             description "Satellite Device";
           }
         }
       }
     }
     leaf drop-unknown-mac-ip {
       description "Drop unknown MAC-IP traffic";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     leaf ovsdb-managed {
       description "All vxlan bridge domains in routing instance are remote managed";
       type empty;
     }
     container network-isolation-profile {
       description "Network isolation configuration";
       uses apply-advanced;
       list group {
         key name;
         description "Network isolation group";
         leaf name {
           description "Group name";
           type string;
         }
         uses apply-advanced;
       }
     }
     container fabric-esi {
       description "Fabric ESI";
       uses apply-advanced;
       leaf identifier {
         description "ESI value";
         type jt:esi;
         mandatory true;
       }
       choice fabric-esi-action {
         case case_1 {
           leaf no-install-host-route {
             description "Don't install MAC-IP host route";
             type empty;
           }
         }
       }
     }
     container vtep-source-interface {
       description "Source layer-3 IFL for VXLAN";
       leaf interface-name {
         type union {
           type jt:interface-name;
           type string {
             pattern "<.*>|$.*";
           }
         }
         mandatory true;
       }
       choice family {
         case case_1 {
           container inet {
             presence "enable inet";
             description "IPv4 source";
             uses apply-advanced;
           }
         }
         case case_2 {
           container inet6 {
             presence "enable inet6";
             description "IPv6 source";
             uses apply-advanced;
           }
         }
       }
     }
     container vtep-remote-interface {
       description "Remote VTEP interface";
       uses apply-advanced;
       list remote-ip {
         key name;
         ordered-by user;
         description "Remote VTEP IP address";
         leaf name {
           description "IP address";
           type jt:ipv4addr;
         }
         uses apply-advanced;
         leaf dynamic-profile {
           description "Define associate dynamic profile";
           type string;
         }
       }
       container default {
         description "To all remote vtep interface";
         uses apply-advanced;
         leaf dynamic-profile {
           description "Define associate dynamic profile";
           type string;
         }
       }
     }
     list interface {
       key name;
       ordered-by user;
       description "Interface for configuring bridge-options";
       leaf name {
         description "Interface name";
         type union {
           type jt:interface-name;
           type string {
             pattern "<.*>|$.*";
           }
         }
       }
       uses apply-advanced;
       container mac-learning-priority {
         description "MAC learning priority for the interface";
         uses apply-advanced;
         leaf priority {
           description "Mac learning priority for the interface";
           type union {
             type string {
               pattern "<.*>|$.*";
             }
             type uint32 {
               range "1 .. 65535";
             }
           }
         }
         leaf packet-action {
           default "discard";
           type enumeration {
             enum "discard" {
               description "Discard the packets and do not learn. Default is forward";
             }
             enum "forward" {
               description "Forward the packet";
             }
           }
         }
       }
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf persistent-learning {
         description "Enable persistent MAC learning on this interface";
         type empty;
       }
       leaf no-mac-notification {
         description "Disable mac notification on this interface";
         type empty;
       }
     }
     leaf-list remote-vtep-list {
       description "Configure static remote VXLAN tunnel endpoints";
       type jt:ipaddr;
       max-elements 1024;
     }
     leaf interface-shutdown-action {
       description "Interface shutdown mode for Storm-Control/Mac-Limit/Mac-Move-limit scenario";
       type enumeration {
         enum "soft-shutdown" {
           description "Soft-shutdown restricts data-packets while control-packets are still received";
         }
         enum "hard-shutdown" {
           description "Hard-shutdown restricts all packets, port will not be operational";
         }
       }
     }
     leaf-list remote-vtep-v6-list {
       description "Configurate static IPv6 remote VXLAN tunnel endpoints";
       type jt:ipv6addr;
       max-elements 1024;
     }
     container route-distinguisher {
       description "Route distinguisher for this instance";
       leaf rd-type {
         description "Number in (16 bit:32 bit) or (32 bit 'L':16 bit) or (IP address:16 bit) format";
         type string {
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     container vrf-target {
       description "VRF target community configuration";
       uses apply-advanced;
       leaf community {
         description "Target community to use in import and export";
         type string {
         }
       }
       leaf import {
         description "Target community to use when filtering on import";
         type string {
         }
       }
       leaf export {
         description "Target community to use when marking routes on export";
         type string {
         }
       }
       container auto {
         description "Auto derive import and export target community from BGP AS & L2";
         presence "enable auto";
         uses juniper-def-rtb-auto-as;
       }
     }
     container redundant-trunk-group {
       description "Redundant trunk group";
       uses apply-advanced;
       list group {
         key name;
         ordered-by user;
         description "Name of Redundant trunk group";
         leaf name {
           description "RTG name";
           type string {
             length "1 .. 63";
           }
         }
         uses apply-advanced;
         leaf preempt-cutover-timer {
           description "Hold timer for primary interface before preempting secondary interface";
           units "seconds";
           type union {
             type string {
               pattern "<.*>|$.*";
             }
             type uint16 {
               range "1 .. 600";
             }
           }
         }
         leaf description {
           description "Text description of the RTG";
           type string {
             length "1 .. 127";
           }
         }
         list interface {
           key name;
           description "Interfaces that are part of this redundant trunk group";
           leaf name {
             description "Interface name";
             type union {
               type jt:interface-name;
               type string {
                 pattern "<.*>|$.*";
               }
             }
           }
           uses apply-advanced;
           leaf primary {
             description "Set Primary Redundant Trunk Group interface";
             type empty;
           }
         }
       }
     }
     container voip {
       description "Voice-over-IP configuration";
       uses apply-advanced;
       list interface {
         key name;
         ordered-by user;
         description "Enable voice over IP on this port";
         leaf name {
           type string;
         }
         uses apply-advanced;
         leaf vlan {
           description "VLAN for voice over IP";
           type string {
           }
           mandatory true;
         }
         leaf forwarding-class {
           description "Forwarding class";
           type string {
           }
         }
       }
     }
     container unknown-unicast-forwarding {
       description "Set interface for forwarding of unknown unicast packets";
       uses apply-advanced;
       list vlan {
         key name;
         description "VLAN for the unknown unicast packets";
         leaf name {
           description "VLAN name or VLAN Tag (1..4095)";
           type string {
           }
         }
         uses apply-advanced;
         choice packet-action {
           case case_1 {
             leaf interface {
               description "Interface to send unknown unicast packets for the VLAN";
               type union {
                 type jt:interface-name;
                 type string {
                   pattern "<.*>|$.*";
                 }
               }
             }
           }
           case case_2 {
             leaf drop {
               description "Drop unknown unicast packets in the VLAN";
               type empty;
             }
           }
         }
       }
     }
   }
   grouping juniper-def-rtb-auto-as {
     uses apply-advanced;
     list import-as {
       key name;
       description "AS to auto import for a list of VNI ids";
       leaf name {
         description "Peer autonomous system number";
         type string {
         }
       }
       uses apply-advanced;
       leaf-list vni-list {
         description "List of VNI identifiers or all";
         type string;
       }
     }
     list export-as {
       key name;
       description "AS to auto export for a list of VNI ids";
       leaf name {
         description "Peer autonomous system number";
         type string {
         }
       }
       uses apply-advanced;
       leaf-list vni-list {
         description "List of VNI identifiers or all";
         type string;
       }
     }
     list as-num {
       key name;
       description "AS to auto import and export for a list of VNI ids";
       leaf name {
         description "Peer autonomous system number";
         type string {
         }
       }
       uses apply-advanced;
       leaf-list vni-list {
         description "List of VNI identifiers or all";
         type string;
       }
     }
   }
   grouping juniper-dynamic-profile-object {
     leaf name {
       description "Name for dynamic profile";
       type string {
         length "1 .. 80";
       }
     }
     uses apply-advanced;
     leaf version-alias {
       description "Dynamic profile version alias, transmitted to RADIUS during authentication";
       type string {
         length "1 .. 63";
       }
     }
     list variables {
       key name;
       ordered-by user;
       description "Dynamic variable configuration";
       uses juniper-dynamic-variable-object;
     }
     container predefined-variable-defaults {
       description "Assign default values to predefined variables";
       uses apply-advanced;
       container aggregation-interface-set-name {
         presence "enable aggregation-interface-set-name";
         description "Default for junos-aggregation-interface-set-name";
         uses apply-advanced;
         choice def-value {
           case case_1 {
             leaf default-value {
               description "Default value for junos-aggregation-interface-set-name";
               type string;
             }
           }
           case case_2 {
             leaf equals {
               description "Computable expression of dynamic profile variables";
               type string;
             }
           }
         }
       }
       container interface-set-name {
         presence "enable interface-set-name";
         description "Default for junos-interface-set-name";
         uses apply-advanced;
         choice def-value {
           case case_1 {
             leaf default-value {
               description "Default value for junos-interface-set-name";
               type string;
             }
           }
           case case_2 {
             leaf equals {
               description "Computable expression of dynamic profile variables";
               type string;
             }
           }
         }
       }
       container default-interface-set-name {
         presence "enable default-interface-set-name";
         description "Default for junos-default-interface-set-name";
         uses apply-advanced;
         leaf equals {
           description "Computable expression of dynamic profile variables";
           type string;
         }
       }
       container phy-ifd-interface-set-name {
         presence "enable phy-ifd-interface-set-name";
         description "Default for junos-phy-ifd-interface-set-name";
         uses apply-advanced;
         choice def-value {
           case case_1 {
             leaf default-value {
               description "Default value for junos-phy-ifd-interface-set-name";
               type string;
             }
           }
           case case_2 {
             leaf equals {
               description "Computable expression of dynamic profile variables";
               type string;
             }
           }
         }
       }
       container phy-ifd-underlying-intf-set-name {
         presence "enable phy-ifd-underlying-intf-set-name";
         description "Default for junos-phy-ifd-underlying-intf-set-name";
         uses apply-advanced;
         choice def-value {
           case case_1 {
             leaf default-value {
               description "Default value for junos-phy-ifd-underlying-intf-set-name";
               type string;
             }
           }
           case case_2 {
             leaf equals {
               description "Computable expression of dynamic profile variables";
               type string;
             }
           }
         }
       }
       container cos-excess-rate {
         description "Default for junos-cos-excess-rate";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-high {
         description "Default for junos-cos-excess-rate-high";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-excess-rate-low {
         description "Default for junos-cos-excess-rate-low";
         uses apply-advanced;
         leaf proportion {
           description "Excess rate as proportion";
           type union {
             type string {
               pattern "<.*>|$.*";
             }
             type uint32 {
               range "0 .. 1000";
             }
           }
         }
         leaf percent {
           description "Excess rate as percentage";
           type union {
             type string {
               pattern "<.*>|$.*";
             }
             type uint32 {
               range "1 .. 100";
             }
           }
         }
       }
       container cos-scheduler-tx {
         description "Default for junos-cos-scheduler-tx";
         uses apply-advanced;
         leaf rate {
           description "Transmit rate as rate";
           type string;
         }
         leaf percent {
           description "Transmit rate as percentage";
           type union {
             type string {
               pattern "<.*>|$.*";
             }
             type uint32 {
               range "0 .. 100";
             }
           }
         }
       }
       container cos-scheduler-bs {
         description "Default for junos-cos-scheduler-bs";
         uses apply-advanced;
         leaf percent {
           description "Buffer size as percentage";
           type union {
             type string {
               pattern "<.*>|$.*";
             }
             type uint32 {
               range "0 .. 100";
             }
           }
         }
         leaf temporal {
           description "Buffer size as temporal";
           units "microseconds";
           type union {
             type uint32;
             type string {
               pattern "<.*>|$.*";
             }
           }
         }
       }
       container cos-scheduler-shaping-rate {
         description "Default for junos-cos-scheduler-shaping-rate";
         uses apply-advanced;
         leaf rate {
           description "Shaping rate as rate";
           units "bits per second";
           type string;
         }
         leaf percent {
           description "Shaping rate as percentage";
           type union {
             type string {
               pattern "<.*>|$.*";
             }
             type uint32 {
               range "1 .. 100";
             }
           }
         }
       }
       list other-variables {
         key name;
         ordered-by user;
         uses base-default-variable-object;
       }
     }
     container routing-instances {
       description "Routing instance configuration";
       uses apply-advanced;
       list instance {
         key name;
         ordered-by user;
         leaf name {
           type enumeration {
             enum "$junos-routing-instance" {
               description "Dynamic profile routing instance name";
             }
           }
         }
         uses apply-advanced;
         list interface {
           key name;
           description "Interface name for this routing instance";
           leaf name {
             type string;
           }
           uses apply-advanced;
           choice mode {
             case case_1 {
               leaf any {
                 description "Interface used for both unicast and multicast traffic";
                 type empty;
               }
             }
             case case_2 {
               leaf unicast {
                 description "Interface used for unicast traffic only";
                 type empty;
               }
             }
             case case_3 {
               leaf multicast {
                 description "Interface used for multicast traffic only";
                 type empty;
               }
             }
           }
           leaf primary {
             description "Preferred multicast vt interface for the routing-instance";
             type empty;
           }
           leaf protect-interface {
             description "Name of protect interface";
             type union {
               type jt:interface-name;
               type string {
                 pattern "<.*>|$.*";
               }
             }
           }
         }
         container routing-options {
           description "Protocol-independent routing option configuration";
           uses apply-advanced;
           list rib {
             key name;
             description "Routing table options";
             leaf name {
               description "Routing table name";
               type string;
             }
             uses apply-advanced;
             container static {
               description "Static routes";
               uses apply-advanced;
               leaf rib-group {
                 description "Routing table group";
                 type string;
               }
               container defaults {
                 description "Global route options";
                 uses apply-advanced;
                 choice retain-choice {
                   leaf retain {
                     description "Always keep route in forwarding table";
                     type empty;
                   }
                   leaf no-retain {
                     description "Don't always keep route in forwarding table";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   type empty;
                 }
                 choice longest-match-choice {
                   leaf longest-match {
                     description "Always use longest prefix match to resolve next hops";
                     type empty;
                   }
                   leaf no-longest-match {
                     description "Don't always use longest prefix match to resolve next hops";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
               }
               list route {
                 key name;
                 description "Static route";
                 leaf name {
                   type jt:ipprefix;
                 }
                 uses apply-advanced;
                 leaf priority {
                   description "Static route priority high/medium/low";
                   type enumeration {
                     enum "medium" {
                       description "Static route medium priority";
                     }
                     enum "low" {
                       description "Static route low priority";
                     }
                     enum "high" {
                       description "Static route high priority";
                     }
                   }
                 }
                 choice next_hop {
                   case case_1 {
                     leaf-list next-hop {
                       ordered-by user;
                       description "Next hop to destination";
                       type union {
                         type jt:ipaddr-or-interface;
                         type string {
                           pattern "<.*>|$.*";
                         }
                       }
                     }
                   }
                   case case_2 {
                     leaf reject {
                       description "Drop packets to destination; send ICMP unreachables";
                       type empty;
                     }
                   }
                   case case_3 {
                     leaf discard {
                       description "Drop packets to destination; send no ICMP unreachables";
                       type empty;
                     }
                   }
                   case case_4 {
                     leaf receive {
                       description "Install a receive route for the destination";
                       type empty;
                     }
                   }
                   case case_5 {
                     leaf next-table {
                       description "Next hop to another table";
                       type string {
                       }
                     }
                   }
                 }
                 leaf description {
                   description "Static route description";
                   type string {
                   }
                 }
                 list qualified-next-hop {
                   key name;
                   ordered-by user;
                   description "Next hop with qualifiers";
                   uses qualified_nh_obj;
                 }
                 leaf backup-pe-group {
                   description "Multicast source redundancy group";
                   type string;
                 }
                 container bfd-liveness-detection {
                   description "Bidirectional Forwarding Detection (BFD) options";
                   uses apply-advanced;
                   leaf version {
                     description "BFD protocol version number";
                     default "automatic";
                     type enumeration {
                       enum "0" {
                         description "BFD version 0 (deprecated)";
                       }
                       enum "1" {
                         description "BFD version 1";
                       }
                       enum "automatic" {
                         description "Choose BFD version automatically";
                       }
                     }
                   }
                   leaf minimum-interval {
                     description "Minimum transmit and receive interval";
                     units "milliseconds";
                     type union {
                       type string {
                         pattern "<.*>|$.*";
                       }
                       type uint32 {
                         range "1 .. 255000";
                       }
                     }
                   }
                   leaf minimum-transmit-interval {
                     description "Minimum transmit interval";
                     status deprecated;
                     units "milliseconds";
                     type union {
                       type string {
                         pattern "<.*>|$.*";
                       }
                       type uint32 {
                         range "1 .. 255000";
                       }
                     }
                   }
                   leaf minimum-receive-interval {
                     description "Minimum receive interval";
                     units "milliseconds";
                     type union {
                       type string {
                         pattern "<.*>|$.*";
                       }
                       type uint32 {
                         range "1 .. 255000";
                       }
                     }
                   }
                   leaf multiplier {
                     description "Detection time multiplier";
                     default "3";
                     type union {
                       type string {
                         pattern "<.*>|$.*";
                       }
                       type uint32 {
                         range "1 .. 255";
                       }
                     }
                   }
                   leaf inline-disable {
                     description "Disable inline mode for this BFD session";
                     type empty;
                   }
                   leaf pdu-size {
                     description "BFD transport protocol payload size";
                     default "24";
                     type union {
                       type string {
                         pattern "<.*>|$.*";
                       }
                       type uint32 {
                         range "24 .. 16000";
                       }
                     }
                   }
                   choice adaptation-choice {
                     case case_1 {
                       leaf no-adaptation {
                         description "Disable adaptation";
                         type empty;
                       }
                     }
                   }
                   container transmit-interval {
                     description "Transmit-interval options";
                     uses apply-advanced;
                     leaf minimum-interval {
                       description "Minimum transmit interval";
                       units "milliseconds";
                       type union {
                         type string {
                           pattern "<.*>|$.*";
                         }
                         type uint32 {
                           range "1 .. 255000";
                         }
                       }
                     }
                     leaf threshold {
                       description "High transmit interval triggering a trap";
                       units "milliseconds";
                       type union {
                         type uint32;
                         type string {
                           pattern "<.*>|$.*";
                         }
                       }
                     }
                   }
                   container detection-time {
                     description "Detection-time options";
                     uses apply-advanced;
                     leaf threshold {
                       description "High detection-time triggering a trap";
                       units "milliseconds";
                       type union {
                         type uint32;
                         type string {
                           pattern "<.*>|$.*";
                         }
                       }
                     }
                   }
                   container authentication {
                     description "Authentication options";
                     uses apply-advanced;
                     leaf key-chain {
                       description "Key chain name";
                       type string;
                     }
                     leaf algorithm {
                       description "Algorithm name";
                       type enumeration {
                         enum "simple-password" {
                           description "Simple password";
                         }
                         enum "keyed-md5" {
                           description "Keyed message Digest 5";
                         }
                         enum "meticulous-keyed-md5" {
                           description "Meticulous keyed message Digest 5";
                         }
                         enum "keyed-sha-1" {
                           description "Keyed secure hash algorithm (SHA1) ";
                         }
                         enum "meticulous-keyed-sha-1" {
                           description "Meticulous keyed secure hash algorithm (SHA1) ";
                         }
                       }
                     }
                     leaf loose-check {
                       description "Verify authentication only if authentication is negotiated";
                       type empty;
                     }
                   }
                   container echo {
                     description "Echo mode parameters";
                     uses apply-advanced;
                     leaf minimum-interval {
                       description "Minimum transmit and receive interval";
                       units "milliseconds";
                       type union {
                         type string {
                           pattern "<.*>|$.*";
                         }
                         type uint32 {
                           range "100 .. 255000";
                         }
                       }
                       mandatory true;
                     }
                   }
                   container echo-lite {
                     description "Echo-lite more parameters";
                     uses apply-advanced;
                     leaf minimum-interval {
                       description "Minimum transmit and receive interval";
                       units "milliseconds";
                       type union {
                         type string {
                           pattern "<.*>|$.*";
                         }
                         type uint32 {
                           range "1 .. 255000";
                         }
                       }
                       mandatory true;
                     }
                   }
                   leaf neighbor {
                     description "BFD neighbor address";
                     type jt:ipaddr;
                   }
                   leaf local-address {
                     description "BFD local address (for multihop only)";
                     type jt:ipaddr;
                   }
                   leaf holddown-interval {
                     description "Time to hold the session-UP notification to the client";
                     units "milliseconds";
                     type union {
                       type string {
                         pattern "<.*>|$.*";
                       }
                       type uint32 {
                         range "0 .. 255000";
                       }
                     }
                   }
                   leaf minimum-receive-ttl {
                     description "Minimum receive TTL below which to drop";
                     type union {
                       type string {
                         pattern "<.*>|$.*";
                       }
                       type uint8 {
                         range "1 .. 255";
                       }
                     }
                   }
                 }
                 choice retain-choice {
                   leaf retain {
                     description "Always keep route in forwarding table";
                     type empty;
                   }
                   leaf no-retain {
                     description "Don't always keep route in forwarding table";
                     type empty;
                   }
                 }
                 choice install-choice {
                   leaf install {
                     description "Install route into forwarding table";
                     type empty;
                   }
                   leaf no-install {
                     description "Don't install route into forwarding table";
                     type empty;
                   }
                 }
                 choice readvertise-choice {
                   leaf readvertise {
                     description "Mark route as eligible to be readvertised";
                     type empty;
                   }
                   leaf no-readvertise {
                     description "Don't mark route as eligible to be readvertised";
                     type empty;
                   }
                 }
                 choice resolve-choice {
                   leaf resolve {
                     description "Allow resolution of indirectly connected next hops";
                     type empty;
                   }
                   leaf no-resolve {
                     description "Don't allow resolution of indirectly connected next hops";
                     type empty;
                   }
                 }
                 leaf explicit-null {
                   description "Allows service label to be popped and will lookup nexthop-table inet6.0";
                   type empty;
                 }
                 choice longest-match-choice {
                   leaf longest-match {
                     description "Always use longest prefix match to resolve next hops";
                     type empty;
                   }
                   leaf no-longest-match {
                     description "Don't always use longest prefix match to resolve next hops";
                     type empty;
                   }
                 }
                 choice passive_flag {
                   case case_1 {
                     leaf active {
                       description "Remove inactive route from forwarding table";
                       type empty;
                     }
                   }
                   case case_2 {
                     leaf passive {
                       description "Retain inactive route in forwarding table";
                       type empty;
                     }
                   }
                 }
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
                 list lsp-next-hop {
                   key name;
                   ordered-by user;
                   description "LSP next hop";
                   uses lsp_nh_obj;
                 }
                 container spring-te-lsp-next-hop {
                   description "SPRING-TE LSP next hop";
                   uses springte_lsp_nh_obj;
                 }
                 container p2mp-ldp-next-hop {
                   description "Point-to-multipoint LDP LSP next hop";
                   uses p2mp_ldp_lsp_nh_obj;
                 }
               }
               leaf protocol-instance-name {
                 description "Name of protocol instance under routing instance";
                 type string;
               }
               container static-route {
                 description "Static route Status";
                 leaf bfd-admin-down {
                   description "Static route State on BFD ADMIN DOWN";
                   type enumeration {
                     enum "active" {
                       description "Static route will be inactive on bfd-admin-down";
                     }
                     enum "passive" {
                       description "Static route will remain active on bfd-admin-down";
                     }
                   }
                 }
               }
               list route-target-filter {
                 key name;
                 description "Route-target-filter route";
                 leaf name {
                   type string {
                     length "1 .. 47";
                   }
                 }
                 uses apply-advanced;
                 leaf autonomous-system {
                   description "BGP AS for filter, overriding global configuration";
                   type string {
                   }
                 }
                 leaf-list community {
                   ordered-by user;
                   description "BGP community identifier";
                   type jt:community;
                 }
                 leaf-list neighbor {
                   ordered-by user;
                   description "BGP peers for filter";
                   type jt:ipaddr-scoped;
                 }
                 leaf-list group {
                   ordered-by user;
                   description "BGP groups for filter";
                   type string;
                 }
                 leaf local {
                   description "Locally originated filter";
                   type empty;
                 }
               }
               list route-target-community-filter {
                 key name;
                 description "Route-target-filter communites";
                 leaf name {
                   type string;
                 }
                 uses apply-advanced;
                 leaf autonomous-system {
                   description "BGP AS for filter, overriding global configuration";
                   type string {
                   }
                 }
                 leaf-list community {
                   ordered-by user;
                   description "BGP community identifier";
                   type jt:community;
                 }
                 leaf-list neighbor {
                   ordered-by user;
                   description "BGP peers for filter";
                   type jt:ipaddr-scoped;
                 }
                 leaf-list group {
                   ordered-by user;
                   description "BGP groups for filter";
                   type string;
                 }
                 leaf local {
                   description "Locally originated filter";
                   type empty;
                 }
               }
             }
             list martians {
               key "address choice-ident choice-value";
               ordered-by user;
               description "Invalid routes";
               uses martian_type;
             }
             container aggregate {
               description "Coalesced routes";
               uses rib_aggregate_type;
             }
             container generate {
               description "Route of last resort";
               uses rib_aggregate_type;
             }
             choice maximum-paths-type {
               case case_1 {
                 container maximum-routes {
                   description "Maximum number of routes";
                   status deprecated;
                   leaf limit {
                     description "Maximum number of routes";
                     type union {
                       type string {
                         pattern "<.*>|$.*";
                       }
                       type uint32 {
                         range "1 .. 4294967295";
                       }
                     }
                     mandatory true;
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
               case case_2 {
                 container maximum-paths {
                   description "Maximum number of paths";
                   leaf limit {
                     description "Maximum number of paths";
                     type union {
                       type string {
                         pattern "<.*>|$.*";
                       }
                       type uint32 {
                         range "1 .. 4294967295";
                       }
                     }
                     mandatory true;
                   }
                   choice log_type {
                     case case_1 {
                       leaf threshold {
                         description "Percentage of limit at which to start generating warnings";
                         type union {
                           type string {
                             pattern "<.*>|$.*";
                           }
                           type uint32 {
                             range "1 .. 100";
                           }
                         }
                       }
                     }
                     case case_2 {
                       leaf log-only {
                         description "Generate warning messages only";
                         type empty;
                       }
                     }
                   }
                   leaf log-interval {
                     description "Minimum interval between log messages";
                     units "seconds";
                     type union {
                       type string {
                         pattern "<.*>|$.*";
                       }
                       type uint32 {
                         range "5 .. 86400";
                       }
                     }
                   }
                 }
               }
             }
             container maximum-prefixes {
               description "Maximum number of prefixes";
               leaf limit {
                 description "Maximum number of prefixes";
                 type union {
                   type string {
                     pattern "<.*>|$.*";
                   }
                   type uint32 {
                     range "1 .. 4294967295";
                   }
                 }
                 mandatory true;
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
             container multipath {
               presence "enable multipath";
               description "Protocol-independent load balancing";
               uses apply-advanced;
               container vpn-unequal-cost {
                 presence "enable vpn-unequal-cost";
                 description "Include VPN routes with unequal IGP metrics";
                 leaf equal-external-internal {
                   description "Include external and internal VPN routes";
                   type empty;
                 }
               }
               leaf as-path-compare {
                 description "Compare AS path sequences in addition to AS path length";
                 type empty;
               }
               leaf preserve-nexthop-hierarchy {
                 description "Force multipath to create List nexthop";
                 type empty;
               }
             }
             container policy-multipath {
               description "Policy based multipath";
               uses apply-advanced;
               leaf-list policy {
                 ordered-by user;
                 description "Import policy to create policy based multipath";
                 type jt:policy-algebra;
               }
               container traceoptions {
                 description "Trace options";
                 uses apply-advanced;
                 container file {
                   description "Trace file options";
                   leaf filename {
                     description "Name of file in which to write trace information";
                     type string {
                       length "1 .. 1024";
                     }
                     mandatory true;
                   }
                   leaf replace {
                     description "Replace trace file rather than appending to it";
                     status deprecated;
                     type empty;
                   }
                   leaf size {
                     description "Maximum trace file size";
                     type string;
                   }
                   leaf files {
                     description "Maximum number of trace files";
                     default "10";
                     type union {
                       type string {
                         pattern "<.*>|$.*";
                       }
                       type uint32 {
                         range "2 .. 1000";
                       }
                     }
                   }
                   leaf no-stamp {
                     description "Do not timestamp trace file";
                     status deprecated;
                     type empty;
                   }
                   choice world-readable-choice {
                     leaf world-readable {
                       description "Allow any user to read the log file";
                       type empty;
                     }
                     leaf no-world-readable {
                       description "Don't allow any user to read the log file";
                       type empty;
                     }
                   }
                 }
                 list flag {
                   key name;
                   ordered-by user;
                   description "Tracing parameters";
                   leaf name {
                     type enumeration {
                       enum "route" {
                         description "Policy-multipath route tracing.";
                       }
                     }
                   }
                   leaf send {
                     description "Trace transmitted packets";
                     type empty;
                   }
                   leaf receive {
                     description "Trace received packets";
                     type empty;
                   }
                   leaf detail {
                     description "Trace detailed information";
                     type empty;
                   }
                   leaf disable {
                     description "Disable this trace flag";
                     type empty;
                   }
                 }
               }
               leaf preserve-nexthop-hierarchy {
                 description "Enable preserved nexthop hierarchy";
                 type empty;
               }
             }
             container protect {
               description "Protocol-independent protection";
               leaf core {
                 description "Protect against unreachability to service-edge router";
                 type empty;
               }
             }
             container access {
               description "Access routes";
               uses apply-advanced;
               list route {
                 key name;
                 ordered-by user;
                 description "Access route";
                 leaf name {
                   description "IP address of destination";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
                 leaf metric {
                   description "Metric value";
                   type union {
                     type string {
                       pattern "<.*>|$.*";
                     }
                     type uint32 {
                       range "1 .. 255";
                     }
                   }
                 }
                 leaf preference {
                   description "Preference value";
                   type union {
                     type uint32;
                     type string {
                       pattern "<.*>|$.*";
                     }
                   }
                 }
                 leaf tag {
                   description "Tag string";
                   type union {
                     type uint32;
                     type string {
                       pattern "<.*>|$.*";
                     }
                   }
                 }
                 leaf tag2 {
                   description "Tag2 string";
                   type union {
                     type uint32;
                     type string {
                       pattern "<.*>|$.*";
                     }
                   }
                 }
               }
             }
             container access-internal {
               description "Access-internal routes";
               uses apply-advanced;
               list route {
                 key name;
                 ordered-by user;
                 description "Access-internal route";
                 leaf name {
                   description "IP address and optional prefix length of destination";
                   type jt:ipprefix;
                 }
                 uses apply-advanced;
                 leaf-list next-hop {
                   ordered-by user;
                   description "Next hop to destination";
                   type union {
                     type jt:ipaddr-or-interface;
                     type string {
                       pattern "<.*>|$.*";
                     }
                   }
                 }
                 list qualified-next-hop {
                   key name;
                   ordered-by user;
                   description "Next hop with qualifiers";
                   uses qualified_nh_obj;
                 }
               }
             }
             container bgp-static {
               description "Routes for BGP static advertisements";
               uses apply-advanced;
               list route {
                 key name;
                 ordered-by user;
                 description "BGP-static route";
                 leaf name {
                   description "IP address and optional prefix length of destination";
                   type jt:ipprefix;
                 }
                 uses apply-advanced;
                 container metric {
                   description "Metric value";
                   presence "enable metric";
                   uses rib_static_metric_type;
                 }
                 container metric2 {
                   description "Metric value 2";
                   presence "enable metric2";
                   uses rib_static_metric_type;
                 }
                 container metric3 {
                   description "Metric value 3";
                   presence "enable metric3";
                   uses rib_static_metric_type;
                 }
                 container metric4 {
                   description "Metric value 4";
                   presence "enable metric4";
                   uses rib_static_metric_type;
                 }
                 container tag {
                   description "Tag string";
                   presence "enable tag";
                   uses rib_static_metric_type;
                 }
                 container tag2 {
                   description "Tag string 2";
                   presence "enable tag2";
                   uses rib_static_metric_type;
                 }
                 container preference {
                   description "Preference value";
                   presence "enable preference";
                   uses rib_static_metric_type;
                 }
                 container preference2 {
                   description "Preference value 2";
                   presence "enable preference2";
                   uses rib_static_metric_type;
                 }
                 container color {
                   description "Color (preference) value";
                   presence "enable color";
                   uses rib_static_metric_type;
                 }
                 container color2 {
                   description "Color (preference) value 2";
                   presence "enable color2";
                   uses rib_static_metric_type;
                 }
                 leaf-list community {
                   ordered-by user;
                   description "BGP community identifier";
                   type jt:community;
                 }
                 container as-path {
                   description "Autonomous system path";
                   uses apply-advanced;
                   leaf path {
                     description "Autonomous system path";
                     type string;
                   }
                   leaf origin {
                     type enumeration {
                       enum "igp" {
                         description "Path originated in the local IGP";
                       }
                       enum "egp" {
                         description "Path originated in another AS";
                       }
                       enum "incomplete" {
                         description "Path was learned by some other means";
                       }
                     }
                   }
                   leaf atomic-aggregate {
                     description "Add ATOMIC_AGGREGATE path attribute to route";
                     type empty;
                   }
                   container aggregator {
                     presence "enable aggregator";
                     description "Add AGGREGATOR path attribute to route";
                   }
                   leaf as-number {
                     description " Autonomous system number in plain number or 'higher 16bits'.'Lower 16 bits' (asdot notation) format";
                     type string {
                     }
                   }
                   leaf address {
                     description "Address of BGP system that formed the route";
                     type jt:ipv4addr;
                   }
                 }
               }
             }
             container flow {
               description "Locally defined flow routing information";
               uses apply-advanced;
               container validation {
                 description "Flow route validation options";
                 presence "enable validation";
                 uses flow-validation;
               }
               list route {
                 key name;
                 ordered-by user;
                 description "Flow route";
                 uses flow-route-inet6;
               }
               container interface-group {
                 description "Interface-group for applying flow-spec filter";
                 uses flow-interface-group;
               }
               leaf discard-action-for-unresolved-redir-addr {
                 description "For action redirect IP if redirect address is unresolved install discard action filter";
                 type empty;
               }
               choice per-route-accounting-choice {
                 leaf per-route-accounting {
                   description "Enable traffic accounting per flowspec route";
                   type empty;
                 }
                 leaf no-per-route-accounting {
                   description "Don't enable traffic accounting per flowspec route";
                   type empty;
                 }
               }
             }
             container rib-export {
               presence "enable rib-export";
               description "Group of routing tables to import the routes";
               uses apply-advanced;
               leaf ribexport-name {
                 description "RIB export group name";
                 type string;
               }
             }
             container label {
               presence "enable label";
               description "Label processing";
               uses apply-advanced;
               leaf-list allocation {
                 ordered-by user;
                 description "Label allocation policy";
                 type jt:policy-algebra;
               }
               leaf-list substitution {
                 ordered-by user;
                 description "Label substitution policy";
                 type jt:policy-algebra;
               }
             }
             leaf-list vpn-global-import {
               ordered-by user;
               description "Import policy for L3VPN routes to global RIB";
               type jt:policy-algebra;
             }
           }
           container access {
             description "Access routes";
             uses apply-advanced;
             list route {
               key name;
               ordered-by user;
               description "Access route";
               leaf name {
                 description "IP address of destination";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
               leaf metric {
                 description "Metric value";
                 type union {
                   type string {
                     pattern "<.*>|$.*";
                   }
                   type uint32 {
                     range "1 .. 255";
                   }
                 }
               }
               leaf preference {
                 description "Preference value";
                 type union {
                   type uint32;
                   type string {
                     pattern "<.*>|$.*";
                   }
                 }
               }
               leaf tag {
                 description "Tag string";
                 type union {
                   type uint32;
                   type string {
                     pattern "<.*>|$.*";
                   }
                 }
               }
               leaf tag2 {
                 description "Tag2 string";
                 type union {
                   type uint32;
                   type string {
                     pattern "<.*>|$.*";
                   }
                 }
               }
             }
           }
           container access-internal {
             description "Access-internal routes";
             uses apply-advanced;
             list route {
               key name;
               ordered-by user;
               description "Access-internal route";
               leaf name {
                 description "IP address and optional prefix length of destination";
                 type jt:ipprefix;
               }
               uses apply-advanced;
               leaf-list next-hop {
                 ordered-by user;
                 description "Next hop to destination";
                 type union {
                   type jt:ipaddr-or-interface;
                   type string {
                     pattern "<.*>|$.*";
                   }
                 }
               }
               list qualified-next-hop {
                 key name;
                 ordered-by user;
                 description "Next hop with qualifiers";
                 uses qualified_nh_obj;
               }
             }
           }
           container multicast {
             description "Global multicast options";
             uses apply-advanced;
             container traceoptions {
               description "Global multicast trace options";
               uses apply-advanced;
               container file {
                 description "Trace file options";
                 leaf filename {
                   description "Name of file in which to write trace information";
                   type string {
                     length "1 .. 1024";
                   }
                   mandatory true;
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 description "Tracing parameters";
                 leaf name {
                   type enumeration {
                     enum "parse" {
                       description "Trace configuration parsing";
                     }
                     enum "config-internal" {
                       description "Trace configuration internals";
                     }
                     enum "route" {
                       description "Trace routing information";
                     }
                     enum "normal" {
                       description "Trace normal events";
                     }
                     enum "general" {
                       description "Trace general events";
                     }
                     enum "state" {
                       description "Trace state transitions";
                     }
                     enum "policy" {
                       description "Trace policy processing";
                     }
                     enum "task" {
                       description "Trace routing protocol task processing";
                     }
                     enum "timer" {
                       description "Trace routing protocol timer processing";
                     }
                     enum "all" {
                       description "Trace everything";
                     }
                   }
                 }
                 leaf disable {
                   description "Disable this trace flag";
                   type empty;
                 }
               }
             }
             leaf rpf {
               status deprecated;
               type string;
             }
             list scope {
               key name;
               ordered-by user;
               description "Multicast address scope";
               leaf name {
                 description "Name to identify multicast address scope";
                 type string;
               }
               uses apply-advanced;
               leaf prefix {
                 description "Administratively scoped address";
                 type jt:ipprefix;
                 mandatory true;
               }
               leaf-list interface {
                 ordered-by user;
                 description "Interface on which to configure scoping";
                 type union {
                   type jt:interface-name;
                   type string {
                     pattern "<.*>|$.*";
                   }
                 }
               }
             }
             leaf-list scope-policy {
               ordered-by user;
               description "Scoping policy";
               type jt:policy-algebra;
             }
             list flow-map {
               key name;
               ordered-by user;
               description "Multicast flow map configuration";
               leaf name {
                 description "Name of the flow map";
                 type string;
               }
               uses apply-advanced;
               leaf-list policy {
                 ordered-by user;
                 description "Policy for matched flows";
                 type jt:policy-algebra;
               }
               container bandwidth {
                 presence "enable bandwidth";
                 description "Bandwidth properties for matched flows";
                 leaf bandwidth-value {
                   description "Static or default bandwidth for the matched flows";
                   units "bps";
                   type string;
                 }
                 leaf adaptive {
                   description "Auto-sense bandwidth for matched flows";
                   type empty;
                 }
               }
               leaf-list redundant-sources {
                 ordered-by user;
                 description "Redundant source addresses";
                 type jt:ipaddr;
               }
               container forwarding-cache {
                 description "Forwarding cache properties for matched flows";
                 uses apply-advanced;
                 container timeout {
                   description "Timeout properties for matched flows";
                   choice timeout_choice {
                     case case_1 {
                       leaf timeout-value {
                         description "Timeout for forwarding cache entry";
                         units "minutes";
                         type union {
                           type string {
                             pattern "<.*>|$.*";
                           }
                           type uint32 {
                             range "1 .. 720";
                           }
                         }
                       }
                     }
                     case case_2 {
                       container never {
                         presence "enable never";
                         description "Forwarding cache entries never time out";
                         uses apply-advanced;
                         leaf non-discard-entry-only {
                           description "Apply only to non-discard entries";
                           type empty;
                         }
                       }
                     }
                   }
                 }
               }
             }
             leaf-list resolve-filter {
               ordered-by user;
               description "Multicast resolve policy filter";
               status deprecated;
               type jt:policy-algebra;
             }
             leaf-list ssm-groups {
               ordered-by user;
               description "Source-specific multicast group ranges";
               type jt:ipprefix;
             }
             leaf cont-stats-collection-interval {
               description "IGMP/MLD continuous statistics collection interval";
               default "300";
               type union {
                 type string {
                   pattern "<.*>|$.*";
                 }
                 type uint16 {
                   range "60 .. 3600";
                 }
               }
             }
             leaf asm-override-ssm {
               description "Allow ASM state for SSM group ranges";
               type empty;
             }
             leaf-list rpf-check-policy {
               ordered-by user;
               description "Disable RPF check for a source group pair";
               type jt:policy-algebra;
             }
             container pim-to-igmp-proxy {
               description "PIM-to-IGMP proxy";
               uses apply-advanced;
               leaf-list upstream-interface {
                 ordered-by user;
                 description "Upstream interface list";
                 type union {
                   type jt:interface-name;
                   type string {
                     pattern "<.*>|$.*";
                   }
                 }
                 max-elements 2;
               }
             }
             container pim-to-mld-proxy {
               description "PIM-to-MLD proxy";
               uses apply-advanced;
               leaf-list upstream-interface {
                 ordered-by user;
                 description "Upstream interface list";
                 type union {
                   type jt:interface-name;
                   type string {
                     pattern "<.*>|$.*";
                   }
                 }
                 max-elements 2;
               }
             }
             leaf resolve-request-holdcount {
               description "Set resolve request holdcount for multicast";
               type union {
                 type string {
                   pattern "<.*>|$.*";
                 }
                 type uint32 {
                   range "0 .. 256";
                 }
               }
             }
             container forwarding-cache {
               description "Multicast forwarding cache";
               uses apply-advanced;
               leaf allow-maximum {
                 description "Allow maximum of global and family level threshold values for suppress and reuse";
                 type empty;
               }
               list family {
                 key name;
                 ordered-by user;
                 description "Protocol family";
                 leaf name {
                   description "Protocol family";
                   type enumeration {
                     enum "inet" {
                       description "IPv4 family";
                     }
                     enum "inet6" {
                       description "IPv6 family";
                     }
                   }
                 }
                 uses apply-advanced;
                 container threshold {
                   presence "enable threshold";
                   description "Multicast forwarding cache suppress threshold";
                   uses apply-advanced;
                   leaf suppress {
                     description "Suppress threshold";
                     type union {
                       type string {
                         pattern "<.*>|$.*";
                       }
                       type uint32 {
                         range "1 .. 200000";
                       }
                     }
                     mandatory true;
                   }
                   leaf reuse {
                     description "Reuse threshold";
                     type union {
                       type string {
                         pattern "<.*>|$.*";
                       }
                       type uint32 {
                         range "1 .. 200000";
                       }
                     }
                   }
                   leaf mvpn-rpt-suppress {
                     description "MVPN RP tree entry suppress threshold";
                     type union {
                       type string {
                         pattern "<.*>|$.*";
                       }
                       type uint32 {
                         range "1 .. 200000";
                       }
                     }
                   }
                   leaf mvpn-rpt-reuse {
                     description "MVPN RP tree entry reuse threshold";
                     type union {
                       type string {
                         pattern "<.*>|$.*";
                       }
                       type uint32 {
                         range "1 .. 200000";
                       }
                     }
                   }
                   leaf log-warning {
                     description "Percentage at which to start generating warnings";
                     type union {
                       type string {
                         pattern "<.*>|$.*";
                       }
                       type uint32 {
                         range "1 .. 100";
                       }
                     }
                   }
                 }
               }
               container threshold {
                 description "Threshold";
                 uses apply-advanced;
                 leaf suppress {
                   description "Suppress threshold";
                   type union {
                     type string {
                       pattern "<.*>|$.*";
                     }
                     type uint32 {
                       range "1 .. 200000";
                     }
                   }
                   mandatory true;
                 }
                 leaf reuse {
                   description "Reuse threshold";
                   type union {
                     type string {
                       pattern "<.*>|$.*";
                     }
                     type uint32 {
                       range "1 .. 200000";
                     }
                   }
                 }
                 leaf mvpn-rpt-suppress {
                   description "MVPN RP tree entry suppress threshold";
                   type union {
                     type string {
                       pattern "<.*>|$.*";
                     }
                     type uint32 {
                       range "1 .. 200000";
                     }
                   }
                 }
                 leaf mvpn-rpt-reuse {
                   description "MVPN RP tree entry reuse threshold";
                   type union {
                     type string {
                       pattern "<.*>|$.*";
                     }
                     type uint32 {
                       range "1 .. 200000";
                     }
                   }
                 }
                 leaf log-warning {
                   description "Percentage at which to start generating warnings";
                   type union {
                     type string {
                       pattern "<.*>|$.*";
                     }
                     type uint32 {
                       range "1 .. 100";
                     }
                   }
                 }
               }
               leaf timeout {
                 description "Forwarding cache entry timeout in minutes";
                 type union {
                   type string {
                     pattern "<.*>|$.*";
                   }
                   type uint32 {
                     range "1 .. 720";
                   }
                 }
               }
             }
             list interface {
               key name;
               ordered-by user;
               description "Multicast interface options";
               uses multicast_interface_options_type;
             }
             list ssm-map {
               key name;
               ordered-by user;
               description "SSM map definitions";
               leaf name {
                 description "SSM map name";
                 type string;
               }
               uses apply-advanced;
               leaf-list policy {
                 ordered-by user;
                 description "Policy for matching group";
                 type jt:policy-algebra;
               }
               leaf-list source {
                 ordered-by user;
                 description "One or more source addresses";
                 type jt:ipaddr;
               }
             }
             list backup-pe-group {
               key name;
               ordered-by user;
               description "Backup PE group definitions";
               leaf name {
                 description "PE group name";
                 type string;
               }
               uses apply-advanced;
               leaf-list backups {
                 ordered-by user;
                 description "One or more IP addresses";
                 type jt:ipaddr;
                 max-elements 8;
               }
               leaf local-address {
                 description "Address to be used as local-address for this group";
                 type jt:ipaddr;
                 mandatory true;
               }
             }
             leaf omit-wildcard-address {
               description "Omit wildcard source/group fields in SPMSI AD NLRI";
               type empty;
             }
             leaf local-address {
               description "Local address for PIM and MVPN sessions";
               type jt:ipv4addr;
             }
           }
         }
       }
     }
     container telemetry {
       description "Telemetry configuration";
       uses apply-advanced;
       container service-statistics {
         presence "enable service-statistics";
         description "Subscriber Service-statistics configuration";
       }
       container subscriber-statistics {
         presence "enable subscriber-statistics";
         description "Subscriber statistics configuration";
       }
       container subscriber-info {
         presence "enable subscriber-info";
         description "Subscriber related information";
         uses apply-advanced;
         leaf service-statistics {
           description "Subscriber Service-statistics configuration";
           type empty;
         }
         leaf subscriber-statistics {
           description "Subscriber statistics configuration";
           type empty;
         }
       }
       container queue-statistics {
         description "Telemetry Queue-Statistics configuration";
         uses apply-advanced;
         list interface {
           key name;
           ordered-by user;
           description "Interface name for this telemetry configuration";
           leaf name {
             type enumeration {
               enum "$junos-interface-name" {
                 description "Dynamic profile interface";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
             }
           }
         }
         list interface-set {
           key name;
           ordered-by user;
           description "Logical interface set configuration";
           leaf name {
             type enumeration {
               enum "$junos-interface-set-name" {
                 description "Dynamic profile Interface set name";
               }
             }
           }
           uses apply-advanced;
           leaf refresh {
             description "Refresh interval range 300-86400";
             type union {
               type string {
                 pattern "<.*>|$.*";
               }
               type uint32 {
                 range "300 .. 86400";
               }
             }
           }
           leaf queues {
             description "Queues to be exported 0-7 separated by ,";
             type string {
             }
           }
         }
       }
     }
     container interfaces {
       description "Interface configuration";
       uses apply-advanced;
       list interface-set {
         key name;
         description "Logical interface set configuration";
         leaf name {
           type string;
         }
         uses apply-advanced;
         list interface {
           key name;
           description "One or more interfaces that belong to interface set";
           leaf name {
             description "Interface name";
             type union {
               type jt:interface-device;
               type string {
                 pattern "<.*>|$.*";
               }
             }
           }
           uses apply-advanced;
           list unit {
             key name;
             description "One or more logical interface unit numbers";
             leaf name {
               description "Unit number";
               type union {
                 type string {
                   pattern "<.*>|$.*";
                 }
                 type uint32 {
                   range "0 .. 1073741823";
                 }
               }
             }
             uses apply-advanced;
           }
           list vlan-tags-outer {
             key name;
             description "One or more outer VLAN tags";
             leaf name {
               description "VLAN tag ID";
               type union {
                 type string {
                   pattern "<.*>|$.*";
                 }
                 type uint32 {
                   range "0 .. 4094";
                 }
               }
             }
             uses apply-advanced;
           }
         }
       }
       container stacked-interface-set {
         presence "enable stacked-interface-set";
         description "Stacked interface set configuration";
         uses apply-advanced;
         list interface-set {
           key name;
           ordered-by user;
           description "Stacked parent interface set configuration";
           leaf name {
             type string;
           }
           uses apply-advanced;
           list interface-set {
             key name;
             ordered-by user;
             description "Stacked child interface set configuration";
             leaf name {
               type string;
             }
             uses apply-advanced;
           }
         }
       }
       container traceoptions {
         description "Interface trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           description "Tracing parameters";
           leaf name {
             type enumeration {
               enum "all" {
                 description "Enable all configuration logging";
               }
               enum "kernel" {
                 description "Log configuration IPC messages to kernel";
               }
               enum "change-events" {
                 description "Log changes that produce configuration events";
               }
               enum "kernel-detail" {
                 description "Log details of configuration messages to kernel";
               }
               enum "config-states" {
                 description "Log the configuration state machine changes";
               }
               enum "resource-usage" {
                 description "Log the resource usage for different states";
               }
               enum "gres-events" {
                 description "Log the events related to GRES ";
               }
               enum "select-events" {
                 description "Log the events on select state machine ";
               }
               enum "bfd-events" {
                 description "Log BFD related events";
               }
               enum "lib-events" {
                 description "Log DCD library related events";
               }
               enum "reserved" {
                 description "Reserved DCD logs";
               }
               enum "emergency" {
                 description "Log DCD emergency events";
               }
               enum "alert" {
                 description "Log DCD alert events";
               }
               enum "critical" {
                 description "Log DCD critical events";
               }
               enum "error" {
                 description "Log DCD error events";
               }
               enum "warning" {
                 description "Log DCD warning events";
               }
               enum "notice" {
                 description "Log DCD notification events";
               }
               enum "informational" {
                 description "Log DCD informations";
               }
               enum "debugging" {
                 description "Log DCD debug events";
               }
               enum "verbose" {
                 description "Log DCD debug all events";
               }
               enum "japi" {
                 description "Log DCD JAPI events";
               }
             }
           }
           leaf disable {
             description "Disable this trace flag";
             type empty;
           }
         }
       }
       list interface-range {
         key name;
         ordered-by user;
         description "Interface ranges configuration";
         leaf name {
           description "Interface-range name";
           type string {
             length "1 .. 128";
           }
         }
         list member {
           key name;
           ordered-by user;
           description "Interfaces belonging to the interface range";
           leaf name {
             description "Member interface name";
             type union {
               type jt:interface-range-wild;
               type string {
                 pattern "<.*>|$.*";
               }
             }
           }
           uses apply-advanced;
         }
         list member-range {
           key name;
           ordered-by user;
           description "Interfaces range in <start-range> to <end-range> format";
           leaf name {
             type union {
               type jt:interface-device;
               type string {
                 pattern "<.*>|$.*";
               }
             }
           }
           leaf end-range {
             type union {
               type jt:interface-device;
               type string {
                 pattern "<.*>|$.*";
               }
             }
             mandatory true;
           }
         }
         uses apply-advanced;
         leaf description {
           description "Text description of interface";
           type string;
         }
         leaf external-model-name {
           description "Name for interface as configured using 3rd-party model";
           type string;
         }
         container management-ethernet-redundancy {
           presence "enable management-ethernet-redundancy";
           description "Management Interface Redundancy";
           uses apply-advanced;
           choice enable_choice {
             case case_1 {
               leaf redundancy-enable {
                 description "Enable Managment Ethernet Redundancy";
                 type empty;
               }
             }
             case case_2 {
               leaf redundancy-disable {
                 description "Disable  Managment Ethernet Redundancy";
                 type empty;
               }
             }
           }
           leaf connectivity-test-interval {
             description "Connectivity test interval";
             default "5";
             units "seconds";
             type union {
               type string {
                 pattern "<.*>|$.*";
               }
               type uint32 {
                 range "1 .. 10";
               }
             }
           }
           leaf connectivity-test-response-interval {
             description "Connectivity test response wait time";
             default "5";
             units "seconds";
             type union {
               type string {
                 pattern "<.*>|$.*";
               }
               type uint32 {
                 range "1 .. 10";
               }
             }
           }
           leaf remote-ipv4-address {
             description "Destination IPV4 address to reach remote ";
             default "nil";
             type jt:ipv4addr;
           }
           leaf remote-ipv6-address {
             description "Destination IPV6 address to reach remote";
             default "nil";
             type jt:ipv6addr;
           }
           leaf number-of-connectivity-retries {
             description "Number of Connectivity retries ";
             default "2";
             type union {
               type string {
                 pattern "<.*>|$.*";
               }
               type uint32 {
                 range "1 .. 8";
               }
             }
           }
         }
         choice enable-disable {
           case case_1 {
             leaf disable {
               description "Disable this interface";
               type empty;
             }
           }
         }
         container traceoptions {
           presence "enable traceoptions";
           description "Interface trace options";
           uses apply-advanced;
           list flag {
             key name;
             ordered-by user;
             description "Tracing parameters";
             leaf name {
               type enumeration {
                 enum "ipc" {
                   description "Trace interface IPC messages";
                 }
                 enum "event" {
                   description "Trace interface events";
                 }
                 enum "media" {
                   description "Trace interface media changes";
                 }
                 enum "all" {
                   description "Enable all interface trace flags";
                 }
               }
             }
           }
         }
         leaf passive-monitor-mode {
           description "Use interface to tap packets from another router";
           type empty;
         }
         choice keepalive_choices {
           case case_1 {
             container keepalives {
               description "Send or demand keepalive messages";
               presence "enable keepalives";
               uses keepalives_type;
             }
           }
           case case_2 {
             leaf no-keepalives {
               description "Do not send keepalive messages";
               type empty;
             }
           }
         }
         choice traps-choice {
           leaf traps {
             description "Enable SNMP notifications on state changes";
             type empty;
           }
           leaf no-traps {
             description "Don't enable SNMP notifications on state changes";
             type empty;
           }
         }
         choice interface-mib-choice {
           leaf interface-mib {
             description "Enable interface-related MIBs";
             type empty;
           }
           leaf no-interface-mib {
             description "Don't enable interface-related MIBs";
             type empty;
           }
         }
         leaf accounting-profile {
           description "Accounting profile name";
           type string;
         }
         choice scheduler_type {
           case case_1 {
             choice per-unit-scheduler-choice {
               leaf per-unit-scheduler {
                 description "Enable subunit queuing on Frame Relay or VLAN IQ interface";
                 type empty;
               }
               leaf no-per-unit-scheduler {
                 description "Don't enable subunit queuing on Frame Relay or VLAN IQ interface";
                 type empty;
               }
             }
           }
           case case_2 {
             leaf shared-scheduler {
               description "Enabled shared queuing on an IQ2 interface";
               type empty;
             }
           }
           case case_3 {
             container hierarchical-scheduler {
               presence "enable hierarchical-scheduler";
               description "Enable hierarchical scheduling";
               leaf maximum-hierarchy-levels {
                 description "Maximum hierarchy levels";
                 type union {
                   type string {
                     pattern "<.*>|$.*";
                   }
                   type uint32;
                 }
               }
               leaf implicit-hierarchy {
                 description "Implicit hierarchy (follows interface hierarchy)";
                 type empty;
               }
             }
           }
         }
         leaf l2tp-maximum-session {
           description "Maximum L2TP session";
           type union {
             type string {
               pattern "<.*>|$.*";
             }
             type uint32 {
               range "0 .. 64000";
             }
           }
         }
         leaf schedulers {
           description "Number of schedulers to allocate for interface";
           type union {
             type uint32;
             type string {
               pattern "<.*>|$.*";
             }
           }
         }
         leaf port-extender-cascade-port {
           description "NGPE Cascade port";
           type empty;
         }
         leaf dce {
           description "Respond to Frame Relay status enquiry messages";
           type empty;
         }
         choice vlan_tag_mode {
           case case_1 {
             leaf vlan-tagging {
               description "802.1q VLAN tagging support";
               type empty;
             }
           }
           case case_2 {
             leaf stacked-vlan-tagging {
               description "Stacked 802.1q VLAN tagging support";
               type empty;
             }
           }
           case case_3 {
           }
           case case_4 {
           }
         }
         leaf number-of-sub-ports {
           description "Number of channels to create for a port";
           type union {
             type string {
               pattern "<.*>|$.*";
             }
             type uint32 {
               range "1 .. 8";
             }
           }
         }
         leaf speed {
           description "Link speed";
           type enumeration {
             enum "auto" {
               description "Enable auto negotiation of interface speed";
             }
             enum "auto-10m-100m" {
               description "Enable auto negotiation of limiting interface speed to 10m/100m";
             }
             enum "10m" {
             }
             enum "100m" {
             }
             enum "1g" {
             }
             enum "2.5g" {
             }
             enum "5g" {
             }
             enum "10g" {
             }
             enum "25g" {
             }
             enum "40g" {
             }
             enum "50g" {
             }
             enum "100g" {
             }
             enum "200g" {
             }
             enum "400g" {
             }
             enum "800g" {
             }
             enum "oc3" {
             }
             enum "oc12" {
             }
             enum "oc48" {
             }
             enum "1.6t" {
             }
           }
         }
         leaf mtu {
           description "Maximum transmit packet size";
           type union {
             type string {
               pattern "<.*>|$.*";
             }
             type uint32;
           }
         }
         container hold-time {
           description "Hold time for link up and link down";
           leaf up {
             description "Link up hold time";
             units "milliseconds";
             type union {
               type uint32;
               type string {
                 pattern "<.*>|$.*";
               }
             }
             mandatory true;
           }
           leaf down {
             description "Link down hold time";
             units "milliseconds";
             type union {
               type uint32;
               type string {
                 pattern "<.*>|$.*";
               }
             }
             mandatory true;
           }
         }
         container port-extender {
           description "Tunnel binding information for the extended port";
           uses apply-advanced;
           container vxlan {
             presence "enable vxlan";
             description "VXLAN binding information for the extended port";
             uses apply-advanced;
             leaf end-point {
               description "Satellite loopback IP address";
               type jt:ipaddr;
               mandatory true;
             }
             leaf vni {
               description "VNI of the satellite extended-port";
               type union {
                 type string {
                   pattern "<.*>|$.*";
                 }
                 type uint32 {
                   range "0 .. 16777214";
                 }
               }
               mandatory true;
             }
           }
         }
         container link-degrade-monitor {
           presence "enable link-degrade-monitor";
           description "Enable link degrade monitoring";
           uses apply-advanced;
           choice enable_choice {
             case case_1 {
               leaf link-degrade-monitor-enable {
                 description "Enable Link Degrade Monitoring";
                 type empty;
               }
             }
             case case_2 {
               leaf no-link-degrade-monitor-enable {
                 description "Disable Link Degrade Monitoring";
                 type empty;
               }
             }
           }
           container actions {
             description "Action upon link degrade event";
             uses apply-advanced;
             choice action_choice {
               case case_1 {
                 leaf media-based {
                   description "Media based";
                   type empty;
                 }
               }
             }
           }
           container recovery {
             description "Link degrade recovery mechanism";
             uses apply-advanced;
             leaf timer {
               description "Auto recovery timer in seconds";
               default "1800";
               type union {
                 type uint32;
                 type string {
                   pattern "<.*>|$.*";
                 }
               }
             }
             choice receovery_choice {
               case case_1 {
                 leaf auto {
                   description "Automatic recovery";
                   type empty;
                 }
               }
               case case_2 {
                 leaf manual {
                   description "Manual recovery";
                   type empty;
                 }
               }
             }
           }
           container thresholds {
             description "Link degrade threshold parameters";
             uses apply-advanced;
             leaf set {
               description "BER at which link considered degraded(1..16)";
               default "1e-7";
               type string {
               }
             }
             leaf clear {
               description "BER at which link considered improved(1..16)";
               default "1e-12";
               type string {
               }
             }
             leaf warning-set {
               description "BER at which link degrade warning raised(1..16)";
               default "1e-9";
               type string {
               }
             }
             leaf warning-clear {
               description "BER at which link degrade warning cleared(1..16)";
               default "1e-11";
               type string {
               }
             }
             leaf interval {
               description "Consecutive link degrade events";
               default "10";
               type union {
                 type string {
                   pattern "<.*>|$.*";
                 }
                 type uint32 {
                   range "1 .. 256";
                 }
               }
             }
           }
         }
         container satop-options {
           description "Structure-Agnostic TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container cesopsn-options {
           description "Structure-Aware TDM over Packet protocol options";
           uses apply-advanced;
           leaf idle-pattern {
             description "An 8-bit hexadecimal pattern to replace TDM data in a lost packet";
             type union {
               type string {
                 pattern "<.*>|$.*";
               }
               type uint32 {
                 range "0 .. 255";
               }
             }
           }
           leaf packetization-latency {
             description "Number of microseconds to create packets";
             units "microseconds";
             type union {
               type string {
                 pattern "<.*>|$.*";
               }
               type uint32 {
                 range "1000 .. 8000";
               }
             }
           }
           leaf payload-size {
             description "Number of payload bytes per packet";
             type union {
               type string {
                 pattern "<.*>|$.*";
               }
               type uint32 {
                 range "64 .. 1024";
               }
             }
           }
           container excessive-packet-loss-rate {
             description "Packet loss options";
             uses apply-advanced;
             leaf threshold {
               description "Percentile designating the threshold of excessive packet loss rate";
               type union {
                 type string {
                   pattern "<.*>|$.*";
                 }
                 type uint8 {
                   range "1 .. 100";
                 }
               }
             }
             leaf sample-period {
               description "Number of milliseconds over which excessive packet loss rate is calculated";
               type union {
                 type string {
                   pattern "<.*>|$.*";
                 }
                 type uint32 {
                   range "1000 .. 65535";
                 }
               }
             }
           }
           choice jitter-buffer-size {
             case case_1 {
               leaf jitter-buffer-packets {
                 description "Number of packets in jitter buffer before packet data is played out in the line";
                 type union {
                   type string {
                     pattern "<.*>|$.*";
                   }
                   type uint32 {
                     range "1 .. 64";
                   }
                 }
               }
             }
             case case_2 {
               leaf jitter-buffer-latency {
                 description "Number of milliseconds delay in jitter buffer before packet data is played out in the line";
                 units "milliseconds";
                 type union {
                   type string {
                     pattern "<.*>|$.*";
                   }
                   type uint32 {
                     range "1 .. 1000";
                   }
                 }
               }
             }
             case case_3 {
               leaf jitter-buffer-auto-adjust {
                 description "Automatically adjust jitter buffer";
                 type empty;
               }
             }
           }
           leaf bit-rate {
             description "In multiples of DS0";
             type union {
               type string {
                 pattern "<.*>|$.*";
               }
               type uint32 {
                 range "1 .. 10240";
               }
             }
           }
         }
         container clocking {
           description "Interface clock source";
           choice clocking_choices {
             case case_1 {
               leaf internal {
                 description "Clocking provided by local system";
                 type empty;
               }
             }
             case case_2 {
               container external {
                 presence "enable external";
                 description "Clocking provided by DCE (loop timing)";
               }
             }
           }
         }
         leaf link-mode {
           description "Link operational mode";
           type enumeration {
             enum "automatic" {
               description "Automatically negotiate duplex";
             }
             enum "half-duplex" {
               description "Half-duplex operation";
             }
             enum "full-duplex" {
               description "Full-duplex operation";
             }
           }
         }
         leaf media-type {
           description "Interface media type (copper or fiber)";
           type enumeration {
             enum "copper" {
               description "Copper as media";
             }
             enum "fiber" {
               description "Fiber as media";
             }
           }
         }
         leaf encapsulation {
           description "Physical link-layer encapsulation";
           type enumeration {
             enum "ethernet" {
               description "Ethernet physical media";
             }
             enum "fddi" {
               description "FDDI physical media";
             }
             enum "token-ring" {
               description "Token Ring physical media";
             }
             enum "ppp" {
               description "Serial PPP device";
             }
             enum "ppp-ccc" {
               description "Serial PPP device for a cross-connect";
             }
             enum "ppp-tcc" {
               description "Serial PPP device for a translational cross-connect";
             }
             enum "ether-vpls-ppp" {
               description "Ethernet VPLS over PPP (bridging) device";
             }
             enum "frame-relay" {
               description "Frame Relay encapsulation";
             }
             enum "frame-relay-ccc" {
               description "Frame Relay for cross-connect";
             }
             enum "frame-relay-tcc" {
               description "Frame Relay for translational cross-connect";
             }
             enum "extended-frame-relay-ccc" {
               description "Any Frame Relay DLCI for cross-connect";
             }
             enum "extended-frame-relay-tcc" {
               description "Any Frame Relay DLCI for translational cross-connect";
             }
             enum "flexible-frame-relay" {
               description "Multiple Frame Relay encapsulations";
             }
             enum "frame-relay-port-ccc" {
               description "Frame Relay port encapsulation for a cross-connect";
             }
             enum "frame-relay-ether-type" {
               description "Cisco-compatible Frame Relay encapsulation";
             }
             enum "frame-relay-ether-type-tcc" {
               description "Cisco-compatible Frame Relay encapsulation for translational cross-connect";
             }
             enum "extended-frame-relay-ether-type-tcc" {
               description "Cisco-compatible Frame Relay encapsulation any DLCI for translational cross-connect";
             }
             enum "cisco-hdlc" {
               description "Cisco-compatible HDLC framing";
             }
             enum "cisco-hdlc-ccc" {
               description "Cisco-compatible HDLC framing for a cross-connect";
             }
             enum "cisco-hdlc-tcc" {
               description "Cisco-compatible HDLC framing for a translational cross-connect";
             }
             enum "vlan-ccc" {
               description "802.1q tagging for a cross-connect";
             }
             enum "extended-vlan-ccc" {
               description "Nonstandard TPID tagging for a cross-connect";
             }
             enum "ethernet-ccc" {
               description "Ethernet cross-connect";
             }
             enum "flexible-ethernet-services" {
               description "Allows per-unit Ethernet encapsulation configuration";
             }
             enum "smds-dxi" {
               description "SMDS DXI framing";
             }
             enum "atm-pvc" {
               description "ATM permanent virtual circuits";
             }
             enum "atm-ccc-cell-relay" {
               description "ATM cell relay encapsulation for cross-connect";
             }
             enum "ethernet-over-atm" {
               description "Ethernet over ATM encapsulation";
             }
             enum "ethernet-tcc" {
               description "Ethernet translational cross-connect";
             }
             enum "extended-vlan-tcc" {
               description "802.1q tagging for a translational cross-connect";
             }
             enum "multilink-frame-relay-uni-nni" {
               description "Multilink Frame Relay UNI NNI (FRF.16) encapsulation";
             }
             enum "satop" {
               description "Structure-Agnostic TDM over Packet encapsulation";
             }
             enum "cesopsn" {
               description "Structure-Agnostic TDM over Packet encapsulation";
             }
             enum "ima" {
               description "Inverse Multiplexing for ATM";
             }
             enum "ethernet-vpls" {
               description "Ethernet virtual private LAN service";
             }
             enum "ethernet-bridge" {
               description "Ethernet layer-2 bridging";
             }
             enum "vlan-vpls" {
               description "VLAN virtual private LAN service";
             }
             enum "vlan-vci-ccc" {
               description "CCC for VLAN Q-in-Q and ATM VPI/VCI interworking";
             }
             enum "extended-vlan-vpls" {
               description "Extended VLAN virtual private LAN service";
             }
             enum "extended-vlan-bridge" {
               description "VLAN layer-2 bridging";
             }
             enum "multilink-ppp" {
               description "Multilink PPP";
             }
             enum "generic-services" {
               description "Generic services";
             }
           }
         }
         leaf network-isolation-profile {
           description "Attach a network isolation profile on this interface";
           type string;
         }
         container framing {
           description "Frame type";
           uses apply-advanced;
           choice frame {
             case case_1 {
               leaf lan-phy {
                 description "802.3ae 10-Gbps LAN-mode interface";
                 type empty;
               }
             }
             case case_2 {
               leaf wan-phy {
                 description "802.3ae 10-Gbps WAN-mode interface";
                 type empty;
               }
             }
             case case_3 {
               leaf sonet {
                 description "SONET framing";
                 type empty;
               }
             }
             case case_4 {
               leaf sdh {
                 description "SDH framing";
                 type empty;
               }
             }
           }
         }
         container lmi {
           description "Local Management Interface settings";
           uses apply-advanced;
           leaf n391dte {
             description "DTE full status polling interval";
             type union {
               type string {
                 pattern "<.*>|$.*";
               }
               type uint16 {
                 range "1 .. 255";
               }
             }
           }
           leaf n392dce {
             description "DCE error threshold";
             type union {
               type string {
                 pattern "<.*>|$.*";
               }
               type uint16 {
                 range "1 .. 10";
               }
             }
           }
           leaf n392dte {
             description "DTE error threshold";
             type union {
               type string {
                 pattern "<.*>|$.*";
               }
               type uint16 {
                 range "1 .. 10";
               }
             }
           }
           leaf n393dce {
             description "DCE monitored event count";
             type union {
               type string {
                 pattern "<.*>|$.*";
               }
               type uint16 {
                 range "1 .. 10";
               }
             }
           }
           leaf n393dte {
             description "DTE monitored event count";
             type union {
               type string {
                 pattern "<.*>|$.*";
               }
               type uint16 {
                 range "1 .. 10";
               }
             }
           }
           leaf t391dte {
             description "DTE polling timer";
             units "seconds";
             type union {
               type string {
                 pattern "<.*>|$.*";
               }
               type uint16 {
                 range "5 .. 30";
               }
             }
           }
           leaf t392dce {
             description "DCE polling verification timer";
             units "seconds";
             type union {
               type string {
                 pattern "<.*>|$.*";
               }
               type uint16 {
                 range "5 .. 30";
               }
             }
           }
           leaf lmi-type {
             description "Specify the Frame Relay LMI type";
             type enumeration {
               enum "ansi" {
                 description "Use ANSI Annex D LMI";
               }
               enum "itu" {
                 description "Use ITU Q933a Annex A LMI";
               }
               enum "c-lmi" {
                 description "Use Consortium LMI";
               }
             }
           }
         }
         container mlfr-uni-nni-bundle-options {
           description "Multilink Frame Relay UNI NNI (FRF.16) management settings";
           uses apply-advanced;
           container cisco-interoperability {
             description "FRF.16 Cisco interoperability settings";
             uses apply-advanced;
             leaf send-lip-remove-link-for-link-reject {
               description "Send Link Integrity Protocol remove link on receiving add-link rejection";
               type empty;
             }
           }
           leaf mrru {
             description "Maximum received reconstructed unit";
             units "bytes";
             type union {
               type string {
                 pattern "<.*>|$.*";
               }
               type uint16 {
                 range "1500 .. 4500";
               }
             }
           }
           leaf yellow-differential-delay {
             description "Yellow differential delay among bundle links to give warning";
             units "milliseconds";
             type union {
               type string {
                 pattern "<.*>|$.*";
               }
               type uint16 {
                 range "3 .. 2000";
               }
             }
           }
           leaf red-differential-delay {
             description "Red differential delay among bundle links to take action";
             units "milliseconds";
             type union {
               type string {
                 pattern "<.*>|$.*";
               }
               type uint16 {
                 range "5 .. 2000";
               }
             }
           }
           leaf action-red-differential-delay {
             description "Type of actions when differential delay exceeds red limit";
             type enumeration {
               enum "remove-link" {
                 description "Remove bundle link from service when exceeding red limit";
               }
               enum "disable-tx" {
                 description "Disable transfer of bundle link when exceeding red limit";
               }
             }
           }
           leaf fragment-threshold {
             description "Fragmentation threshold";
             units "bytes";
             type union {
               type string {
                 pattern "<.*>|$.*";
               }
               type uint32 {
                 range "64 .. 16320";
               }
             }
           }
           leaf drop-timeout {
             description "Drop timeout";
             units "milliseconds";
             type union {
               type string {
                 pattern "<.*>|$.*";
               }
               type uint16 {
                 range "0 .. 2000";
               }
             }
           }
           leaf link-layer-overhead {
             description "Link layer bit stuffing overhead (0.0 .. 50.0 percent)";
             type jt:unsigned-float;
           }
           leaf lmi-type {
             description "Specify the multilink Frame Relay UNI NNI LMI type";
             type enumeration {
               enum "ansi" {
                 description "Use ANSI Annex D LMI";
               }
               enum "itu" {
                 description "Use ITU Q933a Annex A LMI";
               }
               enum "c-lmi" {
                 description "Use Consortium LMI";
               }
             }
           }
           leaf minimum-links {
             description "Minimum number of links to sustain the bundle";
             type union {
               type string {
                 pattern "<.*>|$.*";
               }
               type uint16 {
                 range "1 .. 8";
               }
             }
           }
           leaf hello-timer {
             description "LIP hello timer";
             type union {
               type string {
                 pattern "<.*>|$.*";
               }
               type uint16 {
                 range "5 .. 180";
               }
             }
           }
           leaf acknowledge-timer {
             description "LIP ack timer";
             type union {
               type string {
                 pattern "<.*>|$.*";
               }
               type uint16 {
                 range "1 .. 10";
               }
             }
           }
           leaf acknowledge-retries {
             description "LIP ack retry times";
             type union {
               type string {
                 pattern "<.*>|$.*";
               }
               type uint16 {
                 range "1 .. 5";
               }
             }
           }
           leaf n391 {
             description "Multilink Frame Relay UNI NNI full status polling counter";
             type union {
               type string {
                 pattern "<.*>|$.*";
               }
               type uint16 {
                 range "1 .. 255";
               }
             }
           }
           leaf n392 {
             description "Multilink Frame Relay UNI NNI LMI error threshold";
             type union {
               type string {
                 pattern "<.*>|$.*";
               }
               type uint16 {
                 range "1 .. 10";
               }
             }
           }
           leaf n393 {
             description "Multilink Frame Relay UNI NNI LMI monitored event count";
             type union {
               type string {
                 pattern "<.*>|$.*";
               }
               type uint16 {
                 range "1 .. 10";
               }
             }
           }
           leaf t391 {
             description "Multilink Frame Relay UNI NNI link integrity verify polling timer";
             type union {
               type string {
                 pattern "<.*>|$.*";
               }
               type uint16 {
                 range "5 .. 30";
               }
             }
           }
           leaf t392 {
             description "Multilink Frame Relay UNI NNI polling verification timer";
             type union {
               type string {
                 pattern "<.*>|$.*";
               }
               type uint16 {
                 range "5 .. 30";
               }
             }
           }
         }
         leaf mac {
           description "Hardware MAC address";
           type jt:mac-unicast;
         }
         container receive-bucket {
           description "Set receive bucket parameters";
           uses dcd_rx_bucket_config;
         }
         container transmit-bucket {
           description "Set transmit bucket parameters";
           uses dcd_tx_bucket_config;
         }
         leaf shared-interface {
           description "Enable shared interface on the interface";
           type empty;
         }
         container sonet-options {
           description "SONET interface-specific options";
           uses sonet_options_type;
         }
         container logical-tunnel-options {
           description "Logical Tunnel interface-specific options";
           uses apply-advanced;
           container link-protection {
             presence "enable link-protection";
             description "Enable link protection mode";
             uses apply-advanced;
             leaf revertive {
               description "Revert back (Default mode) from active backup link to primary, if primary is UP";
               type empty;
             }
             leaf non-revertive {
               description "Do not revert back from active backup link to primary, if primary is UP";
               type empty;
             }
           }
           leaf per-unit-mac-disable {
             description "Disable the creation of per unit mac address on LT IFLs for VPLS/CCC encaps";
             type empty;
           }
         }
         container aggregated-sonet-options {
           description "Aggregated SONET interface-specific options";
           uses apply-advanced;
           leaf minimum-links {
             description "Minimum number of aggregated links";
             type union {
               type string {
                 pattern "<.*>|$.*";
               }
               type uint16;
             }
           }
           leaf link-speed {
             description "Aggregated links speed";
             type enumeration {
               enum "oc3" {
                 description "Links are OC-3c or STM-1c";
               }
               enum "oc12" {
                 description "Links are OC-12c or STM-4c";
               }
               enum "oc48" {
                 description "Links are OC-48c or STM-16c";
               }
               enum "oc192" {
                 description "Links are OC-192c or STM-64c";
               }
               enum "oc768" {
                 description "Links are OC-768c or STM-256c";
               }
               enum "mixed" {
                 description "Links are various speeds";
               }
             }
           }
           leaf minimum-bandwidth {
             description "Minimum bandwidth necessary to sustain bundle";
             units "bps";
             type union {
               type string {
                 pattern "<.*>|$.*";
               }
               type uint64 {
                 range "0 .. 159232000000";
               }
             }
           }
         }
         container atm-options {
           description "ATM interface-specific options";
           uses apply-advanced;
           leaf pic-type {
             description "Type of ATM PIC (ATM I, ATM II or ATM CE)";
             type enumeration {
               enum "atm-ce" {
                 description "CE PIC";
               }
               enum "atm2" {
                 description "ATM II IQ PIC";
               }
               enum "atm1" {
                 description "ATM I PIC";
               }
             }
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf use-null-cw {
             description "Always insert/strip null control words with cell-relay";
             type empty;
           }
           container promiscuous-mode {
             presence "enable promiscuous-mode";
             description "Set ATM interface to promiscuous mode";
             uses apply-advanced;
             list vpi {
               key name;
               ordered-by user;
               description "Open this VPI in promiscuous mode";
               leaf name {
                 description "Virtual path index";
                 type union {
                   type string {
                     pattern "<.*>|$.*";
                   }
                   type uint32 {
                     range "0 .. 255";
                   }
                 }
               }
             }
           }
           list vpi {
             key name;
             ordered-by user;
             description "Define a virtual path";
             leaf name {
               description "Virtual path index";
               type union {
                 type string {
                   pattern "<.*>|$.*";
                 }
                 type uint32 {
                   range "0 .. 255";
                 }
               }
             }
             uses apply-advanced;
             leaf maximum-vcs {
               description "Maximum number of virtual circuits on this VP";
               type union {
                 type uint32;
                 type string {
                   pattern "<.*>|$.*";
                 }
               }
             }
             container shaping {
               description "Virtual path traffic-shaping options";
               uses dcd_shaping_config;
             }
             container oam-period {
               description "F4 OAM cell period";
               choice oam_period_choices {
                 case case_1 {
                   leaf oam-period {
                     description "F4 OAM cell period";
                     units "seconds";
                     type union {
                       type string {
                         pattern "<.*>|$.*";
                       }
                       type uint32 {
                         range "1 .. 900";
                       }
                     }
                   }
                 }
                 case case_2 {
                   container disable {
                     presence "enable disable";
                     description "Disable F4 OAM loopback";
                   }
                 }
               }
             }
             container oam-liveness {
               description "F4 OAM virtual path liveness parameters";
               uses apply-advanced;
               leaf up-count {
                 description "Number of F4 OAM cells to consider VP up";
                 type union {
                   type string {
                     pattern "<.*>|$.*";
                   }
                   type uint32 {
                     range "1 .. 255";
                   }
                 }
               }
               leaf down-count {
                 description "Number of F4 OAM cells to consider VP down";
                 type union {
                   type string {
                     pattern "<.*>|$.*";
                   }
                   type uint32 {
                     range "1 .. 255";
                   }
                 }
               }
             }
           }
           container ilmi {
             presence "enable ilmi";
             description "Enable Interim Local Management Interface";
             uses apply-advanced;
           }
           list linear-red-profiles {
             key name;
             ordered-by user;
             description "ATM2 CoS virtual circuit drop profiles";
             leaf name {
               description "Linear RED profile name";
               type string {
               }
             }
             leaf queue-depth {
               description "Maximum queue depth";
               units "cells";
               type string;
               mandatory true;
             }
             leaf high-plp-threshold {
               description "Fill level percentage when linear RED is applied for high PLP";
               type union {
                 type string {
                   pattern "<.*>|$.*";
                 }
                 type uint32 {
                   range "0 .. 100";
                 }
               }
               mandatory true;
             }
             leaf low-plp-threshold {
               description "Fill level percentage when linear RED is applied for low PLP";
               type union {
                 type string {
                   pattern "<.*>|$.*";
                 }
                 type uint32 {
                   range "0 .. 100";
                 }
               }
               mandatory true;
             }
             leaf high-plp-max-threshold {
               description "Fill level percentage with 100 percent packet drop for high PLP";
               type union {
                 type string {
                   pattern "<.*>|$.*";
                 }
                 type uint32 {
                   range "0 .. 100";
                 }
               }
             }
             leaf low-plp-max-threshold {
               description "Fill level percentage with 100 percent packet drop for low PLP";
               type union {
                 type string {
                   pattern "<.*>|$.*";
                 }
                 type uint32 {
                   range "0 .. 100";
                 }
               }
             }
           }
           list scheduler-maps {
             key name;
             ordered-by user;
             description "ATM2 CoS parameters assigned to forwarding classes";
             leaf name {
               description "ATM2 CoS scheduler map name";
               type string {
               }
             }
             uses apply-advanced;
             leaf vc-cos-mode {
               description "ATM2 virtual circuit CoS mode";
               type enumeration {
                 enum "strict" {
                   description "Always schedule high priority queue first";
                 }
                 enum "alternate" {
                   description "Every other packet from high priority queue (default)";
                 }
               }
             }
             list forwarding-class {
               key name;
               ordered-by user;
               description "Scheduling parameters associated with forwarding class";
               leaf name {
                 description "Forwarding class name";
                 type string {
                 }
               }
               uses apply-advanced;
               leaf priority {
                 description "Queuing priority assigned to forwarding class";
                 type enumeration {
                   enum "low" {
                     description "Low priority queuing";
                   }
                   enum "high" {
                     description "High priority queuing";
                   }
                 }
               }
               container transmit-weight {
                 description "Transmit weight";
                 choice weight-method {
                   case case_1 {
                     leaf percent {
                       description "Transmit weight as percentage";
                       type union {
                         type string {
                           pattern "<.*>|$.*";
                         }
                         type uint32 {
                           range "5 .. 100";
                         }
                       }
                     }
                   }
                   case case_2 {
                     leaf cells {
                       description "Transmit weight by cells count";
                       type string;
                     }
                   }
                 }
               }
               choice drop-profile-method {
                 case case_1 {
                   container epd-threshold {
                     description "Early packet discard threshold for ATM2";
                     uses epd_threshold_config;
                   }
                 }
                 case case_2 {
                   leaf linear-red-profile {
                     description "Linear RED profile profile name";
                     type string;
                   }
                 }
               }
             }
           }
           container mpls {
             description "MPLS options";
             uses mpls_ifd_options;
           }
           choice payload-scrambler-choice {
             leaf payload-scrambler {
               description "Enable payload scrambling";
               type empty;
             }
             leaf no-payload-scrambler {
               description "Don't enable payload scrambling";
               type empty;
             }
           }
         }
         container multiservice-options {
           description "Multiservice interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
           choice dump-on-flow-control-choice {
             leaf dump-on-flow-control {
               description "Enable dumping for this interface on prolonged flow-control";
               status deprecated;
               type empty;
             }
             leaf no-dump-on-flow-control {
               description "Don't enable dumping for this interface on prolonged flow-control";
               status deprecated;
               type empty;
             }
           }
           choice reset-on-flow-control-choice {
             leaf reset-on-flow-control {
               description "Enable resetting this interface on prolonged flow-control";
               status deprecated;
               type empty;
             }
             leaf no-reset-on-flow-control {
               description "Don't enable resetting this interface on prolonged flow-control";
               status deprecated;
               type empty;
             }
           }
           container flow-control-options {
             description "Flow control configuration";
             uses apply-advanced;
             leaf dump-on-flow-control {
               description "Cause core dump during prolonged flow-control";
               type empty;
             }
             leaf reset-on-flow-control {
               description "Reset interface during prolonged flow-control";
               type empty;
             }
             leaf down-on-flow-control {
               description "Bring interface down during prolonged flow-control";
               type empty;
             }
             leaf up-on-flow-control {
               description "Keep interface up during prolonged flow-control";
               type empty;
             }
           }
         }
         container ggsn-options {
           description "GGSN interface-specific options";
           uses apply-advanced;
           choice syslog-choice {
             leaf syslog {
               description "Enable system logging on this interface";
               type empty;
             }
             leaf no-syslog {
               description "Don't enable system logging on this interface";
               type empty;
             }
           }
           choice core-dump-choice {
             leaf core-dump {
               description "Enable core dumping on this interface";
               type empty;
             }
             leaf no-core-dump {
               description "Don't enable core dumping on this interface";
               type empty;
             }
           }
         }
         container ppp-options {
           description "Point-to-Point Protocol (PPP) interface-specific options";
           uses ppp_options_type;
         }
         container lsq-failure-options {
           description "Link services queuing failure options";
           uses apply-advanced;
           list trigger-link-failure {
             key name;
             ordered-by user;
             description "Link on which to trigger failure";
             leaf name {
               description "Interface name";
               type union {
                 type jt:interface-device;
                 type string {
                   pattern "<.*>|$.*";
                 }
               }
             }
             uses apply-advanced;
           }
           choice no-termination-request-choice {
             leaf no-termination-request {
               description "Do not send PPP termination requests";
               type empty;
             }
             leaf no-no-termination-request {
               description "Don't do not send PPP termination requests";
               type empty;
             }
           }
         }
         container services-options {
           description "Services interface-specific options";
           uses apply-advanced;
           container syslog {
             description "Define system log parameters";
             uses log-object;
           }
           container jflow-log {
             description "Define Jflow-log parameters.";
             uses apply-advanced;
             leaf message-rate-limit {
               description "Maximum jflow-log NAT error events allowed per second from this interface";
               units "messages per second";
               type union {
                 type string {
                   pattern "<.*>|$.*";
                 }
                 type uint32 {
                   range "1 .. 2147483647";
                 }
               }
             }
           }
           container deterministic-nat-configuration-log-interval {
             presence "enable deterministic-nat-configuration-log-interval";
             description "Define Deterministic NAT parameters";
             uses apply-advanced;
             leaf interval {
               description "Interval in which deterministic NAT logs are generated";
               units "seconds";
               type union {
                 type string {
                   pattern "<.*>|$.*";
                 }
                 type uint32 {
                   range "1800 .. 86400";
                 }
               }
             }
           }
           leaf open-timeout {
             description "Timeout period for TCP session establishment";
             units "seconds";
             type union {
               type string {
                 pattern "<.*>|$.*";
               }
               type uint32 {
                 range "4 .. 300";
               }
             }
           }
           leaf close-timeout {
             description "Timeout period for TCP session tear-down";
             units "seconds";
             type union {
               type string {
                 pattern "<.*>|$.*";
               }
               type uint32 {
                 range "2 .. 300";
               }
             }
           }
           leaf inactivity-timeout {
             description "Inactivity timeout period for established sessions (4..86400)";
             units "seconds";
             type union {
               type uint32;
               type string {
                 pattern "<.*>|$.*";
               }
             }
           }
           leaf inactivity-tcp-timeout {
             description "Inactivity timeout period for TCP established sessions";
             units "seconds";
             type union {
               type string {
                 pattern "<.*>|$.*";
               }
               type uint32 {
                 range "4 .. 86400";
               }
             }
           }
           leaf inactivity-asymm-tcp-timeout {
             description "Inactivity timeout period for asymmetric TCP established sessions";
             units "seconds";
             type union {
               type string {
                 pattern "<.*>|$.*";
               }
               type uint32 {
                 range "4 .. 86400";
               }
             }
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           leaf disable-global-timeout-override {
             description "Disallow overriding  global inactivity or session timeout";
             type empty;
           }
           leaf tcp-tickles {
             description "Number of TCP keep-alive packets to be sent for bi-directional TCP flows";
             default "4";
             type union {
               type string {
                 pattern "<.*>|$.*";
               }
               type uint8 {
                 range "0 .. 30";
               }
             }
           }
           leaf fragment-limit {
             description "Maximum number of fragments allowed for a packet";
             default "64";
             type union {
               type string {
                 pattern "<.*>|$.*";
               }
               type uint8 {
                 range "1 .. 250";
               }
             }
           }
           leaf reassembly-timeout {
             description "Re-assembly timeout (seconds) for fragments of a packet";
             default "4";
             units "seconds";
             type union {
               type string {
                 pattern "<.*>|$.*";
               }
               type uint8 {
                 range "1 .. 60";
               }
             }
           }
           leaf cgn-pic {
             description "PIC will be used for Carrier Grade NAT configuration only";
             type empty;
           }
           leaf pba-interim-logging-interval {
             description "Interim logging interval in seconds";
             default "0";
             units "seconds";
             type union {
               type string {
                 pattern "<.*>|$.*";
               }
               type uint32 {
                 range "0 .. 86400";
               }
             }
           }
           container session-limit {
             presence "enable session-limit";
             description "Session limit";
             uses apply-advanced;
             leaf maximum {
               description "Maximum number of sessions allowed simultaneously";
               type string;
             }
             leaf rate {
               description "Maximum number of new sessions allowed per second";
               type string;
             }
             leaf cpu-load-threshold {
               description "CPU limit in percentage for auto-tuning of session rate";
               units "percent";
               type union {
                 type string {
                   pattern "<.*>|$.*";
                 }
                 type uint8 {
                   range "1 .. 100";
                 }
               }
             }
           }
           leaf enable-subscriber-analysis {
             description "Enable subscriber analysis on the interface";
             type empty;
           }
           leaf disable-subscriber-analysis {
             description "Disable subscriber analysis on the interface";
             type empty;
           }
           leaf disable-usp-tracing {
             description "Disable usp tracing on this pic";
             type empty;
           }
           leaf disable-drop-flows {
             description "Disable drop flows on this pic";
             type empty;
           }
           container ignore-errors {
             presence "enable ignore-errors";
             description "Ignore anomalies or errors";
             leaf tcp {
               description "TCP protocol errors";
               type empty;
             }
             leaf alg {
               description "ALG anomalies or errors";
               type empty;
             }
           }
           container capture {
             description "Packet capture for SFW and NAT on the Services PIC";
             uses apply-advanced;
             leaf capture-size {
               description "The number of packets to store";
               type union {
                 type string {
                   pattern "<.*>|$.*";
                 }
                 type uint32 {
                   range "1 .. 344000";
                 }
               }
             }
             leaf pkt-size {
               description "Number of bytes to be saved from each packet";
               type union {
                 type string {
                   pattern "<.*>|$.*";
                 }
                 type uint16 {
                   range "64 .. 15000";
                 }
               }
             }
             leaf logs-per-packet {
               description "The number of trace messages stored for each packet";
               type union {
                 type string {
                   pattern "<.*>|$.*";
                 }
                 type uint16 {
                   range "0 .. 500";
                 }
               }
             }
             leaf max-log-line-size {
               description "The maximum length of a stored trace message";
               type union {
                 type uint8;
                 type string {
                   pattern "<.*>|$.*";
                 }
               }
             }
             container filter {
               presence "enable filter";
               description "Filtering options for the packet capture";
               uses apply-advanced;
               container source-ip {
                 description "Filter based on source-ip (and wildcard)";
                 leaf ip {
                   description "Source IP";
                   type jt:ipaddr;
                   mandatory true;
                 }
                 leaf wildcard {
                   description "Source IP wildcard";
                   type jt:ipaddr;
                 }
               }
               container dest-ip {
                 description "Filter based on dest-ip (and wildcard)";
                 leaf ip {
                   description "Dest IP";
                   type jt:ipaddr;
                   mandatory true;
                 }
                 leaf wildcard {
                   description "Dest IP wildcard";
                   type jt:ipaddr;
                 }
               }
               container sw-sip {
                 description "Filter based on source softwire ip (and wildcard)";
                 leaf ip {
                   description "Source softwire IP";
                   type jt:ipv6addr;
                   mandatory true;
                 }
                 leaf wildcard {
                   description "Source IP wildcard";
                   type jt:ipv6addr;
                 }
               }
               container sw-dip {
                 description "Filter based on destination softwire ip (and wildcard)";
                 leaf ip {
                   description "Destination softwire IP";
                   type jt:ipaddr;
                   mandatory true;
                 }
                 leaf wildcard {
                   description "Destination IP wildcard";
                   type jt:ipaddr;
                 }
               }
               container sport-range {
                 description "Filter based on source port";
                 leaf low {
                   description "Source port range start";
                   type union {
                     type uint16;
                     type string {
                       pattern "<.*>|$.*";
                     }
                   }
                   mandatory true;
                 }
                 leaf high {
                   description "Source port range end";
                   type union {
                     type uint16;
                     type string {
                       pattern "<.*>|$.*";
                     }
                   }
                   mandatory true;
                 }
               }
               container dport-range {
                 description "Filter based on destination port";
                 leaf low {
                   description "Destination port range start";
                   type union {
                     type uint16;
                     type string {
                       pattern "<.*>|$.*";
                     }
                   }
                   mandatory true;
                 }
                 leaf high {
                   description "Destination port range end";
                   type union {
                     type uint16;
                     type string {
                       pattern "<.*>|$.*";
                     }
                   }
                   mandatory true;
                 }
               }
               leaf proto {
                 description "Filter based on L4 protocol";
                 type enumeration {
                   enum "icmp" {
                   }
                   enum "tcp" {
                   }
                   enum "udp" {
                   }
                 }
               }
             }
           }
           container flow {
             description "Define flow parameters";
             uses apply-advanced;
             container traceoptions {
               description "Trace options for flow services";
             }
           }
           leaf fpc-pic-information {
             description "Include FPC and PIC slot number in the syslogs";
             type empty;
           }
           leaf utc-timestamp {
             description "Use UTC time for security log timestamps";
             type empty;
           }
           leaf syslog-local-system-timestamp {
             description "Use local system time for services syslog timestamp";
             type empty;
           }
         }
         container t3-options {
           description "T3 interface-specific options";
           uses apply-advanced;
           leaf loopback {
             description "Loopback mode";
             type enumeration {
               enum "local" {
                 description "Local loopback";
               }
               enum "remote" {
                 description "Remote loopback";
               }
               enum "payload" {
                 description "Payload loopback";
               }
             }
           }
           choice long-buildout-choice {
             leaf long-buildout {
               description "Set hardware to drive line longer than 255 feet";
               type empty;
             }
             leaf no-long-buildout {
               description "Don't set hardware to drive line longer than 255 feet";
               type empty;
             }
           }
           choice loop-timing-choice {
             leaf loop-timing {
               description "Set loop timing for T3";
               type empty;
             }
             leaf no-loop-timing {
               description "Don't set loop timing for T3";
               type empty;
             }
           }
           container compatibility-mode {
             description "Set CSU compatibility mode";
             choice vendor {
               case case_1 {
                 container larscom {
                   presence "enable larscom";
                   description "Compatible with Larscom CSU";
                   leaf subrate {
                     description "Set subrate value";
                     type union {
                       type string {
                         pattern "<.*>|$.*";
                       }
                       type uint32 {
                         range "1 .. 14";
                       }
                     }
                   }
                 }
               }
               case case_2 {
                 container verilink {
                   presence "enable verilink";
                   description "Compatible with Verilink CSU (not on 2/4-port T3 PIC)";
                   leaf subrate {
                     description "Set subrate value";
                     type union {
                       type string {
                         pattern "<.*>|$.*";
                       }
                       type uint32 {
                         range "1 .. 28";
                       }
                     }
                   }
                 }
               }
               case case_3 {
                 container adtran {
                   presence "enable adtran";
                   description "Compatible with Adtran CSU (not on 2/4-port T3 PIC)";
                   leaf subrate {
                     description "Set subrate value";
                     type union {
                       type string {
                         pattern "<.*>|$.*";
                       }
                       type uint32 {
                         range "1 .. 588";
                       }
                     }
                   }
                 }
               }
               case case_4 {
                 container kentrox {
                   presence "enable kentrox";
                   description "Compatible with Kentrox CSU";
                   leaf subrate {
                     description "Set subrate value (not on 2/4-port T3 PIC)";
                     type union {
                       type string {
                         pattern "<.*>|$.*";
                       }
                       type uint32 {
                         range "1 .. 69";
                       }
                     }
                   }
                 }
               }
               case case_5 {
                 container digital-link {
                   presence "enable digital-link";
                   description "Compatible with Digital Link CSU";
                   leaf subrate {
                     description "Set subrate value";
                     type enumeration {
                       enum "301Kb" {
                         description "301 Kbps";
                       }
                       enum "601Kb" {
                         description "601 Kbps";
                       }
                       enum "902Kb" {
                         description "902 Kbps";
                       }
                       enum "1.2Mb" {
                         description "1.2 Mbps";
                       }
                       enum "1.5Mb" {
                         description "1.5 Mbps";
                       }
                       enum "1.8Mb" {
                         description "1.8 Mbps";
                       }
                       enum "2.1Mb" {
                         description "2.1 Mbps";
                       }
                       enum "2.4Mb" {
                         description "2.4 Mbps";
                       }
                       enum "2.7Mb" {
                         description "2.7 Mbps";
                       }
                       enum "3.0Mb" {
                         description "3.0 Mbps";
                       }
                       enum "3.3Mb" {
                         description "3.3 Mbps";
                       }
                       enum "3.6Mb" {
                         description "3.6 Mbps";
                       }
                       enum "3.9Mb" {
                         description "3.9 Mbps";
                       }
                       enum "4.2Mb" {
                         description "4.2 Mbps";
                       }
                       enum "4.5Mb" {
                         description "4.5 Mbps";
                       }
                       enum "4.8Mb" {
                         description "4.8 Mbps";
                       }
                       enum "5.1Mb" {
                         description "5.1 Mbps";
                       }
                       enum "5.4Mb" {
                         description "5.4 Mbps";
                       }
                       enum "5.7Mb" {
                         description "5.7 Mbps";
                       }
                       enum "6.0Mb" {
                         description "6.0 Mbps";
                       }
                       enum "6.3Mb" {
                         description "6.3 Mbps";
                       }
                       enum "6.6Mb" {
                         description "6.6 Mbps";
                       }
                       enum "6.9Mb" {
                         description "6.9 Mbps";
                       }
                       enum "7.2Mb" {
                         description "7.2 Mbps";
                       }
                       enum "7.5Mb" {
                         description "7.5 Mbps";
                       }
                       enum "7.8Mb" {
                         description "7.8 Mbps";
                       }
                       enum "8.1Mb" {
                         description "8.1 Mbps";
                       }
                       enum "8.4Mb" {
                         description "8.4 Mbps";
                       }
                       enum "8.7Mb" {
                         description "8.7 Mbps";
                       }
                       enum "9.0Mb" {
                         description "9.0 Mbps";
                       }
                       enum "9.3Mb" {
                         description "9.3 Mbps";
                       }
                       enum "9.6Mb" {
                         description "9.6 Mbps";
                       }
                       enum "9.9Mb" {
                         description "9.9 Mbps";
                       }
                       enum "10.2Mb" {
                         description "10.2 Mbps";
                       }
                       enum "10.5Mb" {
                         description "10.5 Mbps";
                       }
                       enum "10.8Mb" {
                         description "10.8 Mbps";
                       }
                       enum "11.1Mb" {
                         description "11.1 Mbps";
                       }
                       enum "11.4Mb" {
                         description "11.4 Mbps";
                       }
                       enum "11.7Mb" {
                         description "11.7 Mbps";
                       }
                       enum "12.0Mb" {
                         description "12.0 Mbps";
                       }
                       enum "12.3Mb" {
                         description "12.3 Mbps";
                       }
                       enum "12.6Mb" {
                         description "12.6 Mbps";
                       }
                       enum "12.9Mb" {
                         description "12.9 Mbps";
                       }
                       enum "13.2Mb" {
                         description "13.2 Mbps";
                       }
                       enum "13.5Mb" {
                         description "13.5 Mbps";
                       }
                       enum "13.8Mb" {
                         description "13.8 Mbps";
                       }
                       enum "14.1Mb" {
                         description "14.1 Mbps";
                       }
                       enum "14.4Mb" {
                         description "14.4 Mbps";
                       }
                       enum "14.7Mb" {
                         description "14.7 Mbps";
                       }
                       enum "15.0Mb" {
                         description "15.0 Mbps";
                       }
                       enum "15.3Mb" {
                         description "15.3 Mbps";
                       }
                       enum "15.6Mb" {
                         description "15.6 Mbps";
                       }
                       enum "15.9Mb" {
                         description "15.9 Mbps";
                       }
                       enum "16.2Mb" {
                         description "16.2 Mbps";
                       }
                       enum "16.5Mb" {
                         description "16.5 Mbps";
                       }
                       enum "16.8Mb" {
                         description "16.8 Mbps";
                       }
                       enum "17.1Mb" {
                         description "17.1 Mbps";
                       }
                       enum "17.4Mb" {
                         description "17.4 Mbps";
                       }
                       enum "17.7Mb" {
                         description "17.7 Mbps";
                       }
                       enum "18.0Mb" {
                         description "18.0 Mbps";
                       }
                       enum "18.3Mb" {
                         description "18.3 Mbps";
                       }
                       enum "18.6Mb" {
                         description "18.6 Mbps";
                       }
                       enum "18.9Mb" {
                         description "18.9 Mbps";
                       }
                       enum "19.2Mb" {
                         description "19.2 Mbps";
                       }
                       enum "19.5Mb" {
                         description "19.5 Mbps";
                       }
                       enum "19.8Mb" {
                         description "19.8 Mbps";
                       }
                       enum "20.1Mb" {
                         description "20.1 Mbps";
                       }
                       enum "20.5Mb" {
                         description "20.5 Mbps";
                       }
                       enum "20.8Mb" {
                         description "20.8 Mbps";
                       }
                       enum "21.1Mb" {
                         description "21.1 Mbps";
                       }
                       enum "21.4Mb" {
                         description "21.4 Mbps";
                       }
                       enum "21.7Mb" {
                         description "21.7 Mbps";
                       }
                       enum "22.0Mb" {
                         description "22.0 Mbps";
                       }
                       enum "22.3Mb" {
                         description "22.3 Mbps";
                       }
                       enum "22.6Mb" {
                         description "22.6 Mbps";
                       }
                       enum "22.9Mb" {
                         description "22.9 Mbps";
                       }
                       enum "23.2Mb" {
                         description "23.2 Mbps";
                       }
                       enum "23.5Mb" {
                         description "23.5 Mbps";
                       }
                       enum "23.8Mb" {
                         description "23.8 Mbps";
                       }
                       enum "24.1Mb" {
                         description "24.1 Mbps";
                       }
                       enum "24.4Mb" {
                         description "24.4 Mbps";
                       }
                       enum "24.7Mb" {
                         description "24.7 Mbps";
                       }
                       enum "25.0Mb" {
                         description "25.0 Mbps";
                       }
                       enum "25.3Mb" {
                         description "25.3 Mbps";
                       }
                       enum "25.6Mb" {
                         description "25.6 Mbps";
                       }
                       enum "25.9Mb" {
                         description "25.9 Mbps";
                       }
                       enum "26.2Mb" {
                         description "26.2 Mbps";
                       }
                       enum "26.5Mb" {
                         description "26.5 Mbps";
                       }
                       enum "26.8Mb" {
                         description "26.8 Mbps";
                       }
                       enum "27.1Mb" {
                         description "27.1 Mbps";
                       }
                       enum "27.4Mb" {
                         description "27.4 Mbps";
                       }
                       enum "27.7Mb" {
                         description "27.7 Mbps";
                       }
                       enum "28.0Mb" {
                         description "28.0 Mbps";
                       }
                       enum "28.3Mb" {
                         description "28.3 Mbps";
                       }
                       enum "28.6Mb" {
                         description "28.6 Mbps";
                       }
                       enum "28.9Mb" {
                         description "28.9 Mbps";
                       }
                       enum "29.2Mb" {
                         description "29.2 Mbps";
                       }
                       enum "29.5Mb" {
                         description "29.5 Mbps";
                       }
                       enum "29.8Mb" {
                         description "29.8 Mbps";
                       }
                       enum "30.1Mb" {
                         description "30.1 Mbps";
                       }
                       enum "30.4Mb" {
                         description "30.4 Mbps";
                       }
                       enum "30.7Mb" {
                         description "30.7 Mbps";
                       }
                       enum "31.0Mb" {
                         description "31.0 Mbps";
                       }
                       enum "31.3Mb" {
                         description "31.3 Mbps";
                       }
                       enum "31.6Mb" {
                         description "31.6 Mbps";
                       }
                       enum "31.9Mb" {
                         description "31.9 Mbps";
                       }
                       enum "32.2Mb" {
                         description "32.2 Mbps";
                       }
                       enum "32.5Mb" {
                         description "32.5 Mbps";
                       }
                       enum "32.8Mb" {
                         description "32.8 Mbps";
                       }
                       enum "33.1Mb" {
                         description "33.1 Mbps";
                       }
                       enum "33.4Mb" {
                         description "33.4 Mbps";
                       }
                       enum "33.7Mb" {
                         description "33.7 Mbps";
                       }
                       enum "34.0Mb" {
                         description "34.0 Mbps";
                       }
                       enum "34.3Mb" {
                         description "34.3 Mbps";
                       }
                       enum "34.6Mb" {
                         description "34.6 Mbps";
                       }
                       enum "34.9Mb" {
                         description "34.9 Mbps";
                       }
                       enum "35.2Mb" {
                         description "35.2 Mbps";
                       }
                       enum "35.5Mb" {
                         description "35.5 Mbps";
                       }
                       enum "35.8Mb" {
                         description "35.8 Mbps";
                       }
                       enum "36.1Mb" {
                         description "36.1 Mbps";
                       }
                       enum "36.4Mb" {
                         description "36.4 Mbps";
                       }
                       enum "36.7Mb" {
                         description "36.7 Mbps";
                       }
                       enum "37.0Mb" {
                         description "37.0 Mbps";
                       }
                       enum "37.3Mb" {
                         description "37.3 Mbps";
                       }
                       enum "37.6Mb" {
                         description "37.6 Mbps";
                       }
                       enum "37.9Mb" {
                         description "37.9 Mbps";
                       }
                       enum "38.2Mb" {
                         description "38.2 Mbps";
                       }
                       enum "38.5Mb" {
                         description "38.5 Mbps";
                       }
                       enum "38.8Mb" {
                         description "38.8 Mbps";
                       }
                       enum "39.1Mb" {
                         description "39.1 Mbps";
                       }
                       enum "39.4Mb" {
                         description "39.4 Mbps";
                       }
                       enum "39.7Mb" {
                         description "39.7 Mbps";
                       }
                       enum "40.0Mb" {
                         description "40.0 Mbps";
                       }
                       enum "40.3Mb" {
                         description "40.3 Mbps";
                       }
                       enum "40.6Mb" {
                         description "40.6 Mbps";
                       }
                       enum "40.9Mb" {
                         description "40.9 Mbps";
                       }
                       enum "41.2Mb" {
                         description "41.2 Mbps";
                       }
                       enum "41.5Mb" {
                         description "41.5 Mbps";
                       }
                       enum "41.8Mb" {
                         description "41.8 Mbps";
                       }
                       enum "42.1Mb" {
                         description "42.1 Mbps";
                       }
                       enum "42.4Mb" {
                         description "42.4 Mbps";
                       }
                       enum "42.7Mb" {
                         description "42.7 Mbps";
                       }
                       enum "43.0Mb" {
                         description "43.0 Mbps";
                       }
                       enum "43.3Mb" {
                         description "43.3 Mbps";
                       }
                       enum "43.6Mb" {
                         description "43.6 Mbps";
                       }
                       enum "43.9Mb" {
                         description "43.9 Mbps";
                       }
                       enum "44.2Mb" {
                         description "44.2 Mbps";
                       }
                     }
                   }
                 }
               }
             }
           }
           choice payload-scrambler-choice {
             leaf payload-scrambler {
               description "Enable payload scrambling";
               type empty;
             }
             leaf no-payload-scrambler {
               description "Don't enable payload scrambling";
               type empty;
             }
           }
           choice cbit-parity-choice {
             leaf cbit-parity {
               description "Enable C-bit parity mode";
               type empty;
             }
             leaf no-cbit-parity {
               description "Don't enable C-bit parity mode";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           choice feac-loop-respond-choice {
             leaf feac-loop-respond {
               description "Respond to FEAC loop requests";
               type empty;
             }
             leaf no-feac-loop-respond {
               description "Don't respond to FEAC loop requests";
               type empty;
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "DS-3 interface encapsulation";
             type enumeration {
               enum "plcp" {
                 description "PLCP encapsulation";
               }
               enum "direct" {
                 description "ATM direct mapping";
               }
             }
           }
         }
         container e3-options {
           description "E3 interface-specific options";
           uses apply-advanced;
           leaf loopback {
             description "Loopback mode";
             type enumeration {
               enum "local" {
                 description "Local loopback";
               }
               enum "remote" {
                 description "Remote loopback";
               }
             }
           }
           choice unframed-choice {
             leaf unframed {
               description "Enable unframed mode";
               type empty;
             }
             leaf no-unframed {
               description "Don't enable unframed mode";
               type empty;
             }
           }
           container compatibility-mode {
             description "Set CSU compatibility mode";
             choice vendor {
               case case_1 {
                 leaf larscom {
                   description "Compatible with Larscom CSU (only non IQ E3 interfaces)";
                   type empty;
                 }
               }
               case case_2 {
                 container digital-link {
                   presence "enable digital-link";
                   description "Compatible with Digital Link CSU";
                   leaf subrate {
                     description "Set subrate value";
                     type enumeration {
                       enum "358Kb" {
                         description "358 Kbps";
                       }
                       enum "716Kb" {
                         description "716 Kbps";
                       }
                       enum "1.1Mb" {
                         description "1.1 Mbps";
                       }
                       enum "1.4Mb" {
                         description "1.4 Mbps";
                       }
                       enum "1.8Mb" {
                         description "1.8 Mbps";
                       }
                       enum "2.1Mb" {
                         description "2.1 Mbps";
                       }
                       enum "2.5Mb" {
                         description "2.5 Mbps";
                       }
                       enum "2.9Mb" {
                         description "2.9 Mbps";
                       }
                       enum "3.2Mb" {
                         description "3.2 Mbps";
                       }
                       enum "3.6Mb" {
                         description "3.6 Mbps";
                       }
                       enum "3.9Mb" {
                         description "3.9 Mbps";
                       }
                       enum "4.3Mb" {
                         description "4.3 Mbps";
                       }
                       enum "4.7Mb" {
                         description "4.7 Mbps";
                       }
                       enum "5.0Mb" {
                         description "5.0 Mbps";
                       }
                       enum "5.4Mb" {
                         description "5.4 Mbps";
                       }
                       enum "5.7Mb" {
                         description "5.7 Mbps";
                       }
                       enum "6.1Mb" {
                         description "6.1 Mbps";
                       }
                       enum "6.4Mb" {
                         description "6.4 Mbps";
                       }
                       enum "6.8Mb" {
                         description "6.8 Mbps";
                       }
                       enum "7.2Mb" {
                         description "7.2 Mbps";
                       }
                       enum "7.5Mb" {
                         description "7.5 Mbps";
                       }
                       enum "7.9Mb" {
                         description "7.9 Mbps";
                       }
                       enum "8.2Mb" {
                         description "8.2 Mbps";
                       }
                       enum "8.6Mb" {
                         description "8.6 Mbps";
                       }
                       enum "9.0Mb" {
                         description "9.0 Mbps";
                       }
                       enum "9.3Mb" {
                         description "9.3 Mbps";
                       }
                       enum "9.7Mb" {
                         description "9.7 Mbps";
                       }
                       enum "10.0Mb" {
                         description "10.0 Mbps";
                       }
                       enum "10.4Mb" {
                         description "10.4 Mbps";
                       }
                       enum "10.7Mb" {
                         description "10.7 Mbps";
                       }
                       enum "11.1Mb" {
                         description "11.1 Mbps";
                       }
                       enum "11.5Mb" {
                         description "11.5 Mbps";
                       }
                       enum "11.8Mb" {
                         description "11.8 Mbps";
                       }
                       enum "12.2Mb" {
                         description "12.2 Mbps";
                       }
                       enum "12.5Mb" {
                         description "12.5 Mbps";
                       }
                       enum "12.9Mb" {
                         description "12.9 Mbps";
                       }
                       enum "13.2Mb" {
                         description "13.2 Mbps";
                       }
                       enum "13.6Mb" {
                         description "13.6 Mbps";
                       }
                       enum "14.0Mb" {
                         description "14.0 Mbps";
                       }
                       enum "14.3Mb" {
                         description "14.3 Mbps";
                       }
                       enum "14.7Mb" {
                         description "14.7 Mbps";
                       }
                       enum "15.0Mb" {
                         description "15.0 Mbps";
                       }
                       enum "15.4Mb" {
                         description "15.4 Mbps";
                       }
                       enum "15.8Mb" {
                         description "15.8 Mbps";
                       }
                       enum "16.1Mb" {
                         description "16.1 Mbps";
                       }
                       enum "16.5Mb" {
                         description "16.5 Mbps";
                       }
                       enum "16.8Mb" {
                         description "16.8 Mbps";
                       }
                       enum "17.2Mb" {
                         description "17.2 Mbps";
                       }
                       enum "17.5Mb" {
                         description "17.5 Mbps";
                       }
                       enum "17.9Mb" {
                         description "17.9 Mbps";
                       }
                       enum "18.3Mb" {
                         description "18.3 Mbps";
                       }
                       enum "18.6Mb" {
                         description "18.6 Mbps";
                       }
                       enum "19.0Mb" {
                         description "19.0 Mbps";
                       }
                       enum "19.3Mb" {
                         description "19.3 Mbps";
                       }
                       enum "19.7Mb" {
                         description "19.7 Mbps";
                       }
                       enum "20.0Mb" {
                         description "20.0 Mbps";
                       }
                       enum "20.4Mb" {
                         description "20.4 Mbps";
                       }
                       enum "20.8Mb" {
                         description "20.8 Mbps";
                       }
                       enum "21.1Mb" {
                         description "21.1 Mbps";
                       }
                       enum "21.5Mb" {
                         description "21.5 Mbps";
                       }
                       enum "21.8Mb" {
                         description "21.8 Mbps";
                       }
                       enum "22.2Mb" {
                         description "22.2 Mbps";
                       }
                       enum "22.6Mb" {
                         description "22.6 Mbps";
                       }
                       enum "22.9Mb" {
                         description "22.9 Mbps";
                       }
                       enum "23.3Mb" {
                         description "23.3 Mbps";
                       }
                       enum "23.6Mb" {
                         description "23.6 Mbps";
                       }
                       enum "24.0Mb" {
                         description "24.0 Mbps";
                       }
                       enum "24.3Mb" {
                         description "24.3 Mbps";
                       }
                       enum "24.7Mb" {
                         description "24.7 Mbps";
                       }
                       enum "25.1Mb" {
                         description "25.1 Mbps";
                       }
                       enum "25.4Mb" {
                         description "25.4 Mbps";
                       }
                       enum "25.8Mb" {
                         description "25.8 Mbps";
                       }
                       enum "26.1Mb" {
                         description "26.1 Mbps";
                       }
                       enum "26.5Mb" {
                         description "26.5 Mbps";
                       }
                       enum "26.9Mb" {
                         description "26.9 Mbps";
                       }
                       enum "27.2Mb" {
                         description "27.2 Mbps";
                       }
                       enum "27.6Mb" {
                         description "27.6 Mbps";
                       }
                       enum "27.9Mb" {
                         description "27.9 Mbps";
                       }
                       enum "28.3Mb" {
                         description "28.3 Mbps";
                       }
                       enum "28.6Mb" {
                         description "28.6 Mbps";
                       }
                       enum "29.0Mb" {
                         description "29.0 Mbps";
                       }
                       enum "29.4Mb" {
                         description "29.4 Mbps";
                       }
                       enum "29.7Mb" {
                         description "29.7 Mbps";
                       }
                       enum "30.1Mb" {
                         description "30.1 Mbps";
                       }
                       enum "30.4Mb" {
                         description "30.4 Mbps";
                       }
                       enum "30.8Mb" {
                         description "30.8 Mbps";
                       }
                       enum "31.1Mb" {
                         description "31.1 Mbps";
                       }
                       enum "31.5Mb" {
                         description "31.5 Mbps";
                       }
                       enum "31.9Mb" {
                         description "31.9 Mbps";
                       }
                       enum "32.2Mb" {
                         description "32.2 Mbps";
                       }
                       enum "32.6Mb" {
                         description "32.6 Mbps";
                       }
                       enum "32.9Mb" {
                         description "32.9 Mbps";
                       }
                       enum "33.3Mb" {
                         description "33.3 Mbps";
                       }
                       enum "33.7Mb" {
                         description "33.7 Mbps";
                       }
                       enum "34.0Mb" {
                         description "34.0 Mbps";
                       }
                     }
                   }
                 }
               }
               case case_3 {
                 container kentrox {
                   presence "enable kentrox";
                   description "Compatible with Kentrox CSU";
                   leaf subrate {
                     description "Set subrate value (only for E3 IQ interfaces)";
                     type union {
                       type string {
                         pattern "<.*>|$.*";
                       }
                       type uint32 {
                         range "1 .. 48";
                       }
                     }
                   }
                 }
               }
             }
           }
           choice payload-scrambler-choice {
             leaf payload-scrambler {
               description "Enable payload scrambling";
               type empty;
             }
             leaf no-payload-scrambler {
               description "Don't enable payload scrambling";
               type empty;
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf invert-data {
             description "Invert data";
             type empty;
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
           leaf buildout {
             description "Line buildout";
             units "feet";
             type union {
               type string {
                 pattern "<.*>|$.*";
               }
               type uint32 {
                 range "0 .. 450";
               }
             }
           }
           leaf atm-encapsulation {
             description "E3 interface encapsulation";
             type enumeration {
               enum "plcp" {
                 description "PLCP encapsulation";
               }
               enum "direct" {
                 description "ATM direct mapping";
               }
             }
           }
           leaf framing {
             description "E3 line format";
             type enumeration {
               enum "g.751" {
                 description "G.751 format";
               }
               enum "g.832" {
                 description "G.832 format";
               }
             }
           }
         }
         container e1-options {
           description "E1 interface-specific options";
           uses apply-advanced;
           leaf timeslots {
             description "Timeslots (1..32); for example, 1-4,6,9-11,32 (no space)";
             type string;
           }
           leaf loopback {
             description "Loopback mode";
             type enumeration {
               enum "local" {
                 description "Local loopback";
               }
               enum "remote" {
                 description "Remote loopback";
               }
             }
           }
           leaf framing {
             description "Framing mode";
             type enumeration {
               enum "g704" {
                 description "G704 mode with CRC4";
               }
               enum "unframed" {
                 description "Unframed mode";
               }
               enum "g704-no-crc4" {
                 description "G704 mode without CRC4";
               }
             }
           }
           leaf fcs {
             description "Frame checksum";
             type enumeration {
               enum "32" {
                 description "32-bit mode";
               }
               enum "16" {
                 description "16-bit mode";
               }
             }
           }
           leaf invert-data {
             description "Invert data";
             type empty;
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
         }
         container t1-options {
           description "T1 interface-specific options";
           uses apply-advanced;
           leaf timeslots {
             description "Timeslots (1..24; for example, 1-3,4,9,22-24 (no space)";
             type string;
           }
           leaf loopback {
             description "Loopback mode";
             type enumeration {
               enum "local" {
                 description "Local loopback";
               }
               enum "remote" {
                 description "Remote loopback";
               }
               enum "payload" {
                 description "Payload loopback";
               }
             }
           }
           leaf buildout {
             description "Line buildout";
             type enumeration {
               enum "0-132" {
                 description "Line buildout is between 0-132 feet";
               }
               enum "133-265" {
                 description "Line buildout is between 133-265 feet";
               }
               enum "266-398" {
                 description "Line buildout is between 266-398 feet";
               }
               enum "399-531" {
                 description "Line buildout is between 399-531 feet";
               }
               enum "532-655" {
                 description "Line buildout is between 532-655 feet";
               }
               enum "long-0db" {
                 description "Long buildout with 0 dB transmit attenuation";
               }
               enum "long-7.5db" {
                 description "Long buildout with 7.5 dB transmit attenuation";
               }
               enum "long-15db" {
                 description "Long buildout with 15 dB transmit attenuation";
               }
               enum "long-22.5db" {
                 description "Long buildout with 22.5 dB transmit attenuation";
               }
             }
           }
           leaf byte-encoding {
             description "Byte encoding";
             type enumeration {
               enum "nx64" {
                 description "8 bits per byte";
               }
               enum "nx56" {
                 description "7 bits per byte";
               }
             }
           }
           leaf line-encoding {
             description "Line encoding";
             type enumeration {
               enum "ami" {
                 description "Automatic mark inversion";
               }
               enum "b8zs" {
                 description "8-bit zero suppression";
               }
             }
           }
           leaf invert-data {
             description "Invert data";
             type empty;
           }
           leaf framing {
             description "Framing mode";
             type enumeration {
               enum "sf" {
                 description "Super frame";
               }
               enum "esf" {
                 description "Extended super frame";
               }
             }
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e3" {
                 description "Pattern is 2^3 - 1";
               }
               enum "pseudo-2e4" {
                 description "Pattern is 2^4 - 1";
               }
               enum "pseudo-2e5" {
                 description "Pattern is 2^5 - 1";
               }
               enum "pseudo-2e6" {
                 description "Pattern is 2^6 - 1";
               }
               enum "pseudo-2e7" {
                 description "Pattern is 2^7 - 1";
               }
               enum "pseudo-2e9-o153" {
                 description "Pattern is 2^9 - 1 (per O.153 standard)";
               }
               enum "pseudo-2e10" {
                 description "Pattern is 2^10 - 1";
               }
               enum "pseudo-2e11-o152" {
                 description "Pattern is 2^11 -1 (per O.152 standard)";
               }
               enum "pseudo-2e15-o151" {
                 description "Pattern is 2^15 - 1 (per O.151 standard)";
               }
               enum "pseudo-2e17" {
                 description "Pattern is 2^17 - 1";
               }
               enum "pseudo-2e18" {
                 description "Pattern is 2^18 - 1";
               }
               enum "pseudo-2e20-o153" {
                 description "Pattern is 2^20 - 1 (per O.153 standard)";
               }
               enum "pseudo-2e20-o151" {
                 description "Pattern is 2^20 - 1 (per O.151 standard)";
               }
               enum "pseudo-2e21" {
                 description "Pattern is 2^21 - 1";
               }
               enum "pseudo-2e22" {
                 description "Pattern is 2^22 - 1";
               }
               enum "pseudo-2e23-o151" {
                 description "Pattern is 2^23 (per O.151 standard)";
               }
               enum "pseudo-2e25" {
                 description "Pattern is 2^25 - 1";
               }
               enum "pseudo-2e28" {
                 description "Pattern is 2^28 - 1";
               }
               enum "pseudo-2e29" {
                 description "Pattern is 2^29 - 1";
               }
               enum "pseudo-2e31" {
                 description "Pattern is 2^31 - 1";
               }
               enum "pseudo-2e32" {
                 description "Pattern is 2^32 - 1";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 86400";
               }
             }
           }
           leaf remote-loopback-respond {
             description "Respond to loop requests from remote end";
             type empty;
           }
           leaf crc-major-alarm-threshold {
             description "CRC Major alarm threshold value";
             default "5e-5";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
             }
           }
           leaf crc-minor-alarm-threshold {
             description "CRC Minor alarm threshold value";
             default "5e-6";
             type enumeration {
               enum "1e-3" {
                 description "1 crc error in 10^3 bits";
               }
               enum "5e-4" {
                 description "5 crc errors in 10^4 bits";
               }
               enum "1e-4" {
                 description "1 crc error in 10^4 bits";
               }
               enum "5e-5" {
                 description "5 crc errors in 10^5 bits";
               }
               enum "1e-5" {
                 description "1 crc error in 10^5 bits";
               }
               enum "5e-6" {
                 description "5 crc errors in 10^6 bits";
               }
               enum "1e-6" {
                 description "1 crc error in 10^6 bits";
               }
             }
           }
         }
         container ds0-options {
           description "DS-0 interface-specific options";
           uses apply-advanced;
           leaf loopback {
             description "Loopback mode";
             type enumeration {
               enum "payload" {
                 description "Payload loopback";
               }
             }
           }
           leaf byte-encoding {
             description "Byte encoding";
             type enumeration {
               enum "nx64" {
                 description "8 bits per byte";
               }
               enum "nx56" {
                 description "7 bits per byte";
               }
             }
           }
           leaf invert-data {
             description "Invert data";
             type empty;
           }
           leaf fcs {
             description "Frame checksum";
             type enumeration {
               enum "32" {
                 description "32-bit mode";
               }
               enum "16" {
                 description "16-bit mode";
               }
             }
           }
           leaf idle-cycle-flag {
             description "Value to transmit in idle cycles";
             type enumeration {
               enum "flags" {
                 description "Transmit 0x7E in idle cycles";
               }
               enum "ones" {
                 description "Transmit 0xFF (all ones) in idle cycles";
               }
             }
           }
           leaf start-end-flag {
             description "Set start/end flags on transmission";
             type enumeration {
               enum "shared" {
                 description "Share start/end flags on transmit";
               }
               enum "filler" {
                 description "Send two idle cycles between start/end flags";
               }
             }
           }
           leaf bert-algorithm {
             description "Set BERT algorithm";
             type enumeration {
               enum "pseudo-2e11-o152" {
                 description "Pattern is 2^11 -1 (per O.152 standard)";
               }
               enum "pseudo-2e15-o151" {
                 description "Pattern is 2^15 - 1 (per O.151 standard)";
               }
               enum "pseudo-2e20-o153" {
                 description "Pattern is 2^20 - 1 (per O.153 standard)";
               }
               enum "pseudo-2e20-o151" {
                 description "Pattern is 2^20 - 1 (per O.151 standard)";
               }
               enum "all-ones-repeating" {
                 description "Repeating one bits";
               }
               enum "all-zeros-repeating" {
                 description "Repeating zero bits";
               }
               enum "alternating-ones-zeros" {
                 description "Alternating ones and zeros";
               }
               enum "alternating-double-ones-zeros" {
                 description "Alternating pairs of ones and zeros";
               }
               enum "repeating-3-in-24" {
                 description "3 bits in 24 are set";
               }
               enum "repeating-1-in-8" {
                 description "1 bit in 8 is set";
               }
               enum "repeating-1-in-4" {
                 description "1 bit in 4 is set";
               }
               enum "repeating-1-in-16" {
                 description "1 bit in 16 is set";
               }
             }
           }
           leaf bert-error-rate {
             description "Bit error rate (10^-n for n > 0, and zero for n = 0)";
             type union {
               type string {
                 pattern "<.*>|$.*";
               }
               type uint32 {
                 range "0 .. 7";
               }
             }
           }
           leaf bert-period {
             description "Length of BERT test";
             units "seconds";
             type union {
               type string {
                 pattern "<.*>|$.*";
               }
               type uint32 {
                 range "1 .. 240";
               }
             }
           }
         }
         container serial-options {
           description "Serial interface-specific options";
           uses apply-advanced;
           leaf line-protocol {
             description "Line protocol to be used";
             default "eia530";
             type enumeration {
               enum "eia530" {
                 description "Line protocol EIA530";
               }
               enum "v.35" {
                 description "Line protocol V.35";
               }
               enum "x.21" {
                 description "Line protocol X.21";
               }
             }
           }
           choice control_leads_choice {
             case case_1 {
               container dte-options {
                 description "DTE options/control leads";
                 uses apply-advanced;
                 leaf ignore-all {
                   description "Ignore all control leads";
                   type empty;
                 }
                 container dtr {
                   description "Data Transmit Ready signal handling";
                   choice dtr_choices {
                     case case_1 {
                       leaf assert {
                         description "Assert DTR signal";
                         type empty;
                       }
                     }
                     case case_2 {
                       leaf de-assert {
                         description "Deassert DTR signal";
                         type empty;
                       }
                     }
                     case case_3 {
                       leaf normal {
                         description "Normal DTR signal";
                         type empty;
                       }
                     }
                     case case_4 {
                       container auto-synchronize {
                         presence "enable auto-synchronize";
                         description "Normal DTR signal, with autoresynchronization";
                         uses apply-advanced;
                         leaf duration {
                           description "Duration of autoresynchronization";
                           units "milliseconds";
                           type union {
                             type string {
                               pattern "<.*>|$.*";
                             }
                             type uint16 {
                               range "1 .. 1000";
                             }
                           }
                         }
                         leaf interval {
                           description "Interval for autoresynchronization";
                           units "seconds";
                           type union {
                             type string {
                               pattern "<.*>|$.*";
                             }
                             type uint16 {
                               range "1 .. 31";
                             }
                           }
                         }
                       }
                     }
                   }
                 }
                 leaf control-signal {
                   description "X.21 control signal handling";
                   type enumeration {
                     enum "assert" {
                       description "Assert control signal";
                     }
                     enum "de-assert" {
                       description "Deassert control signal";
                     }
                     enum "normal" {
                       description "Normal control signal";
                     }
                   }
                 }
                 leaf rts {
                   description "Request To Send signal handling";
                   type enumeration {
                     enum "assert" {
                       description "Assert RTS signal";
                     }
                     enum "de-assert" {
                       description "Deassert RTS signal";
                     }
                     enum "normal" {
                       description "Normal RTS signal";
                     }
                   }
                 }
                 leaf dcd {
                   description "Data Carrier Detect signal handling";
                   type enumeration {
                     enum "require" {
                       description "Require DCD signal";
                     }
                     enum "ignore" {
                       description "Ignore DCD signal";
                     }
                     enum "normal" {
                       description "Normal DCD signal";
                     }
                   }
                 }
                 leaf dsr {
                   description "Data Set Ready signal handling";
                   type enumeration {
                     enum "require" {
                       description "Require DSR signal";
                     }
                     enum "ignore" {
                       description "Ignore DSR signal";
                     }
                     enum "normal" {
                       description "Normal DSR signal";
                     }
                   }
                 }
                 leaf cts {
                   description "Clear To Send signal handling";
                   type enumeration {
                     enum "require" {
                       description "Require CTS signal";
                     }
                     enum "ignore" {
                       description "Ignore CTS signal";
                     }
                     enum "normal" {
                       description "Normal CTS signal";
                     }
                   }
                 }
                 leaf indication {
                   description "X.21 Indication signal handling";
                   type enumeration {
                     enum "require" {
                       description "Require Indication signal";
                     }
                     enum "ignore" {
                       description "Ignore Indication signal";
                     }
                     enum "normal" {
                       description "Normal Indication signal";
                     }
                   }
                 }
                 leaf tm {
                   description "Test Mode signal handling";
                   type enumeration {
                     enum "require" {
                       description "Require TM signal";
                     }
                     enum "ignore" {
                       description "Ignore TM signal";
                     }
                     enum "normal" {
                       description "Normal TM signal";
                     }
                   }
                 }
               }
             }
             case case_2 {
             }
           }
           leaf dtr-circuit {
             description "Data Transmit Ready circuit mode";
             type enumeration {
               enum "balanced" {
                 description "Balanced signal";
               }
               enum "unbalanced" {
                 description "Unbalanced signal";
               }
             }
           }
           leaf dtr-polarity {
             description "Data Transmit Ready signal polarity";
             type enumeration {
               enum "positive" {
                 description "Positive polarity";
               }
               enum "negative" {
                 description "Negative polarity";
               }
             }
           }
           leaf rts-polarity {
             description "Request To Send signal polarity";
             type enumeration {
               enum "positive" {
                 description "Positive polarity";
               }
               enum "negative" {
                 description "Negative polarity";
               }
             }
           }
           leaf control-polarity {
             description "X.21 Control signal polarity";
             type enumeration {
               enum "positive" {
                 description "Positive polarity";
               }
               enum "negative" {
                 description "Negative polarity";
               }
             }
           }
           leaf dcd-polarity {
             description "Data Carrier Detect signal polarity";
             type enumeration {
               enum "positive" {
                 description "Positive polarity";
               }
               enum "negative" {
                 description "Negative polarity";
               }
             }
           }
           leaf dsr-polarity {
             description "Data Set Ready signal polarity";
             type enumeration {
               enum "positive" {
                 description "Positive polarity";
               }
               enum "negative" {
                 description "Negative polarity";
               }
             }
           }
           leaf cts-polarity {
             description "Clear To Send signal polarity";
             type enumeration {
               enum "positive" {
                 description "Positive polarity";
               }
               enum "negative" {
                 description "Negative polarity";
               }
             }
           }
           leaf indication-polarity {
             description "X.21 Indication signal polarity";
             type enumeration {
               enum "positive" {
                 description "Positive polarity";
               }
               enum "negative" {
                 description "Negative polarity";
               }
             }
           }
           leaf tm-polarity {
             description "Test Mode signal polarity";
             type enumeration {
               enum "positive" {
                 description "Positive polarity";
               }
               enum "negative" {
                 description "Negative polarity";
               }
             }
           }
           leaf clocking-mode {
             description "Clock mode";
             type enumeration {
               enum "dce" {
                 description "DCE timing (DTE mode only, not valid for X.21)";
               }
               enum "internal" {
                 description "Internal baud timing";
               }
               enum "loop" {
                 description "Loop timing";
               }
             }
           }
           leaf transmit-clock {
             description "Transmit clock phase";
             type enumeration {
               enum "invert" {
                 description "Shift clock phase 180 degrees";
               }
             }
           }
           leaf clock-rate {
             description "Interface clock rate";
             type enumeration {
               enum "2.048mhz" {
                 description "2.048 MHz";
               }
               enum "2.341mhz" {
                 description "2.341 MHz";
               }
               enum "2.731mhz" {
                 description "2.731 MHz";
               }
               enum "3.277mhz" {
                 description "3.277 MHz";
               }
               enum "4.096mhz" {
                 description "4.096 MHz";
               }
               enum "5.461mhz" {
                 description "5.461 MHz";
               }
               enum "8.192mhz" {
                 description "8.192 MHz";
               }
               enum "16.384mhz" {
                 description "16.384 MHz";
               }
               enum "1.2khz" {
                 description "1.2 KHz";
               }
               enum "2.4khz" {
                 description "2.4 KHz";
               }
               enum "9.6khz" {
                 description "9.6 KHz";
               }
               enum "19.2khz" {
                 description "19.2 KHz";
               }
               enum "38.4khz" {
                 description "38.4 KHz";
               }
               enum "56.0khz" {
                 description "56.0 KHz";
               }
               enum "64.0khz" {
                 description "64.0 KHz";
               }
               enum "72.0khz" {
                 description "72.0 KHz";
               }
               enum "125.0khz" {
                 description "125.0 KHz";
               }
               enum "148.0khz" {
                 description "148.0 KHz";
               }
               enum "250.0khz" {
                 description "250.0 KHz";
               }
               enum "500.0khz" {
                 description "500.0 KHz";
               }
               enum "800.0khz" {
                 description "800.0 KHz";
               }
               enum "1.0mhz" {
                 description "1.0 MHz";
               }
               enum "1.3mhz" {
                 description "1.3 MHz";
               }
               enum "2.0mhz" {
                 description "2.0 MHz";
               }
               enum "4.0mhz" {
                 description "4.0 MHz";
               }
               enum "8.0mhz" {
                 description "8.0 MHz";
               }
             }
           }
           leaf loopback {
             description "Loopback mode";
             type enumeration {
               enum "local" {
                 description "Local loopback";
               }
               enum "remote" {
                 description "Remote/LIU loopback";
               }
               enum "dce-local" {
                 description "DCE local loopback (DTE mode only)";
               }
               enum "dce-remote" {
                 description "DCE remote loopback";
               }
             }
           }
           leaf encoding {
             description "Line encoding";
             type enumeration {
               enum "nrz" {
                 description "Non-Return-To-Zero";
               }
               enum "nrzi" {
                 description "Non-Return-To-Zero-Invertible";
               }
             }
           }
         }
         choice gratuitous-arp-reply-choice {
           leaf gratuitous-arp-reply {
             description "Enable gratuitous ARP reply";
             type empty;
           }
           leaf no-gratuitous-arp-reply {
             description "Don't enable gratuitous ARP reply";
             type empty;
           }
         }
         choice no-gratuitous-arp-request-choice {
           leaf no-gratuitous-arp-request {
             description "Ignore gratuitous ARP request";
             type empty;
           }
           leaf no-no-gratuitous-arp-request {
             description "Don't ignore gratuitous ARP request";
             type empty;
           }
         }
         container ether-options {
           description "Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice source-filtering-choice {
             leaf source-filtering {
               description "Enable source address filtering";
               type empty;
             }
             leaf no-source-filtering {
               description "Don't enable source address filtering";
               type empty;
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container storm-control {
               description "Storm control profile name to bind";
               uses apply-advanced;
               leaf profile-name {
                 description "Profile name";
                 type string;
                 mandatory true;
               }
             }
             container recovery-timeout {
               description "Recovery timeout for this interface";
               leaf time-in-seconds {
                 units "seconds";
                 type union {
                   type string {
                     pattern "<.*>|$.*";
                   }
                   type uint32 {
                     range "10 .. 3600";
                   }
                 }
               }
             }
             choice mac-learn-enable-choice {
               leaf mac-learn-enable {
                 description "Learn MAC addresses dynamically";
                 type empty;
               }
               leaf no-mac-learn-enable {
                 description "Don't learn MAC addresses dynamically";
                 type empty;
               }
             }
           }
           leaf asynchronous-notification {
             description "Enable sending asynchronous notification to peer on CCC-down";
             type empty;
           }
           list source-address-filter {
             key name;
             description "Source address filters";
             leaf name {
               description "Remote MAC address";
               type jt:mac-addr;
             }
           }
           choice auto-negotiation-choice {
             leaf auto-negotiation {
               description "Enable auto-negotiation";
               type empty;
             }
             leaf no-auto-negotiation {
               description "Don't enable auto-negotiation";
               type empty;
             }
           }
           choice flow-control-choice {
             leaf flow-control {
               description "Enable flow control";
               type empty;
             }
             leaf no-flow-control {
               description "Don't enable flow control";
               type empty;
             }
           }
           leaf link-mode {
             description "Link duplex";
             type enumeration {
               enum "automatic" {
                 description "Automatic negotiate duplex ";
               }
               enum "half-duplex" {
                 description "Half-duplex operation";
               }
               enum "full-duplex" {
                 description "Full-duplex operation";
               }
             }
           }
           container mpls {
             description "MPLS options";
             uses mpls_ifd_options;
           }
           leaf ignore-l3-incompletes {
             description "Ignore L3 incomplete errors";
             type empty;
           }
           leaf no-auto-mdix {
             description "Disable auto MDI/MDIX";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
               enum "fec-etc" {
                 description "ETC fec based on IEEE 802.3 Clause 119 for 800G links";
               }
               enum "fec172" {
                 description "IEEE 802.3dj Clause 172, RS-FEC for 800G links";
               }
             }
           }
           container speed {
             description "Specify speed";
             choice automatic {
               case case_1 {
                 container auto-negotiation {
                   presence "enable auto-negotiation";
                   description "Enable auto-negotiation";
                   leaf auto-negotiate-10-100 {
                     description "Limits the auto-negotiation to 10m/100m only";
                     type empty;
                   }
                 }
               }
               case case_2 {
                 leaf ethernet-10m {
                   description "10Mbps";
                   type empty;
                 }
               }
               case case_3 {
                 leaf ethernet-100m {
                   description "100Mbps";
                   type empty;
                 }
               }
               case case_4 {
                 leaf ethernet-1g {
                   description "1Gbps";
                   type empty;
                 }
               }
               case case_5 {
                 leaf ethernet-10g {
                   description "10Gbps";
                   type empty;
                 }
               }
             }
           }
           container ieee-802.3ad {
             description "IEEE 802.3ad";
             uses apply-advanced;
             container lacp {
               description "Link Aggregation Control Protocol configuration";
               uses apply-advanced;
               leaf force-up {
                 description "Keep the port up in absence of received LACPDU";
                 type empty;
               }
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
             container link-protection-sub-group {
               description "Link Protection subgroup configuration";
               uses apply-advanced;
               leaf subgroup-name {
                 description "Name of the subgroup";
                 type string {
                   length "2 .. 64";
                 }
               }
             }
             leaf port-priority {
               description "Link protection Priority of the port (0 ... 65535)";
               type union {
                 type uint16;
                 type string {
                   pattern "<.*>|$.*";
                 }
               }
             }
           }
           leaf ieee-802-3az-eee {
             description "IEEE 802.3az Energy Efficient Ethernet(EEE)";
             type empty;
           }
           leaf mdi-mode {
             description "Cable cross-over mode";
             type enumeration {
               enum "auto" {
                 description "Automatic mdi/mdi-x mode";
               }
               enum "force" {
                 description "Enable auto-MDIX always";
               }
               enum "mdi" {
                 description "MDI(straight through) mode";
               }
               enum "mdix" {
                 description "MDI Cross-over mode";
               }
             }
           }
           leaf autostate-exclude {
             description "Interface will not contribute to IRB state";
             type empty;
           }
         }
         container fibrechannel-options {
           description "Fibre Channel interface-specific options";
           uses apply-advanced;
           choice loopback-choice {
             leaf loopback {
               description "Enable loopback";
               type empty;
             }
             leaf no-loopback {
               description "Don't enable loopback";
               type empty;
             }
           }
           leaf bb-sc-n {
             description "B2B state change number";
             type union {
               type string {
                 pattern "<.*>|$.*";
               }
               type uint16 {
                 range "0 .. 15";
               }
             }
           }
           leaf speed {
             description "Specify speed";
             type enumeration {
               enum "auto-negotiation" {
                 description "Enable auto-negotiation";
               }
               enum "1g" {
                 description "1Gbps";
               }
               enum "2g" {
                 description "2Gbps";
               }
               enum "4g" {
                 description "4Gbps";
               }
               enum "8g" {
                 description "8Gbps";
               }
             }
           }
         }
         container gigether-options {
           description "Gigabit Ethernet interface-specific options";
           uses apply-advanced;
           choice loopback-choice {
             leaf loopback {
               description "Enable loopback";
               type empty;
             }
             leaf no-loopback {
               description "Don't enable loopback";
               type empty;
             }
           }
           leaf loopback-remote {
             description "Enable remote loopback";
             type empty;
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           choice auto_negotiation_option {
             case case_1 {
               leaf no-auto-negotiation {
                 description "Disable auto-negotiation";
                 type empty;
               }
             }
             case case_2 {
               container auto-negotiation {
                 presence "enable auto-negotiation";
                 description "Enable auto-negotiation";
                 leaf remote-fault {
                   type enumeration {
                     enum "local-interface-offline" {
                       description "Disable local interface";
                     }
                     enum "local-interface-online" {
                       description "Enable local interface";
                     }
                   }
                 }
               }
             }
           }
           leaf asynchronous-notification {
             description "Enable sending asynchronous notification to peer on CCC-down";
             type empty;
           }
           list source-address-filter {
             key name;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             container ethernet-policer-profile {
               description "Ethernet level CoS-based policer configuration";
               uses apply-advanced;
               container ieee802.1-priority-map {
                 presence "enable ieee802.1-priority-map";
                 description "Premium priority values for IEEE 802.1p bits";
                 status deprecated;
                 uses apply-advanced;
                 leaf-list premium {
                   ordered-by user;
                   description "Premium policer priority map";
                   type union {
                     type string {
                       pattern "<.*>|$.*";
                     }
                     type uint32 {
                       range "0 .. 7";
                     }
                   }
                 }
               }
               container input-priority-map {
                 description "Input policer priority map";
                 uses cos_policer_input_priority_map;
               }
               container output-priority-map {
                 description "Output policer priority map";
                 uses cos_policer_output_priority_map;
               }
               list policer {
                 key name;
                 ordered-by user;
                 description "Policer template definition";
                 uses cos_policer;
               }
             }
             container accept-from {
               description "Accept traffic from or to specified remote MAC";
               status deprecated;
               uses apply-advanced;
               list mac-address {
                 key name;
                 description "Remote MAC";
                 uses mac_list;
               }
             }
             choice reject-the-rest-choice {
               leaf reject-the-rest {
                 description "Accept traffic from only the specified MAC addresses";
                 status deprecated;
                 type empty;
               }
               leaf no-reject-the-rest {
                 description "Don't accept traffic from only the specified MAC addresses";
                 status deprecated;
                 type empty;
               }
             }
             leaf mac-learn-enable {
               description "Learn MAC addresses dynamically";
               type empty;
             }
           }
           container mpls {
             description "MPLS options";
             uses mpls_ifd_options;
           }
           leaf ignore-l3-incompletes {
             description "Ignore L3 incomplete errors";
             type empty;
           }
           leaf ieee-802-3az-eee {
             description "IEEE 802.3az Energy Efficient Ethernet(EEE)";
             type empty;
           }
           leaf fec {
             description "Forward Error Correction mode";
             type enumeration {
               enum "none" {
                 description "FEC disabled";
               }
               enum "fec91" {
                 description "IEEE 802.3bj Clause 91, Reed-Solomon FEC (RS-FEC)";
               }
               enum "fec74" {
                 description "FEC74 enabled";
               }
               enum "fec108" {
                 description "IEEE 802.3by Clause 108, Reed-Solomon FEC (RS-FEC) on 25g links";
               }
               enum "fec161" {
                 description "IEEE 802.3ck Clause 161 for 100G electrical links";
               }
             }
           }
         }
         container optics-options {
           description "Optics options";
           uses apply-advanced;
           leaf wavelength {
             description "Wavelength of the optics (nanometers) for 50Ghz/100Ghz spacing";
             type enumeration {
               enum "1611.79" {
                 description "1611.79 nm/186.000000 THz 3.125/6.25/12.5/50/75/100GHz spacing";
               }
               enum "1611.76" {
                 description "1611.76 nm/186.003125 THz 3.125GHz spacing";
               }
               enum "1611.73" {
                 description "1611.73 nm/186.006250 THz 3.125/6.25GHz spacing";
               }
               enum "1611.71" {
                 description "1611.71 nm/186.009375 THz 3.125GHz spacing";
               }
               enum "1611.68" {
                 description "1611.68 nm/186.012500 THz 3.125/6.25/12.5GHz spacing";
               }
               enum "1611.65" {
                 description "1611.65 nm/186.015625 THz 3.125GHz spacing";
               }
               enum "1611.62" {
                 description "1611.62 nm/186.018750 THz 3.125/6.25GHz spacing";
               }
               enum "1611.60" {
                 description "1611.60 nm/186.021875 THz 3.125GHz spacing";
               }
               enum "1611.57" {
                 description "1611.57 nm/186.025000 THz 3.125/6.25/12.5GHz spacing";
               }
               enum "1611.54" {
                 description "1611.54 nm/186.028125 THz 3.125GHz spacing";
               }
               enum "1611.52" {
                 description "1611.52 nm/186.031250 THz 3.125/6.25GHz spacing";
               }
               enum "1611.49" {
                 description "1611.49 nm/186.034375 THz 3.125GHz spacing";
               }
               enum "1611.46" {
                 description "1611.46 nm/186.037500 THz 3.125/6.25/12.5GHz spacing";
               }
               enum "1611.44" {
                 description "1611.44 nm/186.040625 THz 3.125GHz spacing";
               }
               enum "1611.41" {
                 description "1611.41 nm/186.043750 THz 3.125/6.25GHz spacing";
               }
               enum "1611.38" {
                 description "1611.38 nm/186.046875 THz 3.125GHz spacing";
               }
               enum "1611.35" {
                 description "1611.35 nm/186.050000 THz 3.125/6.25/12.5/50/75GHz spacing";
               }
               enum "1611.33" {
                 description "1611.33 nm/186.053125 THz 3.125GHz spacing";
               }
               enum "1611.30" {
                 description "1611.30 nm/186.056250 THz 3.125/6.25GHz spacing";
               }
               enum "1611.27" {
                 description "1611.27 nm/186.059375 THz 3.125GHz spacing";
               }
               enum "1611.25" {
                 description "1611.25 nm/186.062500 THz 3.125/6.25/12.5GHz spacing";
               }
               enum "1611.22" {
                 description "1611.22 nm/186.065625 THz 3.125GHz spacing";
               }
               enum "1611.19" {
                 description "1611.19 nm/186.068750 THz 3.125/6.25GHz spacing";
               }
               enum "1611.16" {
                 description "1611.16 nm/186.071875 THz 3.125GHz spacing";
               }
               enum "1611.14" {
                 description "1611.14 nm/186.075000 THz 3.125/6.25/12.5GHz spacing";
               }
               enum "1611.11" {
                 description "1611.11 nm/186.078125 THz 3.125GHz spacing";
               }
               enum "1611.08" {
                 description "1611.08 nm/186.081250 THz 3.125/6.25GHz spacing";
               }
               enum "1611.06" {
                 description "1611.06 nm/186.084375 THz 3.125GHz spacing";
               }
               enum "1611.03" {
                 description "1611.03 nm/186.087500 THz 3.125/6.25/12.5GHz spacing";
               }
               enum "1611.00" {
                 description "1611.00 nm/186.090625 THz 3.125GHz spacing";
               }
               enum "1610.98" {
                 description "1610.98 nm/186.093750 THz 3.125/6.25GHz spacing";
               }
               enum "1610.95" {
                 description "1610.95 nm/186.096875 THz 3.125GHz spacing";
               }
               enum "1610.92" {
                 description "1610.92 nm/186.100000 THz 3.125/6.25/12.5/100GHz spacing";
               }
               enum "1610.89" {
                 description "1610.89 nm/186.103125 THz 3.125GHz spacing";
               }
               enum "1610.87" {
                 description "1610.87 nm/186.106250 THz 3.125/6.25GHz spacing";
               }
               enum "1610.84" {
                 description "1610.84 nm/186.109375 THz 3.125GHz spacing";
               }
               enum "1610.81" {
                 description "1610.81 nm/186.112500 THz 3.125/6.25/12.5GHz spacing";
               }
               enum "1610.79" {
                 description "1610.79 nm/186.115625 THz 3.125GHz spacing";
               }
               enum "1610.76" {
                 description "1610.76 nm/186.118750 THz 3.125/6.25GHz spacing";
               }
               enum "1610.73" {
                 description "1610.73 nm/186.121875 THz 3.125GHz spacing";
               }
               enum "1610.70" {
                 description "1610.70 nm/186.125000 THz 3.125/6.25/12.5/75GHz spacing";
               }
               enum "1610.68" {
                 description "1610.68 nm/186.128125 THz 3.125GHz spacing";
               }
               enum "1610.65" {
                 description "1610.65 nm/186.131250 THz 3.125/6.25GHz spacing";
               }
               enum "1610.62" {
                 description "1610.62 nm/186.134375 THz 3.125GHz spacing";
               }
               enum "1610.60" {
                 description "1610.60 nm/186.137500 THz 3.125/6.25/12.5GHz spacing";
               }
               enum "1610.57" {
                 description "1610.57 nm/186.140625 THz 3.125GHz spacing";
               }
               enum "1610.54" {
                 description "1610.54 nm/186.143750 THz 3.125/6.25GHz spacing";
               }
               enum "1610.52" {
                 description "1610.52 nm/186.146875 THz 3.125GHz spacing";
               }
               enum "1610.49" {
                 description "1610.49 nm/186.150000 THz 3.125/6.25/12.5/50GHz spacing";
               }
               enum "1610.46" {
                 description "1610.46 nm/186.153125 THz 3.125GHz spacing";
               }
               enum "1610.43" {
                 description "1610.43 nm/186.156250 THz 3.125/6.25GHz spacing";
               }
               enum "1610.41" {
                 description "1610.41 nm/186.159375 THz 3.125GHz spacing";
               }
               enum "1610.38" {
                 description "1610.38 nm/186.162500 THz 3.125/6.25/12.5GHz spacing";
               }
               enum "1610.35" {
                 description "1610.35 nm/186.165625 THz 3.125GHz spacing";
               }
               enum "1610.33" {
                 description "1610.33 nm/186.168750 THz 3.125/6.25GHz spacing";
               }
               enum "1610.30" {
                 description "1610.30 nm/186.171875 THz 3.125GHz spacing";
               }
               enum "1610.27" {
                 description "1610.27 nm/186.175000 THz 3.125/6.25/12.5GHz spacing";
               }
               enum "1610.25" {
                 description "1610.25 nm/186.178125 THz 3.125GHz spacing";
               }
               enum "1610.22" {
                 description "1610.22 nm/186.181250 THz 3.125/6.25GHz spacing";
               }
               enum "1610.19" {
                 description "1610.19 nm/186.184375 THz 3.125GHz spacing";
               }
               enum "1610.16" {
                 description "1610.16 nm/186.187500 THz 3.125/6.25/12.5GHz spacing";
               }
               enum "1610.14" {
                 description "1610.14 nm/186.190625 THz 3.125GHz spacing";
               }
               enum "1610.11" {
                 description "1610.11 nm/186.193750 THz 3.125/6.25GHz spacing";
               }
               enum "1610.08" {
                 description "1610.08 nm/186.196875 THz 3.125GHz spacing";
               }
               enum "1610.06" {
                 description "1610.06 nm/186.200000 THz 3.125/6.25/12.5/100GHz spacing";
               }
               enum "1610.03" {
                 description "1610.03 nm/186.203125 THz 3.125GHz spacing";
               }
               enum "1610.00" {
                 description "1610.00 nm/186.206250 THz 3.125/6.25GHz spacing";
               }
               enum "1609.98" {
                 description "1609.98 nm/186.209375 THz 3.125GHz spacing";
               }
               enum "1609.95" {
                 description "1609.95 nm/186.212500 THz 3.125/6.25/12.5GHz spacing";
               }
               enum "1609.92" {
                 description "1609.92 nm/186.215625 THz 3.125GHz spacing";
               }
               enum "1609.89" {
                 description "1609.89 nm/186.218750 THz 3.125/6.25GHz spacing";
               }
               enum "1609.87" {
                 description "1609.87 nm/186.221875 THz 3.125GHz spacing";
               }
               enum "1609.84" {
                 description "1609.84 nm/186.225000 THz 3.125/6.25/12.5GHz spacing";
               }
               enum "1609.81" {
                 description "1609.81 nm/186.228125 THz 3.125GHz spacing";
               }
               enum "1609.79" {
                 description "1609.79 nm/186.231250 THz 3.125/6.25GHz spacing";
               }
               enum "1609.76" {
                 description "1609.76 nm/186.234375 THz 3.125GHz spacing";
               }
               enum "1609.73" {
                 description "1609.73 nm/186.237500 THz 3.125/6.25/12.5GHz spacing";
               }
               enum "1609.70" {
                 description "1609.70 nm/186.240625 THz 3.125GHz spacing";
               }
               enum "1609.68" {
                 description "1609.68 nm/186.243750 THz 3.125/6.25GHz spacing";
               }
               enum "1609.65" {
                 description "1609.65 nm/186.246875 THz 3.125GHz spacing";
               }
               enum "1609.62" {
                 description "1609.62 nm/186.250000 THz 3.125/6.25/12.5/50GHz spacing";
               }
               enum "1609.60" {
                 description "1609.60 nm/186.253125 THz 3.125GHz spacing";
               }
               enum "1609.57" {
                 description "1609.57 nm/186.256250 THz 3.125/6.25GHz spacing";
               }
               enum "1609.54" {
                 description "1609.54 nm/186.259375 THz 3.125GHz spacing";
               }
               enum "1609.52" {
                 description "1609.52 nm/186.262500 THz 3.125/6.25/12.5GHz spacing";
               }
               enum "1609.49" {
                 description "1609.49 nm/186.265625 THz 3.125GHz spacing";
               }
               enum "1609.46" {
                 description "1609.46 nm/186.268750 THz 3.125/6.25GHz spacing";
               }
               enum "1609.43" {
                 description "1609.43 nm/186.271875 THz 3.125GHz spacing";
               }
               enum "1609.41" {
                 description "1609.41 nm/186.275000 THz 3.125/6.25/12.5/75GHz spacing";
               }
               enum "1609.38" {
                 description "1609.38 nm/186.278125 THz 3.125GHz spacing";
               }
               enum "1609.35" {
                 description "1609.35 nm/186.281250 THz 3.125/6.25GHz spacing";
               }
               enum "1609.33" {
                 description "1609.33 nm/186.284375 THz 3.125GHz spacing";
               }
               enum "1609.30" {
                 description "1609.30 nm/186.287500 THz 3.125/6.25/12.5GHz spacing";
               }
               enum "1609.27" {
                 description "1609.27 nm/186.290625 THz 3.125GHz spacing";
               }
               enum "1609.25" {
                 description "1609.25 nm/186.293750 THz 3.125/6.25GHz spacing";
               }
               enum "1609.22" {
                 description "1609.22 nm/186.296875 THz 3.125GHz spacing";
               }
               enum "1609.19" {
                 description "1609.19 nm/186.300000 THz 3.125/6.25/12.5/50/75/100GHz spacing";
               }
               enum "1609.16" {
                 description "1609.16 nm/186.303125 THz 3.125GHz spacing";
               }
               enum "1609.14" {
                 description "1609.14 nm/186.306250 THz 3.125/6.25GHz spacing";
               }
               enum "1609.11" {
                 description "1609.11 nm/186.309375 THz 3.125GHz spacing";
               }
               enum "1609.08" {
                 description "1609.08 nm/186.312500 THz 3.125/6.25/12.5GHz spacing";
               }
               enum "1609.06" {
                 description "1609.06 nm/186.315625 THz 3.125GHz spacing";
               }
               enum "1609.03" {
                 description "1609.03 nm/186.318750 THz 3.125/6.25GHz spacing";
               }
               enum "1609.00" {
                 description "1609.00 nm/186.321875 THz 3.125GHz spacing";
               }
               enum "1608.98" {
                 description "1608.98 nm/186.325000 THz 3.125/6.25/12.5GHz spacing";
               }
               enum "1608.95" {
                 description "1608.95 nm/186.328125 THz 3.125GHz spacing";
               }
               enum "1608.92" {
                 description "1608.92 nm/186.331250 THz 3.125/6.25GHz spacing";
               }
               enum "1608.90" {
                 description "1608.90 nm/186.334375 THz 3.125GHz spacing";
               }
               enum "1608.87" {
                 description "1608.87 nm/186.337500 THz 3.125/6.25/12.5GHz spacing";
               }
               enum "1608.84" {
                 description "1608.84 nm/186.340625 THz 3.125GHz spacing";
               }
               enum "1608.81" {
                 description "1608.81 nm/186.343750 THz 3.125/6.25GHz spacing";
               }
               enum "1608.79" {
                 description "1608.79 nm/186.346875 THz 3.125GHz spacing";
               }
               enum "1608.76" {
                 description "1608.76 nm/186.350000 THz 3.125/6.25/12.5/50/75GHz spacing";
               }
               enum "1608.73" {
                 description "1608.73 nm/186.353125 THz 3.125GHz spacing";
               }
               enum "1608.71" {
                 description "1608.71 nm/186.356250 THz 3.125/6.25GHz spacing";
               }
               enum "1608.68" {
                 description "1608.68 nm/186.359375 THz 3.125GHz spacing";
               }
               enum "1608.65" {
                 description "1608.65 nm/186.362500 THz 3.125/6.25/12.5GHz spacing";
               }
               enum "1608.63" {
                 description "1608.63 nm/186.365625 THz 3.125GHz spacing";
               }
               enum "1608.60" {
                 description "1608.60 nm/186.368750 THz 3.125/6.25GHz spacing";
               }
               enum "1608.57" {
                 description "1608.57 nm/186.371875 THz 3.125GHz spacing";
               }
               enum "1608.54" {
                 description "1608.54 nm/186.375000 THz 3.125/6.25/12.5GHz spacing";
               }
               enum "1608.52" {
                 description "1608.52 nm/186.378125 THz 3.125GHz spacing";
               }
               enum "1608.49" {
                 description "1608.49 nm/186.381250 THz 3.125/6.25GHz spacing";
               }
               enum "1608.46" {
                 description "1608.46 nm/186.384375 THz 3.125GHz spacing";
               }
               enum "1608.44" {
                 description "1608.44 nm/186.387500 THz 3.125/6.25/12.5GHz spacing";
               }
               enum "1608.41" {
                 description "1608.41 nm/186.390625 THz 3.125GHz spacing";
               }
               enum "1608.38" {
                 description "1608.38 nm/186.393750 THz 3.125/6.25GHz spacing";
               }
               enum "1608.36" {
                 description "1608.36 nm/186.396875 THz 3.125GHz spacing";
               }
               enum "1608.33" {
                 description "1608.33 nm/186.400000 THz 3.125/6.25/12.5/100GHz spacing";
               }
               enum "1608.30" {
                 description "1608.30 nm/186.403125 THz 3.125GHz spacing";
               }
               enum "1608.27" {
                 description "1608.27 nm/186.406250 THz 3.125/6.25GHz spacing";
               }
               enum "1608.25" {
                 description "1608.25 nm/186.409375 THz 3.125GHz spacing";
               }
               enum "1608.22" {
                 description "1608.22 nm/186.412500 THz 3.125/6.25/12.5GHz spacing";
               }
               enum "1608.19" {
                 description "1608.19 nm/186.415625 THz 3.125GHz spacing";
               }
               enum "1608.17" {
                 description "1608.17 nm/186.418750 THz 3.125/6.25GHz spacing";
               }
               enum "1608.14" {
                 description "1608.14 nm/186.421875 THz 3.125GHz spacing";
               }
               enum "1608.11" {
                 description "1608.11 nm/186.425000 THz 3.125/6.25/12.5/75GHz spacing";
               }
               enum "1608.09" {
                 description "1608.09 nm/186.428125 THz 3.125GHz spacing";
               }
               enum "1608.06" {
                 description "1608.06 nm/186.431250 THz 3.125/6.25GHz spacing";
               }
               enum "1608.03" {
                 description "1608.03 nm/186.434375 THz 3.125GHz spacing";
               }
               enum "1608.01" {
                 description "1608.01 nm/186.437500 THz 3.125/6.25/12.5GHz spacing";
               }
               enum "1607.98" {
                 description "1607.98 nm/186.440625 THz 3.125GHz spacing";
               }
               enum "1607.95" {
                 description "1607.95 nm/186.443750 THz 3.125/6.25GHz spacing";
               }
               enum "1607.92" {
                 description "1607.92 nm/186.446875 THz 3.125GHz spacing";
               }
               enum "1607.90" {
                 description "1607.90 nm/186.450000 THz 3.125/6.25/12.5/50GHz spacing";
               }
               enum "1607.87" {
                 description "1607.87 nm/186.453125 THz 3.125GHz spacing";
               }
               enum "1607.84" {
                 description "1607.84 nm/186.456250 THz 3.125/6.25GHz spacing";
               }
               enum "1607.82" {
                 description "1607.82 nm/186.459375 THz 3.125GHz spacing";
               }
               enum "1607.79" {
                 description "1607.79 nm/186.462500 THz 3.125/6.25/12.5GHz spacing";
               }
               enum "1607.76" {
                 description "1607.76 nm/186.465625 THz 3.125GHz spacing";
               }
               enum "1607.74" {
                 description "1607.74 nm/186.468750 THz 3.125/6.25GHz spacing";
               }
               enum "1607.71" {
                 description "1607.71 nm/186.471875 THz 3.125GHz spacing";
               }
               enum "1607.68" {
                 description "1607.68 nm/186.475000 THz 3.125/6.25/12.5GHz spacing";
               }
               enum "1607.65" {
                 description "1607.65 nm/186.478125 THz 3.125GHz spacing";
               }
               enum "1607.63" {
                 description "1607.63 nm/186.481250 THz 3.125/6.25GHz spacing";
               }
               enum "1607.60" {
                 description "1607.60 nm/186.484375 THz 3.125GHz spacing";
               }
               enum "1607.57" {
                 description "1607.57 nm/186.487500 THz 3.125/6.25/12.5GHz spacing";
               }
               enum "1607.55" {
                 description "1607.55 nm/186.490625 THz 3.125GHz spacing";
               }
               enum "1607.52" {
                 description "1607.52 nm/186.493750 THz 3.125/6.25GHz spacing";
               }
               enum "1607.49" {
                 description "1607.49 nm/186.496875 THz 3.125GHz spacing";
               }
               enum "1607.47" {
                 description "1607.47 nm/186.500000 THz 3.125/6.25/12.5/100GHz spacing";
               }
               enum "1607.44" {
                 description "1607.44 nm/186.503125 THz 3.125GHz spacing";
               }
               enum "1607.41" {
                 description "1607.41 nm/186.506250 THz 3.125/6.25GHz spacing";
               }
               enum "1607.39" {
                 description "1607.39 nm/186.509375 THz 3.125GHz spacing";
               }
               enum "1607.36" {
                 description "1607.36 nm/186.512500 THz 3.125/6.25/12.5GHz spacing";
               }
               enum "1607.33" {
                 description "1607.33 nm/186.515625 THz 3.125GHz spacing";
               }
               enum "1607.30" {
                 description "1607.30 nm/186.518750 THz 3.125/6.25GHz spacing";
               }
               enum "1607.28" {
                 description "1607.28 nm/186.521875 THz 3.125GHz spacing";
               }
               enum "1607.25" {
                 description "1607.25 nm/186.525000 THz 3.125/6.25/12.5GHz spacing";
               }
               enum "1607.22" {
                 description "1607.22 nm/186.528125 THz 3.125GHz spacing";
               }
               enum "1607.20" {
                 description "1607.20 nm/186.531250 THz 3.125/6.25GHz spacing";
               }
               enum "1607.17" {
                 description "1607.17 nm/186.534375 THz 3.125GHz spacing";
               }
               enum "1607.14" {
                 description "1607.14 nm/186.537500 THz 3.125/6.25/12.5GHz spacing";
               }
               enum "1607.12" {
                 description "1607.12 nm/186.540625 THz 3.125GHz spacing";
               }
               enum "1607.09" {
                 description "1607.09 nm/186.543750 THz 3.125/6.25GHz spacing";
               }
               enum "1607.06" {
                 description "1607.06 nm/186.546875 THz 3.125GHz spacing";
               }
               enum "1607.04" {
                 description "1607.04 nm/186.550000 THz 3.125/6.25/12.5/50GHz spacing";
               }
               enum "1607.01" {
                 description "1607.01 nm/186.553125 THz 3.125GHz spacing";
               }
               enum "1606.98" {
                 description "1606.98 nm/186.556250 THz 3.125/6.25GHz spacing";
               }
               enum "1606.95" {
                 description "1606.95 nm/186.559375 THz 3.125GHz spacing";
               }
               enum "1606.93" {
                 description "1606.93 nm/186.562500 THz 3.125/6.25/12.5GHz spacing";
               }
               enum "1606.90" {
                 description "1606.90 nm/186.565625 THz 3.125GHz spacing";
               }
               enum "1606.87" {
                 description "1606.87 nm/186.568750 THz 3.125/6.25GHz spacing";
               }
               enum "1606.85" {
                 description "1606.85 nm/186.571875 THz 3.125GHz spacing";
               }
               enum "1606.82" {
                 description "1606.82 nm/186.575000 THz 3.125/6.25/12.5/75GHz spacing";
               }
               enum "1606.79" {
                 description "1606.79 nm/186.578125 THz 3.125GHz spacing";
               }
               enum "1606.77" {
                 description "1606.77 nm/186.581250 THz 3.125/6.25GHz spacing";
               }
               enum "1606.74" {
                 description "1606.74 nm/186.584375 THz 3.125GHz spacing";
               }
               enum "1606.71" {
                 description "1606.71 nm/186.587500 THz 3.125/6.25/12.5GHz spacing";
               }
               enum "1606.69" {
                 description "1606.69 nm/186.590625 THz 3.125GHz spacing";
               }
               enum "1606.66" {
                 description "1606.66 nm/186.593750 THz 3.125/6.25GHz spacing";
               }
               enum "1606.63" {
                 description "1606.63 nm/186.596875 THz 3.125GHz spacing";
               }
               enum "1606.60" {
                 description "1606.60 nm/186.600000 THz 3.125/6.25/12.5/50/75/100GHz spacing";
               }
               enum "1606.58" {
                 description "1606.58 nm/186.603125 THz 3.125GHz spacing";
               }
               enum "1606.55" {
                 description "1606.55 nm/186.606250 THz 3.125/6.25GHz spacing";
               }
               enum "1606.52" {
                 description "1606.52 nm/186.609375 THz 3.125GHz spacing";
               }
               enum "1606.50" {
                 description "1606.50 nm/186.612500 THz 3.125/6.25/12.5GHz spacing";
               }
               enum "1606.47" {
                 description "1606.47 nm/186.615625 THz 3.125GHz spacing";
               }
               enum "1606.44" {
                 description "1606.44 nm/186.618750 THz 3.125/6.25GHz spacing";
               }
               enum "1606.42" {
                 description "1606.42 nm/186.621875 THz 3.125GHz spacing";
               }
               enum "1606.39" {
                 description "1606.39 nm/186.625000 THz 3.125/6.25/12.5GHz spacing";
               }
               enum "1606.36" {
                 description "1606.36 nm/186.628125 THz 3.125GHz spacing";
               }
               enum "1606.34" {
                 description "1606.34 nm/186.631250 THz 3.125/6.25GHz spacing";
               }
               enum "1606.31" {
                 description "1606.31 nm/186.634375 THz 3.125GHz spacing";
               }
               enum "1606.28" {
                 description "1606.28 nm/186.637500 THz 3.125/6.25/12.5GHz spacing";
               }
               enum "1606.26" {
                 description "1606.26 nm/186.640625 THz 3.125GHz spacing";
               }
               enum "1606.23" {
                 description "1606.23 nm/186.643750 THz 3.125/6.25GHz spacing";
               }
               enum "1606.20" {
                 description "1606.20 nm/186.646875 THz 3.125GHz spacing";
               }
               enum "1606.17" {
                 description "1606.17 nm/186.650000 THz 3.125/6.25/12.5/50/75GHz spacing";
               }
               enum "1606.15" {
                 description "1606.15 nm/186.653125 THz 3.125GHz spacing";
               }
               enum "1606.12" {
                 description "1606.12 nm/186.656250 THz 3.125/6.25GHz spacing";
               }
               enum "1606.09" {
                 description "1606.09 nm/186.659375 THz 3.125GHz spacing";
               }
               enum "1606.07" {
                 description "1606.07 nm/186.662500 THz 3.125/6.25/12.5GHz spacing";
               }
               enum "1606.04" {
                 description "1606.04 nm/186.665625 THz 3.125GHz spacing";
               }
               enum "1606.01" {
                 description "1606.01 nm/186.668750 THz 3.125/6.25GHz spacing";
               }
               enum "1605.99" {
                 description "1605.99 nm/186.671875 THz 3.125GHz spacing";
               }
               enum "1605.96" {
                 description "1605.96 nm/186.675000 THz 3.125/6.25/12.5GHz spacing";
               }
               enum "1605.93" {
                 description "1605.93 nm/186.678125 THz 3.125GHz spacing";
               }
               enum "1605.91" {
                 description "1605.91 nm/186.681250 THz 3.125/6.25GHz spacing";
               }
               enum "1605.88" {
                 description "1605.88 nm/186.684375 THz 3.125GHz spacing";
               }
               enum "1605.85" {
                 description "1605.85 nm/186.687500 THz 3.125/6.25/12.5GHz spacing";
               }
               enum "1605.82" {
                 description "1605.82 nm/186.690625 THz 3.125GHz spacing";
               }
               enum "1605.80" {
                 description "1605.80 nm/186.693750 THz 3.125/6.25GHz spacing";
               }
               enum "1605.77" {
                 description "1605.77 nm/186.696875 THz 3.125GHz spacing";
               }
               enum "1605.74" {
                 description "1605.74 nm/186.700000 THz 3.125/6.25/12.5/100GHz spacing";
               }
               enum "1605.72" {
                 description "1605.72 nm/186.703125 THz 3.125GHz spacing";
               }
               enum "1605.69" {
                 description "1605.69 nm/186.706250 THz 3.125/6.25GHz spacing";
               }
               enum "1605.66" {
                 description "1605.66 nm/186.709375 THz 3.125GHz spacing";
               }
               enum "1605.64" {
                 description "1605.64 nm/186.712500 THz 3.125/6.25/12.5GHz spacing";
               }
               enum "1605.61" {
                 description "1605.61 nm/186.715625 THz 3.125GHz spacing";
               }
               enum "1605.58" {
                 description "1605.58 nm/186.718750 THz 3.125/6.25GHz spacing";
               }
               enum "1605.56" {
                 description "1605.56 nm/186.721875 THz 3.125GHz spacing";
               }
               enum "1605.53" {
                 description "1605.53 nm/186.725000 THz 3.125/6.25/12.5/75GHz spacing";
               }
               enum "1605.50" {
                 description "1605.50 nm/186.728125 THz 3.125GHz spacing";
               }
               enum "1605.48" {
                 description "1605.48 nm/186.731250 THz 3.125/6.25GHz spacing";
               }
               enum "1605.45" {
                 description "1605.45 nm/186.734375 THz 3.125GHz spacing";
               }
               enum "1605.42" {
                 description "1605.42 nm/186.737500 THz 3.125/6.25/12.5GHz spacing";
               }
               enum "1605.39" {
                 description "1605.39 nm/186.740625 THz 3.125GHz spacing";
               }
               enum "1605.37" {
                 description "1605.37 nm/186.743750 THz 3.125/6.25GHz spacing";
               }
               enum "1605.34" {
                 description "1605.34 nm/186.746875 THz 3.125GHz spacing";
               }
               enum "1605.31" {
                 description "1605.31 nm/186.750000 THz 3.125/6.25/12.5/50GHz spacing";
               }
               enum "1605.29" {
                 description "1605.29 nm/186.753125 THz 3.125GHz spacing";
               }
               enum "1605.26" {
                 description "1605.26 nm/186.756250 THz 3.125/6.25GHz spacing";
               }
               enum "1605.23" {
                 description "1605.23 nm/186.759375 THz 3.125GHz spacing";
               }
               enum "1605.21" {
                 description "1605.21 nm/186.762500 THz 3.125/6.25/12.5GHz spacing";
               }
               enum "1605.18" {
                 description "1605.18 nm/186.765625 THz 3.125GHz spacing";
               }
               enum "1605.15" {
                 description "1605.15 nm/186.768750 THz 3.125/6.25GHz spacing";
               }
               enum "1605.13" {
                 description "1605.13 nm/186.771875 THz 3.125GHz spacing";
               }
               enum "1605.10" {
                 description "1605.10 nm/186.775000 THz 3.125/6.25/12.5GHz spacing";
               }
               enum "1605.07" {
                 description "1605.07 nm/186.778125 THz 3.125GHz spacing";
               }
               enum "1605.05" {
                 description "1605.05 nm/186.781250 THz 3.125/6.25GHz spacing";
               }
               enum "1605.02" {
                 description "1605.02 nm/186.784375 THz 3.125GHz spacing";
               }
               enum "1604.99" {
                 description "1604.99 nm/186.787500 THz 3.125/6.25/12.5GHz spacing";
               }
               enum "1604.97" {
                 description "1604.97 nm/186.790625 THz 3.125GHz spacing";
               }
               enum "1604.94" {
                 description "1604.94 nm/186.793750 THz 3.125/6.25GHz spacing";
               }
               enum "1604.91" {
                 description "1604.91 nm/186.796875 THz 3.125GHz spacing";
               }
               enum "1604.88" {
                 description "1604.88 nm/186.800000 THz 3.125/6.25/12.5/100GHz spacing";
               }
               enum "1604.86" {
                 description "1604.86 nm/186.803125 THz 3.125GHz spacing";
               }
               enum "1604.83" {
                 description "1604.83 nm/186.806250 THz 3.125/6.25GHz spacing";
               }
               enum "1604.80" {
                 description "1604.80 nm/186.809375 THz 3.125GHz spacing";
               }
               enum "1604.78" {
                 description "1604.78 nm/186.812500 THz 3.125/6.25/12.5GHz spacing";
               }
               enum "1604.75" {
                 description "1604.75 nm/186.815625 THz 3.125GHz spacing";
               }
               enum "1604.72" {
                 description "1604.72 nm/186.818750 THz 3.125/6.25GHz spacing";
               }
               enum "1604.70" {
                 description "1604.70 nm/186.821875 THz 3.125GHz spacing";
               }
               enum "1604.67" {
                 description "1604.67 nm/186.825000 THz 3.125/6.25/12.5GHz spacing";
               }
               enum "1604.64" {
                 description "1604.64 nm/186.828125 THz 3.125GHz spacing";
               }
               enum "1604.62" {
                 description "1604.62 nm/186.831250 THz 3.125/6.25GHz spacing";
               }
               enum "1604.59" {
                 description "1604.59 nm/186.834375 THz 3.125GHz spacing";
               }
               enum "1604.56" {
                 description "1604.56 nm/186.837500 THz 3.125/6.25/12.5GHz spacing";
               }
               enum "1604.54" {
                 description "1604.54 nm/186.840625 THz 3.125GHz spacing";
               }
               enum "1604.51" {
                 description "1604.51 nm/186.843750 THz 3.125/6.25GHz spacing";
               }
               enum "1604.48" {
                 description "1604.48 nm/186.846875 THz 3.125GHz spacing";
               }
               enum "1604.46" {
                 description "1604.46 nm/186.850000 THz 3.125/6.25/12.5/50GHz spacing";
               }
               enum "1604.43" {
                 description "1604.43 nm/186.853125 THz 3.125GHz spacing";
               }
               enum "1604.40" {
                 description "1604.40 nm/186.856250 THz 3.125/6.25GHz spacing";
               }
               enum "1604.37" {
                 description "1604.37 nm/186.859375 THz 3.125GHz spacing";
               }
               enum "1604.35" {
                 description "1604.35 nm/186.862500 THz 3.125/6.25/12.5GHz spacing";
               }
               enum "1604.32" {
                 description "1604.32 nm/186.865625 THz 3.125GHz spacing";
               }
               enum "1604.29" {
                 description "1604.29 nm/186.868750 THz 3.125/6.25GHz spacing";
               }
               enum "1604.27" {
                 description "1604.27 nm/186.871875 THz 3.125GHz spacing";
               }
               enum "1604.24" {
                 description "1604.24 nm/186.875000 THz 3.125/6.25/12.5/75GHz spacing";
               }
               enum "1604.21" {
                 description "1604.21 nm/186.878125 THz 3.125GHz spacing";
               }
               enum "1604.19" {
                 description "1604.19 nm/186.881250 THz 3.125/6.25GHz spacing";
               }
               enum "1604.16" {
                 description "1604.16 nm/186.884375 THz 3.125GHz spacing";
               }
               enum "1604.13" {
                 description "1604.13 nm/186.887500 THz 3.125/6.25/12.5GHz spacing";
               }
               enum "1604.11" {
                 description "1604.11 nm/186.890625 THz 3.125GHz spacing";
               }
               enum "1604.08" {
                 description "1604.08 nm/186.893750 THz 3.125/6.25GHz spacing";
               }
               enum "1604.05" {
                 description "1604.05 nm/186.896875 THz 3.125GHz spacing";
               }
               enum "1604.03" {
                 description "1604.03 nm/186.900000 THz 3.125/6.25/12.5/50/75/100GHz spacing";
               }
               enum "1604.00" {
                 description "1604.00 nm/186.903125 THz 3.125GHz spacing";
               }
               enum "1603.97" {
                 description "1603.97 nm/186.906250 THz 3.125/6.25GHz spacing";
               }
               enum "1603.95" {
                 description "1603.95 nm/186.909375 THz 3.125GHz spacing";
               }
               enum "1603.92" {
                 description "1603.92 nm/186.912500 THz 3.125/6.25/12.5GHz spacing";
               }
               enum "1603.89" {
                 description "1603.89 nm/186.915625 THz 3.125GHz spacing";
               }
               enum "1603.87" {
                 description "1603.87 nm/186.918750 THz 3.125/6.25GHz spacing";
               }
               enum "1603.84" {
                 description "1603.84 nm/186.921875 THz 3.125GHz spacing";
               }
               enum "1603.81" {
                 description "1603.81 nm/186.925000 THz 3.125/6.25/12.5GHz spacing";
               }
               enum "1603.78" {
                 description "1603.78 nm/186.928125 THz 3.125GHz spacing";
               }
               enum "1603.76" {
                 description "1603.76 nm/186.931250 THz 3.125/6.25GHz spacing";
               }
               enum "1603.73" {
                 description "1603.73 nm/186.934375 THz 3.125GHz spacing";
               }
               enum "1603.70" {
                 description "1603.70 nm/186.937500 THz 3.125/6.25/12.5GHz spacing";
               }
               enum "1603.68" {
                 description "1603.68 nm/186.940625 THz 3.125GHz spacing";
               }
               enum "1603.65" {
                 description "1603.65 nm/186.943750 THz 3.125/6.25GHz spacing";
               }
               enum "1603.62" {
                 description "1603.62 nm/186.946875 THz 3.125GHz spacing";
               }
               enum "1603.60" {
                 description "1603.60 nm/186.950000 THz 3.125/6.25/12.5/50/75GHz spacing";
               }
               enum "1603.57" {
                 description "1603.57 nm/186.953125 THz 3.125GHz spacing";
               }
               enum "1603.54" {
                 description "1603.54 nm/186.956250 THz 3.125/6.25GHz spacing";
               }
               enum "1603.52" {
                 description "1603.52 nm/186.959375 THz 3.125GHz spacing";
               }
               enum "1603.49" {
                 description "1603.49 nm/186.962500 THz 3.125/6.25/12.5GHz spacing";
               }
               enum "1603.46" {
                 description "1603.46 nm/186.965625 THz 3.125GHz spacing";
               }
               enum "1603.44" {
                 description "1603.44 nm/186.968750 THz 3.125/6.25GHz spacing";
               }
               enum "1603.41" {
                 description "1603.41 nm/186.971875 THz 3.125GHz spacing";
               }
               enum "1603.38" {
                 description "1603.38 nm/186.975000 THz 3.125/6.25/12.5GHz spacing";
               }
               enum "1603.36" {
                 description "1603.36 nm/186.978125 THz 3.125GHz spacing";
               }
               enum "1603.33" {
                 description "1603.33 nm/186.981250 THz 3.125/6.25GHz spacing";
               }
               enum "1603.30" {
                 description "1603.30 nm/186.984375 THz 3.125GHz spacing";
               }
               enum "1603.28" {
                 description "1603.28 nm/186.987500 THz 3.125/6.25/12.5GHz spacing";
               }
               enum "1603.25" {
                 description "1603.25 nm/186.990625 THz 3.125GHz spacing";
               }
               enum "1603.22" {
                 description "1603.22 nm/186.993750 THz 3.125/6.25GHz spacing";
               }
               enum "1603.20" {
                 description "1603.20 nm/186.996875 THz 3.125GHz spacing";
               }
               enum "1603.17" {
                 description "1603.17 nm/187.000000 THz 3.125/6.25/12.5/100GHz spacing";
               }
               enum "1603.14" {
                 description "1603.14 nm/187.003125 THz 3.125GHz spacing";
               }
               enum "1603.11" {
                 description "1603.11 nm/187.006250 THz 3.125/6.25GHz spacing";
               }
               enum "1603.09" {
                 description "1603.09 nm/187.009375 THz 3.125GHz spacing";
               }
               enum "1603.06" {
                 description "1603.06 nm/187.012500 THz 3.125/6.25/12.5GHz spacing";
               }
               enum "1603.03" {
                 description "1603.03 nm/187.015625 THz 3.125GHz spacing";
               }
               enum "1603.01" {
                 description "1603.01 nm/187.018750 THz 3.125/6.25GHz spacing";
               }
               enum "1602.98" {
                 description "1602.98 nm/187.021875 THz 3.125GHz spacing";
               }
               enum "1602.95" {
                 description "1602.95 nm/187.025000 THz 3.125/6.25/12.5/75GHz spacing";
               }
               enum "1602.93" {
                 description "1602.93 nm/187.028125 THz 3.125GHz spacing";
               }
               enum "1602.90" {
                 description "1602.90 nm/187.031250 THz 3.125/6.25GHz spacing";
               }
               enum "1602.87" {
                 description "1602.87 nm/187.034375 THz 3.125GHz spacing";
               }
               enum "1602.85" {
                 description "1602.85 nm/187.037500 THz 3.125/6.25/12.5GHz spacing";
               }
               enum "1602.82" {
                 description "1602.82 nm/187.040625 THz 3.125GHz spacing";
               }
               enum "1602.79" {
                 description "1602.79 nm/187.043750 THz 3.125/6.25GHz spacing";
               }
               enum "1602.77" {
                 description "1602.77 nm/187.046875 THz 3.125GHz spacing";
               }
               enum "1602.74" {
                 description "1602.74 nm/187.050000 THz 3.125/6.25/12.5/50GHz spacing";
               }
               enum "1602.71" {
                 description "1602.71 nm/187.053125 THz 3.125GHz spacing";
               }
               enum "1602.69" {
                 description "1602.69 nm/187.056250 THz 3.125/6.25GHz spacing";
               }
               enum "1602.66" {
                 description "1602.66 nm/187.059375 THz 3.125GHz spacing";
               }
               enum "1602.63" {
                 description "1602.63 nm/187.062500 THz 3.125/6.25/12.5GHz spacing";
               }
               enum "1602.61" {
                 description "1602.61 nm/187.065625 THz 3.125GHz spacing";
               }
               enum "1602.58" {
                 description "1602.58 nm/187.068750 THz 3.125/6.25GHz spacing";
               }
               enum "1602.55" {
                 description "1602.55 nm/187.071875 THz 3.125GHz spacing";
               }
               enum "1602.53" {
                 description "1602.53 nm/187.075000 THz 3.125/6.25/12.5GHz spacing";
               }
               enum "1602.50" {
                 description "1602.50 nm/187.078125 THz 3.125GHz spacing";
               }
               enum "1602.47" {
                 description "1602.47 nm/187.081250 THz 3.125/6.25GHz spacing";
               }
               enum "1602.45" {
                 description "1602.45 nm/187.084375 THz 3.125GHz spacing";
               }
               enum "1602.42" {
                 description "1602.42 nm/187.087500 THz 3.125/6.25/12.5GHz spacing";
               }
               enum "1602.39" {
                 description "1602.39 nm/187.090625 THz 3.125GHz spacing";
               }
               enum "1602.36" {
                 description "1602.36 nm/187.093750 THz 3.125/6.25GHz spacing";
               }
               enum "1602.34" {
                 description "1602.34 nm/187.096875 THz 3.125GHz spacing";
               }
               enum "1602.31" {
                 description "1602.31 nm/187.100000 THz 3.125/6.25/12.5/100GHz spacing";
               }
               enum "1602.28" {
                 description "1602.28 nm/187.103125 THz 3.125GHz spacing";
               }
               enum "1602.26" {
                 description "1602.26 nm/187.106250 THz 3.125/6.25GHz spacing";
               }
               enum "1602.23" {
                 description "1602.23 nm/187.109375 THz 3.125GHz spacing";
               }
               enum "1602.20" {
                 description "1602.20 nm/187.112500 THz 3.125/6.25/12.5GHz spacing";
               }
               enum "1602.18" {
                 description "1602.18 nm/187.115625 THz 3.125GHz spacing";
               }
               enum "1602.15" {
                 description "1602.15 nm/187.118750 THz 3.125/6.25GHz spacing";
               }
               enum "1602.12" {
                 description "1602.12 nm/187.121875 THz 3.125GHz spacing";
               }
               enum "1602.10" {
                 description "1602.10 nm/187.125000 THz 3.125/6.25/12.5GHz spacing";
               }
               enum "1602.07" {
                 description "1602.07 nm/187.128125 THz 3.125GHz spacing";
               }
               enum "1602.04" {
                 description "1602.04 nm/187.131250 THz 3.125/6.25GHz spacing";
               }
               enum "1602.02" {
                 description "1602.02 nm/187.134375 THz 3.125GHz spacing";
               }
               enum "1601.99" {
                 description "1601.99 nm/187.137500 THz 3.125/6.25/12.5GHz spacing";
               }
               enum "1601.96" {
                 description "1601.96 nm/187.140625 THz 3.125GHz spacing";
               }
               enum "1601.94" {
                 description "1601.94 nm/187.143750 THz 3.125/6.25GHz spacing";
               }
               enum "1601.91" {
                 description "1601.91 nm/187.146875 THz 3.125GHz spacing";
               }
               enum "1601.88" {
                 description "1601.88 nm/187.150000 THz 3.125/6.25/12.5/50GHz spacing";
               }
               enum "1601.86" {
                 description "1601.86 nm/187.153125 THz 3.125GHz spacing";
               }
               enum "1601.83" {
                 description "1601.83 nm/187.156250 THz 3.125/6.25GHz spacing";
               }
               enum "1601.80" {
                 description "1601.80 nm/187.159375 THz 3.125GHz spacing";
               }
               enum "1601.78" {
                 description "1601.78 nm/187.162500 THz 3.125/6.25/12.5GHz spacing";
               }
               enum "1601.75" {
                 description "1601.75 nm/187.165625 THz 3.125GHz spacing";
               }
               enum "1601.72" {
                 description "1601.72 nm/187.168750 THz 3.125/6.25GHz spacing";
               }
               enum "1601.70" {
                 description "1601.70 nm/187.171875 THz 3.125GHz spacing";
               }
               enum "1601.67" {
                 description "1601.67 nm/187.175000 THz 3.125/6.25/12.5/75GHz spacing";
               }
               enum "1601.64" {
                 description "1601.64 nm/187.178125 THz 3.125GHz spacing";
               }
               enum "1601.62" {
                 description "1601.62 nm/187.181250 THz 3.125/6.25GHz spacing";
               }
               enum "1601.59" {
                 description "1601.59 nm/187.184375 THz 3.125GHz spacing";
               }
               enum "1601.56" {
                 description "1601.56 nm/187.187500 THz 3.125/6.25/12.5GHz spacing";
               }
               enum "1601.54" {
                 description "1601.54 nm/187.190625 THz 3.125GHz spacing";
               }
               enum "1601.51" {
                 description "1601.51 nm/187.193750 THz 3.125/6.25GHz spacing";
               }
               enum "1601.48" {
                 description "1601.48 nm/187.196875 THz 3.125GHz spacing";
               }
               enum "1601.46" {
                 description "1601.46 nm/187.200000 THz 3.125/6.25/12.5/50/75/100GHz spacing";
               }
               enum "1601.43" {
                 description "1601.43 nm/187.203125 THz 3.125GHz spacing";
               }
               enum "1601.40" {
                 description "1601.40 nm/187.206250 THz 3.125/6.25GHz spacing";
               }
               enum "1601.38" {
                 description "1601.38 nm/187.209375 THz 3.125GHz spacing";
               }
               enum "1601.35" {
                 description "1601.35 nm/187.212500 THz 3.125/6.25/12.5GHz spacing";
               }
               enum "1601.32" {
                 description "1601.32 nm/187.215625 THz 3.125GHz spacing";
               }
               enum "1601.30" {
                 description "1601.30 nm/187.218750 THz 3.125/6.25GHz spacing";
               }
               enum "1601.27" {
                 description "1601.27 nm/187.221875 THz 3.125GHz spacing";
               }
               enum "1601.24" {
                 description "1601.24 nm/187.225000 THz 3.125/6.25/12.5GHz spacing";
               }
               enum "1601.21" {
                 description "1601.21 nm/187.228125 THz 3.125GHz spacing";
               }
               enum "1601.19" {
                 description "1601.19 nm/187.231250 THz 3.125/6.25GHz spacing";
               }
               enum "1601.16" {
                 description "1601.16 nm/187.234375 THz 3.125GHz spacing";
               }
               enum "1601.13" {
                 description "1601.13 nm/187.237500 THz 3.125/6.25/12.5GHz spacing";
               }
               enum "1601.11" {
                 description "1601.11 nm/187.240625 THz 3.125GHz spacing";
               }
               enum "1601.08" {
                 description "1601.08 nm/187.243750 THz 3.125/6.25GHz spacing";
               }
               enum "1601.05" {
                 description "1601.05 nm/187.246875 THz 3.125GHz spacing";
               }
               enum "1601.03" {
                 description "1601.03 nm/187.250000 THz 3.125/6.25/12.5/50/75GHz spacing";
               }
               enum "1601.00" {
                 description "1601.00 nm/187.253125 THz 3.125GHz spacing";
               }
               enum "1600.97" {
                 description "1600.97 nm/187.256250 THz 3.125/6.25GHz spacing";
               }
               enum "1600.95" {
                 description "1600.95 nm/187.259375 THz 3.125GHz spacing";
               }
               enum "1600.92" {
                 description "1600.92 nm/187.262500 THz 3.125/6.25/12.5GHz spacing";
               }
               enum "1600.89" {
                 description "1600.89 nm/187.265625 THz 3.125GHz spacing";
               }
               enum "1600.87" {
                 description "1600.87 nm/187.268750 THz 3.125/6.25GHz spacing";
               }
               enum "1600.84" {
                 description "1600.84 nm/187.271875 THz 3.125GHz spacing";
               }
               enum "1600.81" {
                 description "1600.81 nm/187.275000 THz 3.125/6.25/12.5GHz spacing";
               }
               enum "1600.79" {
                 description "1600.79 nm/187.278125 THz 3.125GHz spacing";
               }
               enum "1600.76" {
                 description "1600.76 nm/187.281250 THz 3.125/6.25GHz spacing";
               }
               enum "1600.73" {
                 description "1600.73 nm/187.284375 THz 3.125GHz spacing";
               }
               enum "1600.71" {
                 description "1600.71 nm/187.287500 THz 3.125/6.25/12.5GHz spacing";
               }
               enum "1600.68" {
                 description "1600.68 nm/187.290625 THz 3.125GHz spacing";
               }
               enum "1600.65" {
                 description "1600.65 nm/187.293750 THz 3.125/6.25GHz spacing";
               }
               enum "1600.63" {
                 description "1600.63 nm/187.296875 THz 3.125GHz spacing";
               }
               enum "1600.60" {
                 description "1600.60 nm/187.300000 THz 3.125/6.25/12.5/100GHz spacing";
               }
               enum "1600.57" {
                 description "1600.57 nm/187.303125 THz 3.125GHz spacing";
               }
               enum "1600.55" {
                 description "1600.55 nm/187.306250 THz 3.125/6.25GHz spacing";
               }
               enum "1600.52" {
                 description "1600.52 nm/187.309375 THz 3.125GHz spacing";
               }
               enum "1600.49" {
                 description "1600.49 nm/187.312500 THz 3.125/6.25/12.5GHz spacing";
               }
               enum "1600.47" {
                 description "1600.47 nm/187.315625 THz 3.125GHz spacing";
               }
               enum "1600.44" {
                 description "1600.44 nm/187.318750 THz 3.125/6.25GHz spacing";
               }
               enum "1600.41" {
                 description "1600.41 nm/187.321875 THz 3.125GHz spacing";
               }
               enum "1600.39" {
                 description "1600.39 nm/187.325000 THz 3.125/6.25/12.5/75GHz spacing";
               }
               enum "1600.36" {
                 description "1600.36 nm/187.328125 THz 3.125GHz spacing";
               }
               enum "1600.33" {
                 description "1600.33 nm/187.331250 THz 3.125/6.25GHz spacing";
               }
               enum "1600.31" {
                 description "1600.31 nm/187.334375 THz 3.125GHz spacing";
               }
               enum "1600.28" {
                 description "1600.28 nm/187.337500 THz 3.125/6.25/12.5GHz spacing";
               }
               enum "1600.25" {
                 description "1600.25 nm/187.340625 THz 3.125GHz spacing";
               }
               enum "1600.23" {
                 description "1600.23 nm/187.343750 THz 3.125/6.25GHz spacing";
               }
               enum "1600.20" {
                 description "1600.20 nm/187.346875 THz 3.125GHz spacing";
               }
               enum "1600.17" {
                 description "1600.17 nm/187.350000 THz 3.125/6.25/12.5/50GHz spacing";
               }
               enum "1600.15" {
                 description "1600.15 nm/187.353125 THz 3.125GHz spacing";
               }
               enum "1600.12" {
                 description "1600.12 nm/187.356250 THz 3.125/6.25GHz spacing";
               }
               enum "1600.09" {
                 description "1600.09 nm/187.359375 THz 3.125GHz spacing";
               }
               enum "1600.07" {
                 description "1600.07 nm/187.362500 THz 3.125/6.25/12.5GHz spacing";
               }
               enum "1600.04" {
                 description "1600.04 nm/187.365625 THz 3.125GHz spacing";
               }
               enum "1600.01" {
                 description "1600.01 nm/187.368750 THz 3.125/6.25GHz spacing";
               }
               enum "1599.99" {
                 description "1599.99 nm/187.371875 THz 3.125GHz spacing";
               }
               enum "1599.96" {
                 description "1599.96 nm/187.375000 THz 3.125/6.25/12.5GHz spacing";
               }
               enum "1599.93" {
                 description "1599.93 nm/187.378125 THz 3.125GHz spacing";
               }
               enum "1599.91" {
                 description "1599.91 nm/187.381250 THz 3.125/6.25GHz spacing";
               }
               enum "1599.88" {
                 description "1599.88 nm/187.384375 THz 3.125GHz spacing";
               }
               enum "1599.85" {
                 description "1599.85 nm/187.387500 THz 3.125/6.25/12.5GHz spacing";
               }
               enum "1599.83" {
                 description "1599.83 nm/187.390625 THz 3.125GHz spacing";
               }
               enum "1599.80" {
                 description "1599.80 nm/187.393750 THz 3.125/6.25GHz spacing";
               }
               enum "1599.77" {
                 description "1599.77 nm/187.396875 THz 3.125GHz spacing";
               }
               enum "1599.75" {
                 description "1599.75 nm/187.400000 THz 3.125/6.25/12.5/100GHz spacing";
               }
               enum "1599.72" {
                 description "1599.72 nm/187.403125 THz 3.125GHz spacing";
               }
               enum "1599.69" {
                 description "1599.69 nm/187.406250 THz 3.125/6.25GHz spacing";
               }
               enum "1599.67" {
                 description "1599.67 nm/187.409375 THz 3.125GHz spacing";
               }
               enum "1599.64" {
                 description "1599.64 nm/187.412500 THz 3.125/6.25/12.5GHz spacing";
               }
               enum "1599.61" {
                 description "1599.61 nm/187.415625 THz 3.125GHz spacing";
               }
               enum "1599.59" {
                 description "1599.59 nm/187.418750 THz 3.125/6.25GHz spacing";
               }
               enum "1599.56" {
                 description "1599.56 nm/187.421875 THz 3.125GHz spacing";
               }
               enum "1599.53" {
                 description "1599.53 nm/187.425000 THz 3.125/6.25/12.5GHz spacing";
               }
               enum "1599.51" {
                 description "1599.51 nm/187.428125 THz 3.125GHz spacing";
               }
               enum "1599.48" {
                 description "1599.48 nm/187.431250 THz 3.125/6.25GHz spacing";
               }
               enum "1599.45" {
                 description "1599.45 nm/187.434375 THz 3.125GHz spacing";
               }
               enum "1599.43" {
                 description "1599.43 nm/187.437500 THz 3.125/6.25/12.5GHz spacing";
               }
               enum "1599.40" {
                 description "1599.40 nm/187.440625 THz 3.125GHz spacing";
               }
               enum "1599.37" {
                 description "1599.37 nm/187.443750 THz 3.125/6.25GHz spacing";
               }
               enum "1599.35" {
                 description "1599.35 nm/187.446875 THz 3.125GHz spacing";
               }
               enum "1599.32" {
                 description "1599.32 nm/187.450000 THz 3.125/6.25/12.5/50GHz spacing";
               }
               enum "1599.29" {
                 description "1599.29 nm/187.453125 THz 3.125GHz spacing";
               }
               enum "1599.27" {
                 description "1599.27 nm/187.456250 THz 3.125/6.25GHz spacing";
               }
               enum "1599.24" {
                 description "1599.24 nm/187.459375 THz 3.125GHz spacing";
               }
               enum "1599.21" {
                 description "1599.21 nm/187.462500 THz 3.125/6.25/12.5GHz spacing";
               }
               enum "1599.19" {
                 description "1599.19 nm/187.465625 THz 3.125GHz spacing";
               }
               enum "1599.16" {
                 description "1599.16 nm/187.468750 THz 3.125/6.25GHz spacing";
               }
               enum "1599.13" {
                 description "1599.13 nm/187.471875 THz 3.125GHz spacing";
               }
               enum "1599.11" {
                 description "1599.11 nm/187.475000 THz 3.125/6.25/12.5/75GHz spacing";
               }
               enum "1599.08" {
                 description "1599.08 nm/187.478125 THz 3.125GHz spacing";
               }
               enum "1599.05" {
                 description "1599.05 nm/187.481250 THz 3.125/6.25GHz spacing";
               }
               enum "1599.03" {
                 description "1599.03 nm/187.484375 THz 3.125GHz spacing";
               }
               enum "1599.00" {
                 description "1599.00 nm/187.487500 THz 3.125/6.25/12.5GHz spacing";
               }
               enum "1598.97" {
                 description "1598.97 nm/187.490625 THz 3.125GHz spacing";
               }
               enum "1598.95" {
                 description "1598.95 nm/187.493750 THz 3.125/6.25GHz spacing";
               }
               enum "1598.92" {
                 description "1598.92 nm/187.496875 THz 3.125GHz spacing";
               }
               enum "1598.89" {
                 description "1598.89 nm/187.500000 THz 3.125/6.25/12.5/50/75/100GHz spacing";
               }
               enum "1598.87" {
                 description "1598.87 nm/187.503125 THz 3.125GHz spacing";
               }
               enum "1598.84" {
                 description "1598.84 nm/187.506250 THz 3.125/6.25GHz spacing";
               }
               enum "1598.81" {
                 description "1598.81 nm/187.509375 THz 3.125GHz spacing";
               }
               enum "1598.79" {
                 description "1598.79 nm/187.512500 THz 3.125/6.25/12.5GHz spacing";
               }
               enum "1598.76" {
                 description "1598.76 nm/187.515625 THz 3.125GHz spacing";
               }
               enum "1598.73" {
                 description "1598.73 nm/187.518750 THz 3.125/6.25GHz spacing";
               }
               enum "1598.71" {
                 description "1598.71 nm/187.521875 THz 3.125GHz spacing";
               }
               enum "1598.68" {
                 description "1598.68 nm/187.525000 THz 3.125/6.25/12.5GHz spacing";
               }
               enum "1598.65" {
                 description "1598.65 nm/187.528125 THz 3.125GHz spacing";
               }
               enum "1598.63" {
                 description "1598.63 nm/187.531250 THz 3.125/6.25GHz spacing";
               }
               enum "1598.60" {
                 description "1598.60 nm/187.534375 THz 3.125GHz spacing";
               }
               enum "1598.57" {
                 description "1598.57 nm/187.537500 THz 3.125/6.25/12.5GHz spacing";
               }
               enum "1598.55" {
                 description "1598.55 nm/187.540625 THz 3.125GHz spacing";
               }
               enum "1598.52" {
                 description "1598.52 nm/187.543750 THz 3.125/6.25GHz spacing";
               }
               enum "1598.49" {
                 description "1598.49 nm/187.546875 THz 3.125GHz spacing";
               }
               enum "1598.47" {
                 description "1598.47 nm/187.550000 THz 3.125/6.25/12.5/50/75GHz spacing";
               }
               enum "1598.44" {
                 description "1598.44 nm/187.553125 THz 3.125GHz spacing";
               }
               enum "1598.41" {
                 description "1598.41 nm/187.556250 THz 3.125/6.25GHz spacing";
               }
               enum "1598.39" {
                 description "1598.39 nm/187.559375 THz 3.125GHz spacing";
               }
               enum "1598.36" {
                 description "1598.36 nm/187.562500 THz 3.125/6.25/12.5GHz spacing";
               }
               enum "1598.33" {
                 description "1598.33 nm/187.565625 THz 3.125GHz spacing";
               }
               enum "1598.31" {
                 description "1598.31 nm/187.568750 THz 3.125/6.25GHz spacing";
               }
               enum "1598.28" {
                 description "1598.28 nm/187.571875 THz 3.125GHz spacing";
               }
               enum "1598.25" {
                 description "1598.25 nm/187.575000 THz 3.125/6.25/12.5GHz spacing";
               }
               enum "1598.23" {
                 description "1598.23 nm/187.578125 THz 3.125GHz spacing";
               }
               enum "1598.20" {
                 description "1598.20 nm/187.581250 THz 3.125/6.25GHz spacing";
               }
               enum "1598.17" {
                 description "1598.17 nm/187.584375 THz 3.125GHz spacing";
               }
               enum "1598.15" {
                 description "1598.15 nm/187.587500 THz 3.125/6.25/12.5GHz spacing";
               }
               enum "1598.12" {
                 description "1598.12 nm/187.590625 THz 3.125GHz spacing";
               }
               enum "1598.09" {
                 description "1598.09 nm/187.593750 THz 3.125/6.25GHz spacing";
               }
               enum "1598.07" {
                 description "1598.07 nm/187.596875 THz 3.125GHz spacing";
               }
               enum "1598.04" {
                 description "1598.04 nm/187.600000 THz 3.125/6.25/12.5/100GHz spacing";
               }
               enum "1598.01" {
                 description "1598.01 nm/187.603125 THz 3.125GHz spacing";
               }
               enum "1597.99" {
                 description "1597.99 nm/187.606250 THz 3.125/6.25GHz spacing";
               }
               enum "1597.96" {
                 description "1597.96 nm/187.609375 THz 3.125GHz spacing";
               }
               enum "1597.93" {
                 description "1597.93 nm/187.612500 THz 3.125/6.25/12.5GHz spacing";
               }
               enum "1597.91" {
                 description "1597.91 nm/187.615625 THz 3.125GHz spacing";
               }
               enum "1597.88" {
                 description "1597.88 nm/187.618750 THz 3.125/6.25GHz spacing";
               }
               enum "1597.85" {
                 description "1597.85 nm/187.621875 THz 3.125GHz spacing";
               }
               enum "1597.83" {
                 description "1597.83 nm/187.625000 THz 3.125/6.25/12.5/75GHz spacing";
               }
               enum "1597.80" {
                 description "1597.80 nm/187.628125 THz 3.125GHz spacing";
               }
               enum "1597.77" {
                 description "1597.77 nm/187.631250 THz 3.125/6.25GHz spacing";
               }
               enum "1597.75" {
                 description "1597.75 nm/187.634375 THz 3.125GHz spacing";
               }
               enum "1597.72" {
                 description "1597.72 nm/187.637500 THz 3.125/6.25/12.5GHz spacing";
               }
               enum "1597.69" {
                 description "1597.69 nm/187.640625 THz 3.125GHz spacing";
               }
               enum "1597.67" {
                 description "1597.67 nm/187.643750 THz 3.125/6.25GHz spacing";
               }
               enum "1597.64" {
                 description "1597.64 nm/187.646875 THz 3.125GHz spacing";
               }
               enum "1597.62" {
                 description "1597.62 nm/187.650000 THz 3.125/6.25/12.5/50GHz spacing";
               }
               enum "1597.59" {
                 description "1597.59 nm/187.653125 THz 3.125GHz spacing";
               }
               enum "1597.56" {
                 description "1597.56 nm/187.656250 THz 3.125/6.25GHz spacing";
               }
               enum "1597.54" {
                 description "1597.54 nm/187.659375 THz 3.125GHz spacing";
               }
               enum "1597.51" {
                 description "1597.51 nm/187.662500 THz 3.125/6.25/12.5GHz spacing";
               }
               enum "1597.48" {
                 description "1597.48 nm/187.665625 THz 3.125GHz spacing";
               }
               enum "1597.46" {
                 description "1597.46 nm/187.668750 THz 3.125/6.25GHz spacing";
               }
               enum "1597.43" {
                 description "1597.43 nm/187.671875 THz 3.125GHz spacing";
               }
               enum "1597.40" {
                 description "1597.40 nm/187.675000 THz 3.125/6.25/12.5GHz spacing";
               }
               enum "1597.38" {
                 description "1597.38 nm/187.678125 THz 3.125GHz spacing";
               }
               enum "1597.35" {
                 description "1597.35 nm/187.681250 THz 3.125/6.25GHz spacing";
               }
               enum "1597.32" {
                 description "1597.32 nm/187.684375 THz 3.125GHz spacing";
               }
               enum "1597.30" {
                 description "1597.30 nm/187.687500 THz 3.125/6.25/12.5GHz spacing";
               }
               enum "1597.27" {
                 description "1597.27 nm/187.690625 THz 3.125GHz spacing";
               }
               enum "1597.24" {
                 description "1597.24 nm/187.693750 THz 3.125/6.25GHz spacing";
               }
               enum "1597.22" {
                 description "1597.22 nm/187.696875 THz 3.125GHz spacing";
               }
               enum "1597.19" {
                 description "1597.19 nm/187.700000 THz 3.125/6.25/12.5/100GHz spacing";
               }
               enum "1597.16" {
                 description "1597.16 nm/187.703125 THz 3.125GHz spacing";
               }
               enum "1597.14" {
                 description "1597.14 nm/187.706250 THz 3.125/6.25GHz spacing";
               }
               enum "1597.11" {
                 description "1597.11 nm/187.709375 THz 3.125GHz spacing";
               }
               enum "1597.08" {
                 description "1597.08 nm/187.712500 THz 3.125/6.25/12.5GHz spacing";
               }
               enum "1597.06" {
                 description "1597.06 nm/187.715625 THz 3.125GHz spacing";
               }
               enum "1597.03" {
                 description "1597.03 nm/187.718750 THz 3.125/6.25GHz spacing";
               }
               enum "1597.00" {
                 description "1597.00 nm/187.721875 THz 3.125GHz spacing";
               }
               enum "1596.98" {
                 description "1596.98 nm/187.725000 THz 3.125/6.25/12.5GHz spacing";
               }
               enum "1596.95" {
                 description "1596.95 nm/187.728125 THz 3.125GHz spacing";
               }
               enum "1596.92" {
                 description "1596.92 nm/187.731250 THz 3.125/6.25GHz spacing";
               }
               enum "1596.90" {
                 description "1596.90 nm/187.734375 THz 3.125GHz spacing";
               }
               enum "1596.87" {
                 description "1596.87 nm/187.737500 THz 3.125/6.25/12.5GHz spacing";
               }
               enum "1596.84" {
                 description "1596.84 nm/187.740625 THz 3.125GHz spacing";
               }
               enum "1596.82" {
                 description "1596.82 nm/187.743750 THz 3.125/6.25GHz spacing";
               }
               enum "1596.79" {
                 description "1596.79 nm/187.746875 THz 3.125GHz spacing";
               }
               enum "1596.76" {
                 description "1596.76 nm/187.750000 THz 3.125/6.25/12.5/50GHz spacing";
               }
               enum "1596.74" {
                 description "1596.74 nm/187.753125 THz 3.125GHz spacing";
               }
               enum "1596.71" {
                 description "1596.71 nm/187.756250 THz 3.125/6.25GHz spacing";
               }
               enum "1596.68" {
                 description "1596.68 nm/187.759375 THz 3.125GHz spacing";
               }
               enum "1596.66" {
                 description "1596.66 nm/187.762500 THz 3.125/6.25/12.5GHz spacing";
               }
               enum "1596.63" {
                 description "1596.63 nm/187.765625 THz 3.125GHz spacing";
               }
               enum "1596.60" {
                 description "1596.60 nm/187.768750 THz 3.125/6.25GHz spacing";
               }
               enum "1596.58" {
                 description "1596.58 nm/187.771875 THz 3.125GHz spacing";
               }
               enum "1596.55" {
                 description "1596.55 nm/187.775000 THz 3.125/6.25/12.5/75GHz spacing";
               }
               enum "1596.52" {
                 description "1596.52 nm/187.778125 THz 3.125GHz spacing";
               }
               enum "1596.50" {
                 description "1596.50 nm/187.781250 THz 3.125/6.25GHz spacing";
               }
               enum "1596.47" {
                 description "1596.47 nm/187.784375 THz 3.125GHz spacing";
               }
               enum "1596.45" {
                 description "1596.45 nm/187.787500 THz 3.125/6.25/12.5GHz spacing";
               }
               enum "1596.42" {
                 description "1596.42 nm/187.790625 THz 3.125GHz spacing";
               }
               enum "1596.39" {
                 description "1596.39 nm/187.793750 THz 3.125/6.25GHz spacing";
               }
               enum "1596.37" {
                 description "1596.37 nm/187.796875 THz 3.125GHz spacing";
               }
               enum "1596.34" {
                 description "1596.34 nm/187.800000 THz 3.125/6.25/12.5/50/75/100GHz spacing";
               }
               enum "1596.31" {
                 description "1596.31 nm/187.803125 THz 3.125GHz spacing";
               }
               enum "1596.29" {
                 description "1596.29 nm/187.806250 THz 3.125/6.25GHz spacing";
               }
               enum "1596.26" {
                 description "1596.26 nm/187.809375 THz 3.125GHz spacing";
               }
               enum "1596.23" {
                 description "1596.23 nm/187.812500 THz 3.125/6.25/12.5GHz spacing";
               }
               enum "1596.21" {
                 description "1596.21 nm/187.815625 THz 3.125GHz spacing";
               }
               enum "1596.18" {
                 description "1596.18 nm/187.818750 THz 3.125/6.25GHz spacing";
               }
               enum "1596.15" {
                 description "1596.15 nm/187.821875 THz 3.125GHz spacing";
               }
               enum "1596.13" {
                 description "1596.13 nm/187.825000 THz 3.125/6.25/12.5GHz spacing";
               }
               enum "1596.10" {
                 description "1596.10 nm/187.828125 THz 3.125GHz spacing";
               }
               enum "1596.07" {
                 description "1596.07 nm/187.831250 THz 3.125/6.25GHz spacing";
               }
               enum "1596.05" {
                 description "1596.05 nm/187.834375 THz 3.125GHz spacing";
               }
               enum "1596.02" {
                 description "1596.02 nm/187.837500 THz 3.125/6.25/12.5GHz spacing";
               }
               enum "1595.99" {
                 description "1595.99 nm/187.840625 THz 3.125GHz spacing";
               }
               enum "1595.97" {
                 description "1595.97 nm/187.843750 THz 3.125/6.25GHz spacing";
               }
               enum "1595.94" {
                 description "1595.94 nm/187.846875 THz 3.125GHz spacing";
               }
               enum "1595.91" {
                 description "1595.91 nm/187.850000 THz 3.125/6.25/12.5/50/75GHz spacing";
               }
               enum "1595.89" {
                 description "1595.89 nm/187.853125 THz 3.125GHz spacing";
               }
               enum "1595.86" {
                 description "1595.86 nm/187.856250 THz 3.125/6.25GHz spacing";
               }
               enum "1595.83" {
                 description "1595.83 nm/187.859375 THz 3.125GHz spacing";
               }
               enum "1595.81" {
                 description "1595.81 nm/187.862500 THz 3.125/6.25/12.5GHz spacing";
               }
               enum "1595.78" {
                 description "1595.78 nm/187.865625 THz 3.125GHz spacing";
               }
               enum "1595.75" {
                 description "1595.75 nm/187.868750 THz 3.125/6.25GHz spacing";
               }
               enum "1595.73" {
                 description "1595.73 nm/187.871875 THz 3.125GHz spacing";
               }
               enum "1595.70" {
                 description "1595.70 nm/187.875000 THz 3.125/6.25/12.5GHz spacing";
               }
               enum "1595.68" {
                 description "1595.68 nm/187.878125 THz 3.125GHz spacing";
               }
               enum "1595.65" {
                 description "1595.65 nm/187.881250 THz 3.125/6.25GHz spacing";
               }
               enum "1595.62" {
                 description "1595.62 nm/187.884375 THz 3.125GHz spacing";
               }
               enum "1595.60" {
                 description "1595.60 nm/187.887500 THz 3.125/6.25/12.5GHz spacing";
               }
               enum "1595.57" {
                 description "1595.57 nm/187.890625 THz 3.125GHz spacing";
               }
               enum "1595.54" {
                 description "1595.54 nm/187.893750 THz 3.125/6.25GHz spacing";
               }
               enum "1595.52" {
                 description "1595.52 nm/187.896875 THz 3.125GHz spacing";
               }
               enum "1595.49" {
                 description "1595.49 nm/187.900000 THz 3.125/6.25/12.5/100GHz spacing";
               }
               enum "1595.46" {
                 description "1595.46 nm/187.903125 THz 3.125GHz spacing";
               }
               enum "1595.44" {
                 description "1595.44 nm/187.906250 THz 3.125/6.25GHz spacing";
               }
               enum "1595.41" {
                 description "1595.41 nm/187.909375 THz 3.125GHz spacing";
               }
               enum "1595.38" {
                 description "1595.38 nm/187.912500 THz 3.125/6.25/12.5GHz spacing";
               }
               enum "1595.36" {
                 description "1595.36 nm/187.915625 THz 3.125GHz spacing";
               }
               enum "1595.33" {
                 description "1595.33 nm/187.918750 THz 3.125/6.25GHz spacing";
               }
               enum "1595.30" {
                 description "1595.30 nm/187.921875 THz 3.125GHz spacing";
               }
               enum "1595.28" {
                 description "1595.28 nm/187.925000 THz 3.125/6.25/12.5/75GHz spacing";
               }
               enum "1595.25" {
                 description "1595.25 nm/187.928125 THz 3.125GHz spacing";
               }
               enum "1595.22" {
                 description "1595.22 nm/187.931250 THz 3.125/6.25GHz spacing";
               }
               enum "1595.20" {
                 description "1595.20 nm/187.934375 THz 3.125GHz spacing";
               }
               enum "1595.17" {
                 description "1595.17 nm/187.937500 THz 3.125/6.25/12.5GHz spacing";
               }
               enum "1595.14" {
                 description "1595.14 nm/187.940625 THz 3.125GHz spacing";
               }
               enum "1595.12" {
                 description "1595.12 nm/187.943750 THz 3.125/6.25GHz spacing";
               }
               enum "1595.09" {
                 description "1595.09 nm/187.946875 THz 3.125GHz spacing";
               }
               enum "1595.06" {
                 description "1595.06 nm/187.950000 THz 3.125/6.25/12.5/50GHz spacing";
               }
               enum "1595.04" {
                 description "1595.04 nm/187.953125 THz 3.125GHz spacing";
               }
               enum "1595.01" {
                 description "1595.01 nm/187.956250 THz 3.125/6.25GHz spacing";
               }
               enum "1594.99" {
                 description "1594.99 nm/187.959375 THz 3.125GHz spacing";
               }
               enum "1594.96" {
                 description "1594.96 nm/187.962500 THz 3.125/6.25/12.5GHz spacing";
               }
               enum "1594.93" {
                 description "1594.93 nm/187.965625 THz 3.125GHz spacing";
               }
               enum "1594.91" {
                 description "1594.91 nm/187.968750 THz 3.125/6.25GHz spacing";
               }
               enum "1594.88" {
                 description "1594.88 nm/187.971875 THz 3.125GHz spacing";
               }
               enum "1594.85" {
                 description "1594.85 nm/187.975000 THz 3.125/6.25/12.5GHz spacing";
               }
               enum "1594.83" {
                 description "1594.83 nm/187.978125 THz 3.125GHz spacing";
               }
               enum "1594.80" {
                 description "1594.80 nm/187.981250 THz 3.125/6.25GHz spacing";
               }
               enum "1594.77" {
                 description "1594.77 nm/187.984375 THz 3.125GHz spacing";
               }
               enum "1594.75" {
                 description "1594.75 nm/187.987500 THz 3.125/6.25/12.5GHz spacing";
               }
               enum "1594.72" {
                 description "1594.72 nm/187.990625 THz 3.125GHz spacing";
               }
               enum "1594.69" {
                 description "1594.69 nm/187.993750 THz 3.125/6.25GHz spacing";
               }
               enum "1594.67" {
                 description "1594.67 nm/187.996875 THz 3.125GHz spacing";
               }
               enum "1594.64" {
                 description "1594.64 nm/188.000000 THz 3.125/6.25/12.5/100GHz spacing";
               }
               enum "1594.61" {
                 description "1594.61 nm/188.003125 THz 3.125GHz spacing";
               }
               enum "1594.59" {
                 description "1594.59 nm/188.006250 THz 3.125/6.25GHz spacing";
               }
               enum "1594.56" {
                 description "1594.56 nm/188.009375 THz 3.125GHz spacing";
               }
               enum "1594.53" {
                 description "1594.53 nm/188.012500 THz 3.125/6.25/12.5GHz spacing";
               }
               enum "1594.51" {
                 description "1594.51 nm/188.015625 THz 3.125GHz spacing";
               }
               enum "1594.48" {
                 description "1594.48 nm/188.018750 THz 3.125/6.25GHz spacing";
               }
               enum "1594.46" {
                 description "1594.46 nm/188.021875 THz 3.125GHz spacing";
               }
               enum "1594.43" {
                 description "1594.43 nm/188.025000 THz 3.125/6.25/12.5GHz spacing";
               }
               enum "1594.40" {
                 description "1594.40 nm/188.028125 THz 3.125GHz spacing";
               }
               enum "1594.38" {
                 description "1594.38 nm/188.031250 THz 3.125/6.25GHz spacing";
               }
               enum "1594.35" {
                 description "1594.35 nm/188.034375 THz 3.125GHz spacing";
               }
               enum "1594.32" {
                 description "1594.32 nm/188.037500 THz 3.125/6.25/12.5GHz spacing";
               }
               enum "1594.30" {
                 description "1594.30 nm/188.040625 THz 3.125GHz spacing";
               }
               enum "1594.27" {
                 description "1594.27 nm/188.043750 THz 3.125/6.25GHz spacing";
               }
               enum "1594.24" {
                 description "1594.24 nm/188.046875 THz 3.125GHz spacing";
               }
               enum "1594.22" {
                 description "1594.22 nm/188.050000 THz 3.125/6.25/12.5/50GHz spacing";
               }
               enum "1594.19" {
                 description "1594.19 nm/188.053125 THz 3.125GHz spacing";
               }
               enum "1594.16" {
                 description "1594.16 nm/188.056250 THz 3.125/6.25GHz spacing";
               }
               enum "1594.14" {
                 description "1594.14 nm/188.059375 THz 3.125GHz spacing";
               }
               enum "1594.11" {
                 description "1594.11 nm/188.062500 THz 3.125/6.25/12.5GHz spacing";
               }
               enum "1594.08" {
                 description "1594.08 nm/188.065625 THz 3.125GHz spacing";
               }
               enum "1594.06" {
                 description "1594.06 nm/188.068750 THz 3.125/6.25GHz spacing";
               }
               enum "1594.03" {
                 description "1594.03 nm/188.071875 THz 3.125GHz spacing";
               }
               enum "1594.00" {
                 description "1594.00 nm/188.075000 THz 3.125/6.25/12.5/75GHz spacing";
               }
               enum "1593.98" {
                 description "1593.98 nm/188.078125 THz 3.125GHz spacing";
               }
               enum "1593.95" {
                 description "1593.95 nm/188.081250 THz 3.125/6.25GHz spacing";
               }
               enum "1593.93" {
                 description "1593.93 nm/188.084375 THz 3.125GHz spacing";
               }
               enum "1593.90" {
                 description "1593.90 nm/188.087500 THz 3.125/6.25/12.5GHz spacing";
               }
               enum "1593.87" {
                 description "1593.87 nm/188.090625 THz 3.125GHz spacing";
               }
               enum "1593.85" {
                 description "1593.85 nm/188.093750 THz 3.125/6.25GHz spacing";
               }
               enum "1593.82" {
                 description "1593.82 nm/188.096875 THz 3.125GHz spacing";
               }
               enum "1593.79" {
                 description "1593.79 nm/188.100000 THz 3.125/6.25/12.5/50/75/100GHz spacing";
               }
               enum "1593.77" {
                 description "1593.77 nm/188.103125 THz 3.125GHz spacing";
               }
               enum "1593.74" {
                 description "1593.74 nm/188.106250 THz 3.125/6.25GHz spacing";
               }
               enum "1593.71" {
                 description "1593.71 nm/188.109375 THz 3.125GHz spacing";
               }
               enum "1593.69" {
                 description "1593.69 nm/188.112500 THz 3.125/6.25/12.5GHz spacing";
               }
               enum "1593.66" {
                 description "1593.66 nm/188.115625 THz 3.125GHz spacing";
               }
               enum "1593.63" {
                 description "1593.63 nm/188.118750 THz 3.125/6.25GHz spacing";
               }
               enum "1593.61" {
                 description "1593.61 nm/188.121875 THz 3.125GHz spacing";
               }
               enum "1593.58" {
                 description "1593.58 nm/188.125000 THz 3.125/6.25/12.5GHz spacing";
               }
               enum "1593.55" {
                 description "1593.55 nm/188.128125 THz 3.125GHz spacing";
               }
               enum "1593.53" {
                 description "1593.53 nm/188.131250 THz 3.125/6.25GHz spacing";
               }
               enum "1593.50" {
                 description "1593.50 nm/188.134375 THz 3.125GHz spacing";
               }
               enum "1593.48" {
                 description "1593.48 nm/188.137500 THz 3.125/6.25/12.5GHz spacing";
               }
               enum "1593.45" {
                 description "1593.45 nm/188.140625 THz 3.125GHz spacing";
               }
               enum "1593.42" {
                 description "1593.42 nm/188.143750 THz 3.125/6.25GHz spacing";
               }
               enum "1593.40" {
                 description "1593.40 nm/188.146875 THz 3.125GHz spacing";
               }
               enum "1593.37" {
                 description "1593.37 nm/188.150000 THz 3.125/6.25/12.5/50/75GHz spacing";
               }
               enum "1593.34" {
                 description "1593.34 nm/188.153125 THz 3.125GHz spacing";
               }
               enum "1593.32" {
                 description "1593.32 nm/188.156250 THz 3.125/6.25GHz spacing";
               }
               enum "1593.29" {
                 description "1593.29 nm/188.159375 THz 3.125GHz spacing";
               }
               enum "1593.26" {
                 description "1593.26 nm/188.162500 THz 3.125/6.25/12.5GHz spacing";
               }
               enum "1593.24" {
                 description "1593.24 nm/188.165625 THz 3.125GHz spacing";
               }
               enum "1593.21" {
                 description "1593.21 nm/188.168750 THz 3.125/6.25GHz spacing";
               }
               enum "1593.18" {
                 description "1593.18 nm/188.171875 THz 3.125GHz spacing";
               }
               enum "1593.16" {
                 description "1593.16 nm/188.175000 THz 3.125/6.25/12.5GHz spacing";
               }
               enum "1593.13" {
                 description "1593.13 nm/188.178125 THz 3.125GHz spacing";
               }
               enum "1593.10" {
                 description "1593.10 nm/188.181250 THz 3.125/6.25GHz spacing";
               }
               enum "1593.08" {
                 description "1593.08 nm/188.184375 THz 3.125GHz spacing";
               }
               enum "1593.05" {
                 description "1593.05 nm/188.187500 THz 3.125/6.25/12.5GHz spacing";
               }
               enum "1593.03" {
                 description "1593.03 nm/188.190625 THz 3.125GHz spacing";
               }
               enum "1593.00" {
                 description "1593.00 nm/188.193750 THz 3.125/6.25GHz spacing";
               }
               enum "1592.97" {
                 description "1592.97 nm/188.196875 THz 3.125GHz spacing";
               }
               enum "1592.95" {
                 description "1592.95 nm/188.200000 THz 3.125/6.25/12.5/100GHz spacing";
               }
               enum "1592.92" {
                 description "1592.92 nm/188.203125 THz 3.125GHz spacing";
               }
               enum "1592.89" {
                 description "1592.89 nm/188.206250 THz 3.125/6.25GHz spacing";
               }
               enum "1592.87" {
                 description "1592.87 nm/188.209375 THz 3.125GHz spacing";
               }
               enum "1592.84" {
                 description "1592.84 nm/188.212500 THz 3.125/6.25/12.5GHz spacing";
               }
               enum "1592.81" {
                 description "1592.81 nm/188.215625 THz 3.125GHz spacing";
               }
               enum "1592.79" {
                 description "1592.79 nm/188.218750 THz 3.125/6.25GHz spacing";
               }
               enum "1592.76" {
                 description "1592.76 nm/188.221875 THz 3.125GHz spacing";
               }
               enum "1592.73" {
                 description "1592.73 nm/188.225000 THz 3.125/6.25/12.5/75GHz spacing";
               }
               enum "1592.71" {
                 description "1592.71 nm/188.228125 THz 3.125GHz spacing";
               }
               enum "1592.68" {
                 description "1592.68 nm/188.231250 THz 3.125/6.25GHz spacing";
               }
               enum "1592.66" {
                 description "1592.66 nm/188.234375 THz 3.125GHz spacing";
               }
               enum "1592.63" {
                 description "1592.63 nm/188.237500 THz 3.125/6.25/12.5GHz spacing";
               }
               enum "1592.60" {
                 description "1592.60 nm/188.240625 THz 3.125GHz spacing";
               }
               enum "1592.58" {
                 description "1592.58 nm/188.243750 THz 3.125/6.25GHz spacing";
               }
               enum "1592.55" {
                 description "1592.55 nm/188.246875 THz 3.125GHz spacing";
               }
               enum "1592.52" {
                 description "1592.52 nm/188.250000 THz 3.125/6.25/12.5/50GHz spacing";
               }
               enum "1592.50" {
                 description "1592.50 nm/188.253125 THz 3.125GHz spacing";
               }
               enum "1592.47" {
                 description "1592.47 nm/188.256250 THz 3.125/6.25GHz spacing";
               }
               enum "1592.44" {
                 description "1592.44 nm/188.259375 THz 3.125GHz spacing";
               }
               enum "1592.42" {
                 description "1592.42 nm/188.262500 THz 3.125/6.25/12.5GHz spacing";
               }
               enum "1592.39" {
                 description "1592.39 nm/188.265625 THz 3.125GHz spacing";
               }
               enum "1592.36" {
                 description "1592.36 nm/188.268750 THz 3.125/6.25GHz spacing";
               }
               enum "1592.34" {
                 description "1592.34 nm/188.271875 THz 3.125GHz spacing";
               }
               enum "1592.31" {
                 description "1592.31 nm/188.275000 THz 3.125/6.25/12.5GHz spacing";
               }
               enum "1592.29" {
                 description "1592.29 nm/188.278125 THz 3.125GHz spacing";
               }
               enum "1592.26" {
                 description "1592.26 nm/188.281250 THz 3.125/6.25GHz spacing";
               }
               enum "1592.23" {
                 description "1592.23 nm/188.284375 THz 3.125GHz spacing";
               }
               enum "1592.21" {
                 description "1592.21 nm/188.287500 THz 3.125/6.25/12.5GHz spacing";
               }
               enum "1592.18" {
                 description "1592.18 nm/188.290625 THz 3.125GHz spacing";
               }
               enum "1592.15" {
                 description "1592.15 nm/188.293750 THz 3.125/6.25GHz spacing";
               }
               enum "1592.13" {
                 description "1592.13 nm/188.296875 THz 3.125GHz spacing";
               }
               enum "1592.10" {
                 description "1592.10 nm/188.300000 THz 3.125/6.25/12.5/100GHz spacing";
               }
               enum "1592.07" {
                 description "1592.07 nm/188.303125 THz 3.125GHz spacing";
               }
               enum "1592.05" {
                 description "1592.05 nm/188.306250 THz 3.125/6.25GHz spacing";
               }
               enum "1592.02" {
                 description "1592.02 nm/188.309375 THz 3.125GHz spacing";
               }
               enum "1591.99" {
                 description "1591.99 nm/188.312500 THz 3.125/6.25/12.5GHz spacing";
               }
               enum "1591.97" {
                 description "1591.97 nm/188.315625 THz 3.125GHz spacing";
               }
               enum "1591.94" {
                 description "1591.94 nm/188.318750 THz 3.125/6.25GHz spacing";
               }
               enum "1591.92" {
                 description "1591.92 nm/188.321875 THz 3.125GHz spacing";
               }
               enum "1591.89" {
                 description "1591.89 nm/188.325000 THz 3.125/6.25/12.5GHz spacing";
               }
               enum "1591.86" {
                 description "1591.86 nm/188.328125 THz 3.125GHz spacing";
               }
               enum "1591.84" {
                 description "1591.84 nm/188.331250 THz 3.125/6.25GHz spacing";
               }
               enum "1591.81" {
                 description "1591.81 nm/188.334375 THz 3.125GHz spacing";
               }
               enum "1591.78" {
                 description "1591.78 nm/188.337500 THz 3.125/6.25/12.5GHz spacing";
               }
               enum "1591.76" {
                 description "1591.76 nm/188.340625 THz 3.125GHz spacing";
               }
               enum "1591.73" {
                 description "1591.73 nm/188.343750 THz 3.125/6.25GHz spacing";
               }
               enum "1591.70" {
                 description "1591.70 nm/188.346875 THz 3.125GHz spacing";
               }
               enum "1591.68" {
                 description "1591.68 nm/188.350000 THz 3.125/6.25/12.5/50GHz spacing";
               }
               enum "1591.65" {
                 description "1591.65 nm/188.353125 THz 3.125GHz spacing";
               }
               enum "1591.62" {
                 description "1591.62 nm/188.356250 THz 3.125/6.25GHz spacing";
               }
               enum "1591.60" {
                 description "1591.60 nm/188.359375 THz 3.125GHz spacing";
               }
               enum "1591.57" {
                 description "1591.57 nm/188.362500 THz 3.125/6.25/12.5GHz spacing";
               }
               enum "1591.55" {
                 description "1591.55 nm/188.365625 THz 3.125GHz spacing";
               }
               enum "1591.52" {
                 description "1591.52 nm/188.368750 THz 3.125/6.25GHz spacing";
               }
               enum "1591.49" {
                 description "1591.49 nm/188.371875 THz 3.125GHz spacing";
               }
               enum "1591.47" {
                 description "1591.47 nm/188.375000 THz 3.125/6.25/12.5/75GHz spacing";
               }
               enum "1591.44" {
                 description "1591.44 nm/188.378125 THz 3.125GHz spacing";
               }
               enum "1591.41" {
                 description "1591.41 nm/188.381250 THz 3.125/6.25GHz spacing";
               }
               enum "1591.39" {
                 description "1591.39 nm/188.384375 THz 3.125GHz spacing";
               }
               enum "1591.36" {
                 description "1591.36 nm/188.387500 THz 3.125/6.25/12.5GHz spacing";
               }
               enum "1591.33" {
                 description "1591.33 nm/188.390625 THz 3.125GHz spacing";
               }
               enum "1591.31" {
                 description "1591.31 nm/188.393750 THz 3.125/6.25GHz spacing";
               }
               enum "1591.28" {
                 description "1591.28 nm/188.396875 THz 3.125GHz spacing";
               }
               enum "1591.26" {
                 description "1591.26 nm/188.400000 THz 3.125/6.25/12.5/50/75/100GHz spacing";
               }
               enum "1591.23" {
                 description "1591.23 nm/188.403125 THz 3.125GHz spacing";
               }
               enum "1591.20" {
                 description "1591.20 nm/188.406250 THz 3.125/6.25GHz spacing";
               }
               enum "1591.18" {
                 description "1591.18 nm/188.409375 THz 3.125GHz spacing";
               }
               enum "1591.15" {
                 description "1591.15 nm/188.412500 THz 3.125/6.25/12.5GHz spacing";
               }
               enum "1591.12" {
                 description "1591.12 nm/188.415625 THz 3.125GHz spacing";
               }
               enum "1591.10" {
                 description "1591.10 nm/188.418750 THz 3.125/6.25GHz spacing";
               }
               enum "1591.07" {
                 description "1591.07 nm/188.421875 THz 3.125GHz spacing";
               }
               enum "1591.04" {
                 description "1591.04 nm/188.425000 THz 3.125/6.25/12.5GHz spacing";
               }
               enum "1591.02" {
                 description "1591.02 nm/188.428125 THz 3.125GHz spacing";
               }
               enum "1590.99" {
                 description "1590.99 nm/188.431250 THz 3.125/6.25GHz spacing";
               }
               enum "1590.96" {
                 description "1590.96 nm/188.434375 THz 3.125GHz spacing";
               }
               enum "1590.94" {
                 description "1590.94 nm/188.437500 THz 3.125/6.25/12.5GHz spacing";
               }
               enum "1590.91" {
                 description "1590.91 nm/188.440625 THz 3.125GHz spacing";
               }
               enum "1590.89" {
                 description "1590.89 nm/188.443750 THz 3.125/6.25GHz spacing";
               }
               enum "1590.86" {
                 description "1590.86 nm/188.446875 THz 3.125GHz spacing";
               }
               enum "1590.83" {
                 description "1590.83 nm/188.450000 THz 3.125/6.25/12.5/50/75GHz spacing";
               }
               enum "1590.81" {
                 description "1590.81 nm/188.453125 THz 3.125GHz spacing";
               }
               enum "1590.78" {
                 description "1590.78 nm/188.456250 THz 3.125/6.25GHz spacing";
               }
               enum "1590.75" {
                 description "1590.75 nm/188.459375 THz 3.125GHz spacing";
               }
               enum "1590.73" {
                 description "1590.73 nm/188.462500 THz 3.125/6.25/12.5GHz spacing";
               }
               enum "1590.70" {
                 description "1590.70 nm/188.465625 THz 3.125GHz spacing";
               }
               enum "1590.67" {
                 description "1590.67 nm/188.468750 THz 3.125/6.25GHz spacing";
               }
               enum "1590.65" {
                 description "1590.65 nm/188.471875 THz 3.125GHz spacing";
               }
               enum "1590.62" {
                 description "1590.62 nm/188.475000 THz 3.125/6.25/12.5GHz spacing";
               }
               enum "1590.60" {
                 description "1590.60 nm/188.478125 THz 3.125GHz spacing";
               }
               enum "1590.57" {
                 description "1590.57 nm/188.481250 THz 3.125/6.25GHz spacing";
               }
               enum "1590.54" {
                 description "1590.54 nm/188.484375 THz 3.125GHz spacing";
               }
               enum "1590.52" {
                 description "1590.52 nm/188.487500 THz 3.125/6.25/12.5GHz spacing";
               }
               enum "1590.49" {
                 description "1590.49 nm/188.490625 THz 3.125GHz spacing";
               }
               enum "1590.46" {
                 description "1590.46 nm/188.493750 THz 3.125/6.25GHz spacing";
               }
               enum "1590.44" {
                 description "1590.44 nm/188.496875 THz 3.125GHz spacing";
               }
               enum "1590.41" {
                 description "1590.41 nm/188.500000 THz 3.125/6.25/12.5/100GHz spacing";
               }
               enum "1590.38" {
                 description "1590.38 nm/188.503125 THz 3.125GHz spacing";
               }
               enum "1590.36" {
                 description "1590.36 nm/188.506250 THz 3.125/6.25GHz spacing";
               }
               enum "1590.33" {
                 description "1590.33 nm/188.509375 THz 3.125GHz spacing";
               }
               enum "1590.31" {
                 description "1590.31 nm/188.512500 THz 3.125/6.25/12.5GHz spacing";
               }
               enum "1590.28" {
                 description "1590.28 nm/188.515625 THz 3.125GHz spacing";
               }
               enum "1590.25" {
                 description "1590.25 nm/188.518750 THz 3.125/6.25GHz spacing";
               }
               enum "1590.23" {
                 description "1590.23 nm/188.521875 THz 3.125GHz spacing";
               }
               enum "1590.20" {
                 description "1590.20 nm/188.525000 THz 3.125/6.25/12.5/75GHz spacing";
               }
               enum "1590.17" {
                 description "1590.17 nm/188.528125 THz 3.125GHz spacing";
               }
               enum "1590.15" {
                 description "1590.15 nm/188.531250 THz 3.125/6.25GHz spacing";
               }
               enum "1590.12" {
                 description "1590.12 nm/188.534375 THz 3.125GHz spacing";
               }
               enum "1590.09" {
                 description "1590.09 nm/188.537500 THz 3.125/6.25/12.5GHz spacing";
               }
               enum "1590.07" {
                 description "1590.07 nm/188.540625 THz 3.125GHz spacing";
               }
               enum "1590.04" {
                 description "1590.04 nm/188.543750 THz 3.125/6.25GHz spacing";
               }
               enum "1590.02" {
                 description "1590.02 nm/188.546875 THz 3.125GHz spacing";
               }
               enum "1589.99" {
                 description "1589.99 nm/188.550000 THz 3.125/6.25/12.5/50GHz spacing";
               }
               enum "1589.96" {
                 description "1589.96 nm/188.553125 THz 3.125GHz spacing";
               }
               enum "1589.94" {
                 description "1589.94 nm/188.556250 THz 3.125/6.25GHz spacing";
               }
               enum "1589.91" {
                 description "1589.91 nm/188.559375 THz 3.125GHz spacing";
               }
               enum "1589.88" {
                 description "1589.88 nm/188.562500 THz 3.125/6.25/12.5GHz spacing";
               }
               enum "1589.86" {
                 description "1589.86 nm/188.565625 THz 3.125GHz spacing";
               }
               enum "1589.83" {
                 description "1589.83 nm/188.568750 THz 3.125/6.25GHz spacing";
               }
               enum "1589.80" {
                 description "1589.80 nm/188.571875 THz 3.125GHz spacing";
               }
               enum "1589.78" {
                 description "1589.78 nm/188.575000 THz 3.125/6.25/12.5GHz spacing";
               }
               enum "1589.75" {
                 description "1589.75 nm/188.578125 THz 3.125GHz spacing";
               }
               enum "1589.73" {
                 description "1589.73 nm/188.581250 THz 3.125/6.25GHz spacing";
               }
               enum "1589.70" {
                 description "1589.70 nm/188.584375 THz 3.125GHz spacing";
               }
               enum "1589.67" {
                 description "1589.67 nm/188.587500 THz 3.125/6.25/12.5GHz spacing";
               }
               enum "1589.65" {
                 description "1589.65 nm/188.590625 THz 3.125GHz spacing";
               }
               enum "1589.62" {
                 description "1589.62 nm/188.593750 THz 3.125/6.25GHz spacing";
               }
               enum "1589.59" {
                 description "1589.59 nm/188.596875 THz 3.125GHz spacing";
               }
               enum "1589.57" {
                 description "1589.57 nm/188.600000 THz 3.125/6.25/12.5/100GHz spacing";
               }
               enum "1589.54" {
                 description "1589.54 nm/188.603125 THz 3.125GHz spacing";
               }
               enum "1589.51" {
                 description "1589.51 nm/188.606250 THz 3.125/6.25GHz spacing";
               }
               enum "1589.49" {
                 description "1589.49 nm/188.609375 THz 3.125GHz spacing";
               }
               enum "1589.46" {
                 description "1589.46 nm/188.612500 THz 3.125/6.25/12.5GHz spacing";
               }
               enum "1589.44" {
                 description "1589.44 nm/188.615625 THz 3.125GHz spacing";
               }
               enum "1589.41" {
                 description "1589.41 nm/188.618750 THz 3.125/6.25GHz spacing";
               }
               enum "1589.38" {
                 description "1589.38 nm/188.621875 THz 3.125GHz spacing";
               }
               enum "1589.36" {
                 description "1589.36 nm/188.625000 THz 3.125/6.25/12.5GHz spacing";
               }
               enum "1589.33" {
                 description "1589.33 nm/188.628125 THz 3.125GHz spacing";
               }
               enum "1589.30" {
                 description "1589.30 nm/188.631250 THz 3.125/6.25GHz spacing";
               }
               enum "1589.28" {
                 description "1589.28 nm/188.634375 THz 3.125GHz spacing";
               }
               enum "1589.25" {
                 description "1589.25 nm/188.637500 THz 3.125/6.25/12.5GHz spacing";
               }
               enum "1589.23" {
                 description "1589.23 nm/188.640625 THz 3.125GHz spacing";
               }
               enum "1589.20" {
                 description "1589.20 nm/188.643750 THz 3.125/6.25GHz spacing";
               }
               enum "1589.17" {
                 description "1589.17 nm/188.646875 THz 3.125GHz spacing";
               }
               enum "1589.15" {
                 description "1589.15 nm/188.650000 THz 3.125/6.25/12.5/50GHz spacing";
               }
               enum "1589.12" {
                 description "1589.12 nm/188.653125 THz 3.125GHz spacing";
               }
               enum "1589.09" {
                 description "1589.09 nm/188.656250 THz 3.125/6.25GHz spacing";
               }
               enum "1589.07" {
                 description "1589.07 nm/188.659375 THz 3.125GHz spacing";
               }
               enum "1589.04" {
                 description "1589.04 nm/188.662500 THz 3.125/6.25/12.5GHz spacing";
               }
               enum "1589.01" {
                 description "1589.01 nm/188.665625 THz 3.125GHz spacing";
               }
               enum "1588.99" {
                 description "1588.99 nm/188.668750 THz 3.125/6.25GHz spacing";
               }
               enum "1588.96" {
                 description "1588.96 nm/188.671875 THz 3.125GHz spacing";
               }
               enum "1588.94" {
                 description "1588.94 nm/188.675000 THz 3.125/6.25/12.5/75GHz spacing";
               }
               enum "1588.91" {
                 description "1588.91 nm/188.678125 THz 3.125GHz spacing";
               }
               enum "1588.88" {
                 description "1588.88 nm/188.681250 THz 3.125/6.25GHz spacing";
               }
               enum "1588.86" {
                 description "1588.86 nm/188.684375 THz 3.125GHz spacing";
               }
               enum "1588.83" {
                 description "1588.83 nm/188.687500 THz 3.125/6.25/12.5GHz spacing";
               }
               enum "1588.80" {
                 description "1588.80 nm/188.690625 THz 3.125GHz spacing";
               }
               enum "1588.78" {
                 description "1588.78 nm/188.693750 THz 3.125/6.25GHz spacing";
               }
               enum "1588.75" {
                 description "1588.75 nm/188.696875 THz 3.125GHz spacing";
               }
               enum "1588.73" {
                 description "1588.73 nm/188.700000 THz 3.125/6.25/12.5/50/75/100GHz spacing";
               }
               enum "1588.70" {
                 description "1588.70 nm/188.703125 THz 3.125GHz spacing";
               }
               enum "1588.67" {
                 description "1588.67 nm/188.706250 THz 3.125/6.25GHz spacing";
               }
               enum "1588.65" {
                 description "1588.65 nm/188.709375 THz 3.125GHz spacing";
               }
               enum "1588.62" {
                 description "1588.62 nm/188.712500 THz 3.125/6.25/12.5GHz spacing";
               }
               enum "1588.59" {
                 description "1588.59 nm/188.715625 THz 3.125GHz spacing";
               }
               enum "1588.57" {
                 description "1588.57 nm/188.718750 THz 3.125/6.25GHz spacing";
               }
               enum "1588.54" {
                 description "1588.54 nm/188.721875 THz 3.125GHz spacing";
               }
               enum "1588.51" {
                 description "1588.51 nm/188.725000 THz 3.125/6.25/12.5GHz spacing";
               }
               enum "1588.49" {
                 description "1588.49 nm/188.728125 THz 3.125GHz spacing";
               }
               enum "1588.46" {
                 description "1588.46 nm/188.731250 THz 3.125/6.25GHz spacing";
               }
               enum "1588.44" {
                 description "1588.44 nm/188.734375 THz 3.125GHz spacing";
               }
               enum "1588.41" {
                 description "1588.41 nm/188.737500 THz 3.125/6.25/12.5GHz spacing";
               }
               enum "1588.38" {
                 description "1588.38 nm/188.740625 THz 3.125GHz spacing";
               }
               enum "1588.36" {
                 description "1588.36 nm/188.743750 THz 3.125/6.25GHz spacing";
               }
               enum "1588.33" {
                 description "1588.33 nm/188.746875 THz 3.125GHz spacing";
               }
               enum "1588.30" {
                 description "1588.30 nm/188.750000 THz 3.125/6.25/12.5/50/75GHz spacing";
               }
               enum "1588.28" {
                 description "1588.28 nm/188.753125 THz 3.125GHz spacing";
               }
               enum "1588.25" {
                 description "1588.25 nm/188.756250 THz 3.125/6.25GHz spacing";
               }
               enum "1588.23" {
                 description "1588.23 nm/188.759375 THz 3.125GHz spacing";
               }
               enum "1588.20" {
                 description "1588.20 nm/188.762500 THz 3.125/6.25/12.5GHz spacing";
               }
               enum "1588.17" {
                 description "1588.17 nm/188.765625 THz 3.125GHz spacing";
               }
               enum "1588.15" {
                 description "1588.15 nm/188.768750 THz 3.125/6.25GHz spacing";
               }
               enum "1588.12" {
                 description "1588.12 nm/188.771875 THz 3.125GHz spacing";
               }
               enum "1588.09" {
                 description "1588.09 nm/188.775000 THz 3.125/6.25/12.5GHz spacing";
               }
               enum "1588.07" {
                 description "1588.07 nm/188.778125 THz 3.125GHz spacing";
               }
               enum "1588.04" {
                 description "1588.04 nm/188.781250 THz 3.125/6.25GHz spacing";
               }
               enum "1588.02" {
                 description "1588.02 nm/188.784375 THz 3.125GHz spacing";
               }
               enum "1587.99" {
                 description "1587.99 nm/188.787500 THz 3.125/6.25/12.5GHz spacing";
               }
               enum "1587.96" {
                 description "1587.96 nm/188.790625 THz 3.125GHz spacing";
               }
               enum "1587.94" {
                 description "1587.94 nm/188.793750 THz 3.125/6.25GHz spacing";
               }
               enum "1587.91" {
                 description "1587.91 nm/188.796875 THz 3.125GHz spacing";
               }
               enum "1587.88" {
                 description "1587.88 nm/188.800000 THz 3.125/6.25/12.5/100GHz spacing";
               }
               enum "1587.86" {
                 description "1587.86 nm/188.803125 THz 3.125GHz spacing";
               }
               enum "1587.83" {
                 description "1587.83 nm/188.806250 THz 3.125/6.25GHz spacing";
               }
               enum "1587.80" {
                 description "1587.80 nm/188.809375 THz 3.125GHz spacing";
               }
               enum "1587.78" {
                 description "1587.78 nm/188.812500 THz 3.125/6.25/12.5GHz spacing";
               }
               enum "1587.75" {
                 description "1587.75 nm/188.815625 THz 3.125GHz spacing";
               }
               enum "1587.73" {
                 description "1587.73 nm/188.818750 THz 3.125/6.25GHz spacing";
               }
               enum "1587.70" {
                 description "1587.70 nm/188.821875 THz 3.125GHz spacing";
               }
               enum "1587.67" {
                 description "1587.67 nm/188.825000 THz 3.125/6.25/12.5/75GHz spacing";
               }
               enum "1587.65" {
                 description "1587.65 nm/188.828125 THz 3.125GHz spacing";
               }
               enum "1587.62" {
                 description "1587.62 nm/188.831250 THz 3.125/6.25GHz spacing";
               }
               enum "1587.59" {
                 description "1587.59 nm/188.834375 THz 3.125GHz spacing";
               }
               enum "1587.57" {
                 description "1587.57 nm/188.837500 THz 3.125/6.25/12.5GHz spacing";
               }
               enum "1587.54" {
                 description "1587.54 nm/188.840625 THz 3.125GHz spacing";
               }
               enum "1587.52" {
                 description "1587.52 nm/188.843750 THz 3.125/6.25GHz spacing";
               }
               enum "1587.49" {
                 description "1587.49 nm/188.846875 THz 3.125GHz spacing";
               }
               enum "1587.46" {
                 description "1587.46 nm/188.850000 THz 3.125/6.25/12.5/50GHz spacing";
               }
               enum "1587.44" {
                 description "1587.44 nm/188.853125 THz 3.125GHz spacing";
               }
               enum "1587.41" {
                 description "1587.41 nm/188.856250 THz 3.125/6.25GHz spacing";
               }
               enum "1587.38" {
                 description "1587.38 nm/188.859375 THz 3.125GHz spacing";
               }
               enum "1587.36" {
                 description "1587.36 nm/188.862500 THz 3.125/6.25/12.5GHz spacing";
               }
               enum "1587.33" {
                 description "1587.33 nm/188.865625 THz 3.125GHz spacing";
               }
               enum "1587.31" {
                 description "1587.31 nm/188.868750 THz 3.125/6.25GHz spacing";
               }
               enum "1587.28" {
                 description "1587.28 nm/188.871875 THz 3.125GHz spacing";
               }
               enum "1587.25" {
                 description "1587.25 nm/188.875000 THz 3.125/6.25/12.5GHz spacing";
               }
               enum "1587.23" {
                 description "1587.23 nm/188.878125 THz 3.125GHz spacing";
               }
               enum "1587.20" {
                 description "1587.20 nm/188.881250 THz 3.125/6.25GHz spacing";
               }
               enum "1587.17" {
                 description "1587.17 nm/188.884375 THz 3.125GHz spacing";
               }
               enum "1587.15" {
                 description "1587.15 nm/188.887500 THz 3.125/6.25/12.5GHz spacing";
               }
               enum "1587.12" {
                 description "1587.12 nm/188.890625 THz 3.125GHz spacing";
               }
               enum "1587.10" {
                 description "1587.10 nm/188.893750 THz 3.125/6.25GHz spacing";
               }
               enum "1587.07" {
                 description "1587.07 nm/188.896875 THz 3.125GHz spacing";
               }
               enum "1587.04" {
                 description "1587.04 nm/188.900000 THz 3.125/6.25/12.5/100GHz spacing";
               }
               enum "1587.02" {
                 description "1587.02 nm/188.903125 THz 3.125GHz spacing";
               }
               enum "1586.99" {
                 description "1586.99 nm/188.906250 THz 3.125/6.25GHz spacing";
               }
               enum "1586.96" {
                 description "1586.96 nm/188.909375 THz 3.125GHz spacing";
               }
               enum "1586.94" {
                 description "1586.94 nm/188.912500 THz 3.125/6.25/12.5GHz spacing";
               }
               enum "1586.91" {
                 description "1586.91 nm/188.915625 THz 3.125GHz spacing";
               }
               enum "1586.89" {
                 description "1586.89 nm/188.918750 THz 3.125/6.25GHz spacing";
               }
               enum "1586.86" {
                 description "1586.86 nm/188.921875 THz 3.125GHz spacing";
               }
               enum "1586.83" {
                 description "1586.83 nm/188.925000 THz 3.125/6.25/12.5GHz spacing";
               }
               enum "1586.81" {
                 description "1586.81 nm/188.928125 THz 3.125GHz spacing";
               }
               enum "1586.78" {
                 description "1586.78 nm/188.931250 THz 3.125/6.25GHz spacing";
               }
               enum "1586.75" {
                 description "1586.75 nm/188.934375 THz 3.125GHz spacing";
               }
               enum "1586.73" {
                 description "1586.73 nm/188.937500 THz 3.125/6.25/12.5GHz spacing";
               }
               enum "1586.70" {
                 description "1586.70 nm/188.940625 THz 3.125GHz spacing";
               }
               enum "1586.68" {
                 description "1586.68 nm/188.943750 THz 3.125/6.25GHz spacing";
               }
               enum "1586.65" {
                 description "1586.65 nm/188.946875 THz 3.125GHz spacing";
               }
               enum "1586.62" {
                 description "1586.62 nm/188.950000 THz 3.125/6.25/12.5/50GHz spacing";
               }
               enum "1586.60" {
                 description "1586.60 nm/188.953125 THz 3.125GHz spacing";
               }
               enum "1586.57" {
                 description "1586.57 nm/188.956250 THz 3.125/6.25GHz spacing";
               }
               enum "1586.54" {
                 description "1586.54 nm/188.959375 THz 3.125GHz spacing";
               }
               enum "1586.52" {
                 description "1586.52 nm/188.962500 THz 3.125/6.25/12.5GHz spacing";
               }
               enum "1586.49" {
                 description "1586.49 nm/188.965625 THz 3.125GHz spacing";
               }
               enum "1586.47" {
                 description "1586.47 nm/188.968750 THz 3.125/6.25GHz spacing";
               }
               enum "1586.44" {
                 description "1586.44 nm/188.971875 THz 3.125GHz spacing";
               }
               enum "1586.41" {
                 description "1586.41 nm/188.975000 THz 3.125/6.25/12.5/75GHz spacing";
               }
               enum "1586.39" {
                 description "1586.39 nm/188.978125 THz 3.125GHz spacing";
               }
               enum "1586.36" {
                 description "1586.36 nm/188.981250 THz 3.125/6.25GHz spacing";
               }
               enum "1586.33" {
                 description "1586.33 nm/188.984375 THz 3.125GHz spacing";
               }
               enum "1586.31" {
                 description "1586.31 nm/188.987500 THz 3.125/6.25/12.5GHz spacing";
               }
               enum "1586.28" {
                 description "1586.28 nm/188.990625 THz 3.125GHz spacing";
               }
               enum "1586.26" {
                 description "1586.26 nm/188.993750 THz 3.125/6.25GHz spacing";
               }
               enum "1586.23" {
                 description "1586.23 nm/188.996875 THz 3.125GHz spacing";
               }
               enum "1586.20" {
                 description "1586.20 nm/189.000000 THz 3.125/6.25/12.5/50/75/100GHz spacing";
               }
               enum "1586.18" {
                 description "1586.18 nm/189.003125 THz 3.125GHz spacing";
               }
               enum "1586.15" {
                 description "1586.15 nm/189.006250 THz 3.125/6.25GHz spacing";
               }
               enum "1586.12" {
                 description "1586.12 nm/189.009375 THz 3.125GHz spacing";
               }
               enum "1586.10" {
                 description "1586.10 nm/189.012500 THz 3.125/6.25/12.5GHz spacing";
               }
               enum "1586.07" {
                 description "1586.07 nm/189.015625 THz 3.125GHz spacing";
               }
               enum "1586.05" {
                 description "1586.05 nm/189.018750 THz 3.125/6.25GHz spacing";
               }
               enum "1586.02" {
                 description "1586.02 nm/189.021875 THz 3.125GHz spacing";
               }
               enum "1585.99" {
                 description "1585.99 nm/189.025000 THz 3.125/6.25/12.5GHz spacing";
               }
               enum "1585.97" {
                 description "1585.97 nm/189.028125 THz 3.125GHz spacing";
               }
               enum "1585.94" {
                 description "1585.94 nm/189.031250 THz 3.125/6.25GHz spacing";
               }
               enum "1585.92" {
                 description "1585.92 nm/189.034375 THz 3.125GHz spacing";
               }
               enum "1585.89" {
                 description "1585.89 nm/189.037500 THz 3.125/6.25/12.5GHz spacing";
               }
               enum "1585.86" {
                 description "1585.86 nm/189.040625 THz 3.125GHz spacing";
               }
               enum "1585.84" {
                 description "1585.84 nm/189.043750 THz 3.125/6.25GHz spacing";
               }
               enum "1585.81" {
                 description "1585.81 nm/189.046875 THz 3.125GHz spacing";
               }
               enum "1585.78" {
                 description "1585.78 nm/189.050000 THz 3.125/6.25/12.5/50/75GHz spacing";
               }
               enum "1585.76" {
                 description "1585.76 nm/189.053125 THz 3.125GHz spacing";
               }
               enum "1585.73" {
                 description "1585.73 nm/189.056250 THz 3.125/6.25GHz spacing";
               }
               enum "1585.71" {
                 description "1585.71 nm/189.059375 THz 3.125GHz spacing";
               }
               enum "1585.68" {
                 description "1585.68 nm/189.062500 THz 3.125/6.25/12.5GHz spacing";
               }
               enum "1585.65" {
                 description "1585.65 nm/189.065625 THz 3.125GHz spacing";
               }
               enum "1585.63" {
                 description "1585.63 nm/189.068750 THz 3.125/6.25GHz spacing";
               }
               enum "1585.60" {
                 description "1585.60 nm/189.071875 THz 3.125GHz spacing";
               }
               enum "1585.57" {
                 description "1585.57 nm/189.075000 THz 3.125/6.25/12.5GHz spacing";
               }
               enum "1585.55" {
                 description "1585.55 nm/189.078125 THz 3.125GHz spacing";
               }
               enum "1585.52" {
                 description "1585.52 nm/189.081250 THz 3.125/6.25GHz spacing";
               }
               enum "1585.50" {
                 description "1585.50 nm/189.084375 THz 3.125GHz spacing";
               }
               enum "1585.47" {
                 description "1585.47 nm/189.087500 THz 3.125/6.25/12.5GHz spacing";
               }
               enum "1585.44" {
                 description "1585.44 nm/189.090625 THz 3.125GHz spacing";
               }
               enum "1585.42" {
                 description "1585.42 nm/189.093750 THz 3.125/6.25GHz spacing";
               }
               enum "1585.39" {
                 description "1585.39 nm/189.096875 THz 3.125GHz spacing";
               }
               enum "1585.36" {
                 description "1585.36 nm/189.100000 THz 3.125/6.25/12.5/100GHz spacing";
               }
               enum "1585.34" {
                 description "1585.34 nm/189.103125 THz 3.125GHz spacing";
               }
               enum "1585.31" {
                 description "1585.31 nm/189.106250 THz 3.125/6.25GHz spacing";
               }
               enum "1585.29" {
                 description "1585.29 nm/189.109375 THz 3.125GHz spacing";
               }
               enum "1585.26" {
                 description "1585.26 nm/189.112500 THz 3.125/6.25/12.5GHz spacing";
               }
               enum "1585.23" {
                 description "1585.23 nm/189.115625 THz 3.125GHz spacing";
               }
               enum "1585.21" {
                 description "1585.21 nm/189.118750 THz 3.125/6.25GHz spacing";
               }
               enum "1585.18" {
                 description "1585.18 nm/189.121875 THz 3.125GHz spacing";
               }
               enum "1585.16" {
                 description "1585.16 nm/189.125000 THz 3.125/6.25/12.5/75GHz spacing";
               }
               enum "1585.13" {
                 description "1585.13 nm/189.128125 THz 3.125GHz spacing";
               }
               enum "1585.10" {
                 description "1585.10 nm/189.131250 THz 3.125/6.25GHz spacing";
               }
               enum "1585.08" {
                 description "1585.08 nm/189.134375 THz 3.125GHz spacing";
               }
               enum "1585.05" {
                 description "1585.05 nm/189.137500 THz 3.125/6.25/12.5GHz spacing";
               }
               enum "1585.02" {
                 description "1585.02 nm/189.140625 THz 3.125GHz spacing";
               }
               enum "1585.00" {
                 description "1585.00 nm/189.143750 THz 3.125/6.25GHz spacing";
               }
               enum "1584.97" {
                 description "1584.97 nm/189.146875 THz 3.125GHz spacing";
               }
               enum "1584.95" {
                 description "1584.95 nm/189.150000 THz 3.125/6.25/12.5/50GHz spacing";
               }
               enum "1584.92" {
                 description "1584.92 nm/189.153125 THz 3.125GHz spacing";
               }
               enum "1584.89" {
                 description "1584.89 nm/189.156250 THz 3.125/6.25GHz spacing";
               }
               enum "1584.87" {
                 description "1584.87 nm/189.159375 THz 3.125GHz spacing";
               }
               enum "1584.84" {
                 description "1584.84 nm/189.162500 THz 3.125/6.25/12.5GHz spacing";
               }
               enum "1584.81" {
                 description "1584.81 nm/189.165625 THz 3.125GHz spacing";
               }
               enum "1584.79" {
                 description "1584.79 nm/189.168750 THz 3.125/6.25GHz spacing";
               }
               enum "1584.76" {
                 description "1584.76 nm/189.171875 THz 3.125GHz spacing";
               }
               enum "1584.74" {
                 description "1584.74 nm/189.175000 THz 3.125/6.25/12.5GHz spacing";
               }
               enum "1584.71" {
                 description "1584.71 nm/189.178125 THz 3.125GHz spacing";
               }
               enum "1584.68" {
                 description "1584.68 nm/189.181250 THz 3.125/6.25GHz spacing";
               }
               enum "1584.66" {
                 description "1584.66 nm/189.184375 THz 3.125GHz spacing";
               }
               enum "1584.63" {
                 description "1584.63 nm/189.187500 THz 3.125/6.25/12.5GHz spacing";
               }
               enum "1584.61" {
                 description "1584.61 nm/189.190625 THz 3.125GHz spacing";
               }
               enum "1584.58" {
                 description "1584.58 nm/189.193750 THz 3.125/6.25GHz spacing";
               }
               enum "1584.55" {
                 description "1584.55 nm/189.196875 THz 3.125GHz spacing";
               }
               enum "1584.53" {
                 description "1584.53 nm/189.200000 THz 3.125/6.25/12.5/100GHz spacing";
               }
               enum "1584.50" {
                 description "1584.50 nm/189.203125 THz 3.125GHz spacing";
               }
               enum "1584.47" {
                 description "1584.47 nm/189.206250 THz 3.125/6.25GHz spacing";
               }
               enum "1584.45" {
                 description "1584.45 nm/189.209375 THz 3.125GHz spacing";
               }
               enum "1584.42" {
                 description "1584.42 nm/189.212500 THz 3.125/6.25/12.5GHz spacing";
               }
               enum "1584.40" {
                 description "1584.40 nm/189.215625 THz 3.125GHz spacing";
               }
               enum "1584.37" {
                 description "1584.37 nm/189.218750 THz 3.125/6.25GHz spacing";
               }
               enum "1584.34" {
                 description "1584.34 nm/189.221875 THz 3.125GHz spacing";
               }
               enum "1584.32" {
                 description "1584.32 nm/189.225000 THz 3.125/6.25/12.5GHz spacing";
               }
               enum "1584.29" {
                 description "1584.29 nm/189.228125 THz 3.125GHz spacing";
               }
               enum "1584.27" {
                 description "1584.27 nm/189.231250 THz 3.125/6.25GHz spacing";
               }
               enum "1584.24" {
                 description "1584.24 nm/189.234375 THz 3.125GHz spacing";
               }
               enum "1584.21" {
                 description "1584.21 nm/189.237500 THz 3.125/6.25/12.5GHz spacing";
               }
               enum "1584.19" {
                 description "1584.19 nm/189.240625 THz 3.125GHz spacing";
               }
               enum "1584.16" {
                 description "1584.16 nm/189.243750 THz 3.125/6.25GHz spacing";
               }
               enum "1584.13" {
                 description "1584.13 nm/189.246875 THz 3.125GHz spacing";
               }
               enum "1584.11" {
                 description "1584.11 nm/189.250000 THz 3.125/6.25/12.5/50GHz spacing";
               }
               enum "1584.08" {
                 description "1584.08 nm/189.253125 THz 3.125GHz spacing";
               }
               enum "1584.06" {
                 description "1584.06 nm/189.256250 THz 3.125/6.25GHz spacing";
               }
               enum "1584.03" {
                 description "1584.03 nm/189.259375 THz 3.125GHz spacing";
               }
               enum "1584.00" {
                 description "1584.00 nm/189.262500 THz 3.125/6.25/12.5GHz spacing";
               }
               enum "1583.98" {
                 description "1583.98 nm/189.265625 THz 3.125GHz spacing";
               }
               enum "1583.95" {
                 description "1583.95 nm/189.268750 THz 3.125/6.25GHz spacing";
               }
               enum "1583.93" {
                 description "1583.93 nm/189.271875 THz 3.125GHz spacing";
               }
               enum "1583.90" {
                 description "1583.90 nm/189.275000 THz 3.125/6.25/12.5/75GHz spacing";
               }
               enum "1583.87" {
                 description "1583.87 nm/189.278125 THz 3.125GHz spacing";
               }
               enum "1583.85" {
                 description "1583.85 nm/189.281250 THz 3.125/6.25GHz spacing";
               }
               enum "1583.82" {
                 description "1583.82 nm/189.284375 THz 3.125GHz spacing";
               }
               enum "1583.79" {
                 description "1583.79 nm/189.287500 THz 3.125/6.25/12.5GHz spacing";
               }
               enum "1583.77" {
                 description "1583.77 nm/189.290625 THz 3.125GHz spacing";
               }
               enum "1583.74" {
                 description "1583.74 nm/189.293750 THz 3.125/6.25GHz spacing";
               }
               enum "1583.72" {
                 description "1583.72 nm/189.296875 THz 3.125GHz spacing";
               }
               enum "1583.69" {
                 description "1583.69 nm/189.300000 THz 3.125/6.25/12.5/50/75/100GHz spacing";
               }
               enum "1583.66" {
                 description "1583.66 nm/189.303125 THz 3.125GHz spacing";
               }
               enum "1583.64" {
                 description "1583.64 nm/189.306250 THz 3.125/6.25GHz spacing";
               }
               enum "1583.61" {
                 description "1583.61 nm/189.309375 THz 3.125GHz spacing";
               }
               enum "1583.59" {
                 description "1583.59 nm/189.312500 THz 3.125/6.25/12.5GHz spacing";
               }
               enum "1583.56" {
                 description "1583.56 nm/189.315625 THz 3.125GHz spacing";
               }
               enum "1583.53" {
                 description "1583.53 nm/189.318750 THz 3.125/6.25GHz spacing";
               }
               enum "1583.51" {
                 description "1583.51 nm/189.321875 THz 3.125GHz spacing";
               }
               enum "1583.48" {
                 description "1583.48 nm/189.325000 THz 3.125/6.25/12.5GHz spacing";
               }
               enum "1583.45" {
                 description "1583.45 nm/189.328125 THz 3.125GHz spacing";
               }
               enum "1583.43" {
                 description "1583.43 nm/189.331250 THz 3.125/6.25GHz spacing";
               }
               enum "1583.40" {
                 description "1583.40 nm/189.334375 THz 3.125GHz spacing";
               }
               enum "1583.38" {
                 description "1583.38 nm/189.337500 THz 3.125/6.25/12.5GHz spacing";
               }
               enum "1583.35" {
                 description "1583.35 nm/189.340625 THz 3.125GHz spacing";
               }
               enum "1583.32" {
                 description "1583.32 nm/189.343750 THz 3.125/6.25GHz spacing";
               }
               enum "1583.30" {
                 description "1583.30 nm/189.346875 THz 3.125GHz spacing";
               }
               enum "1583.27" {
                 description "1583.27 nm/189.350000 THz 3.125/6.25/12.5/50/75GHz spacing";
               }
               enum "1583.25" {
                 description "1583.25 nm/189.353125 THz 3.125GHz spacing";
               }
               enum "1583.22" {
                 description "1583.22 nm/189.356250 THz 3.125/6.25GHz spacing";
               }
               enum "1583.19" {
                 description "1583.19 nm/189.359375 THz 3.125GHz spacing";
               }
               enum "1583.17" {
                 description "1583.17 nm/189.362500 THz 3.125/6.25/12.5GHz spacing";
               }
               enum "1583.14" {
                 description "1583.14 nm/189.365625 THz 3.125GHz spacing";
               }
               enum "1583.11" {
                 description "1583.11 nm/189.368750 THz 3.125/6.25GHz spacing";
               }
               enum "1583.09" {
                 description "1583.09 nm/189.371875 THz 3.125GHz spacing";
               }
               enum "1583.06" {
                 description "1583.06 nm/189.375000 THz 3.125/6.25/12.5GHz spacing";
               }
               enum "1583.04" {
                 description "1583.04 nm/189.378125 THz 3.125GHz spacing";
               }
               enum "1583.01" {
                 description "1583.01 nm/189.381250 THz 3.125/6.25GHz spacing";
               }
               enum "1582.98" {
                 description "1582.98 nm/189.384375 THz 3.125GHz spacing";
               }
               enum "1582.96" {
                 description "1582.96 nm/189.387500 THz 3.125/6.25/12.5GHz spacing";
               }
               enum "1582.93" {
                 description "1582.93 nm/189.390625 THz 3.125GHz spacing";
               }
               enum "1582.91" {
                 description "1582.91 nm/189.393750 THz 3.125/6.25GHz spacing";
               }
               enum "1582.88" {
                 description "1582.88 nm/189.396875 THz 3.125GHz spacing";
               }
               enum "1582.85" {
                 description "1582.85 nm/189.400000 THz 3.125/6.25/12.5/100GHz spacing";
               }
               enum "1582.83" {
                 description "1582.83 nm/189.403125 THz 3.125GHz spacing";
               }
               enum "1582.80" {
                 description "1582.80 nm/189.406250 THz 3.125/6.25GHz spacing";
               }
               enum "1582.78" {
                 description "1582.78 nm/189.409375 THz 3.125GHz spacing";
               }
               enum "1582.75" {
                 description "1582.75 nm/189.412500 THz 3.125/6.25/12.5GHz spacing";
               }
               enum "1582.72" {
                 description "1582.72 nm/189.415625 THz 3.125GHz spacing";
               }
               enum "1582.70" {
                 description "1582.70 nm/189.418750 THz 3.125/6.25GHz spacing";
               }
               enum "1582.67" {
                 description "1582.67 nm/189.421875 THz 3.125GHz spacing";
               }
               enum "1582.64" {
                 description "1582.64 nm/189.425000 THz 3.125/6.25/12.5/75GHz spacing";
               }
               enum "1582.62" {
                 description "1582.62 nm/189.428125 THz 3.125GHz spacing";
               }
               enum "1582.59" {
                 description "1582.59 nm/189.431250 THz 3.125/6.25GHz spacing";
               }
               enum "1582.57" {
                 description "1582.57 nm/189.434375 THz 3.125GHz spacing";
               }
               enum "1582.54" {
                 description "1582.54 nm/189.437500 THz 3.125/6.25/12.5GHz spacing";
               }
               enum "1582.51" {
                 description "1582.51 nm/189.440625 THz 3.125GHz spacing";
               }
               enum "1582.49" {
                 description "1582.49 nm/189.443750 THz 3.125/6.25GHz spacing";
               }
               enum "1582.46" {
                 description "1582.46 nm/189.446875 THz 3.125GHz spacing";
               }
               enum "1582.44" {
                 description "1582.44 nm/189.450000 THz 3.125/6.25/12.5/50GHz spacing";
               }
               enum "1582.41" {
                 description "1582.41 nm/189.453125 THz 3.125GHz spacing";
               }
               enum "1582.38" {
                 description "1582.38 nm/189.456250 THz 3.125/6.25GHz spacing";
               }
               enum "1582.36" {
                 description "1582.36 nm/189.459375 THz 3.125GHz spacing";
               }
               enum "1582.33" {
                 description "1582.33 nm/189.462500 THz 3.125/6.25/12.5GHz spacing";
               }
               enum "1582.31" {
                 description "1582.31 nm/189.465625 THz 3.125GHz spacing";
               }
               enum "1582.28" {
                 description "1582.28 nm/189.468750 THz 3.125/6.25GHz spacing";
               }
               enum "1582.25" {
                 description "1582.25 nm/189.471875 THz 3.125GHz spacing";
               }
               enum "1582.23" {
                 description "1582.23 nm/189.475000 THz 3.125/6.25/12.5GHz spacing";
               }
               enum "1582.20" {
                 description "1582.20 nm/189.478125 THz 3.125GHz spacing";
               }
               enum "1582.17" {
                 description "1582.17 nm/189.481250 THz 3.125/6.25GHz spacing";
               }
               enum "1582.15" {
                 description "1582.15 nm/189.484375 THz 3.125GHz spacing";
               }
               enum "1582.12" {
                 description "1582.12 nm/189.487500 THz 3.125/6.25/12.5GHz spacing";
               }
               enum "1582.10" {
                 description "1582.10 nm/189.490625 THz 3.125GHz spacing";
               }
               enum "1582.07" {
                 description "1582.07 nm/189.493750 THz 3.125/6.25GHz spacing";
               }
               enum "1582.04" {
                 description "1582.04 nm/189.496875 THz 3.125GHz spacing";
               }
               enum "1582.02" {
                 description "1582.02 nm/189.500000 THz 3.125/6.25/12.5/100GHz spacing";
               }
               enum "1581.99" {
                 description "1581.99 nm/189.503125 THz 3.125GHz spacing";
               }
               enum "1581.97" {
                 description "1581.97 nm/189.506250 THz 3.125/6.25GHz spacing";
               }
               enum "1581.94" {
                 description "1581.94 nm/189.509375 THz 3.125GHz spacing";
               }
               enum "1581.91" {
                 description "1581.91 nm/189.512500 THz 3.125/6.25/12.5GHz spacing";
               }
               enum "1581.89" {
                 description "1581.89 nm/189.515625 THz 3.125GHz spacing";
               }
               enum "1581.86" {
                 description "1581.86 nm/189.518750 THz 3.125/6.25GHz spacing";
               }
               enum "1581.84" {
                 description "1581.84 nm/189.521875 THz 3.125GHz spacing";
               }
               enum "1581.81" {
                 description "1581.81 nm/189.525000 THz 3.125/6.25/12.5GHz spacing";
               }
               enum "1581.78" {
                 description "1581.78 nm/189.528125 THz 3.125GHz spacing";
               }
               enum "1581.76" {
                 description "1581.76 nm/189.531250 THz 3.125/6.25GHz spacing";
               }
               enum "1581.73" {
                 description "1581.73 nm/189.534375 THz 3.125GHz spacing";
               }
               enum "1581.71" {
                 description "1581.71 nm/189.537500 THz 3.125/6.25/12.5GHz spacing";
               }
               enum "1581.68" {
                 description "1581.68 nm/189.540625 THz 3.125GHz spacing";
               }
               enum "1581.65" {
                 description "1581.65 nm/189.543750 THz 3.125/6.25GHz spacing";
               }
               enum "1581.63" {
                 description "1581.63 nm/189.546875 THz 3.125GHz spacing";
               }
               enum "1581.60" {
                 description "1581.60 nm/189.550000 THz 3.125/6.25/12.5/50GHz spacing";
               }
               enum "1581.57" {
                 description "1581.57 nm/189.553125 THz 3.125GHz spacing";
               }
               enum "1581.55" {
                 description "1581.55 nm/189.556250 THz 3.125/6.25GHz spacing";
               }
               enum "1581.52" {
                 description "1581.52 nm/189.559375 THz 3.125GHz spacing";
               }
               enum "1581.50" {
                 description "1581.50 nm/189.562500 THz 3.125/6.25/12.5GHz spacing";
               }
               enum "1581.47" {
                 description "1581.47 nm/189.565625 THz 3.125GHz spacing";
               }
               enum "1581.44" {
                 description "1581.44 nm/189.568750 THz 3.125/6.25GHz spacing";
               }
               enum "1581.42" {
                 description "1581.42 nm/189.571875 THz 3.125GHz spacing";
               }
               enum "1581.39" {
                 description "1581.39 nm/189.575000 THz 3.125/6.25/12.5/75GHz spacing";
               }
               enum "1581.37" {
                 description "1581.37 nm/189.578125 THz 3.125GHz spacing";
               }
               enum "1581.34" {
                 description "1581.34 nm/189.581250 THz 3.125/6.25GHz spacing";
               }
               enum "1581.31" {
                 description "1581.31 nm/189.584375 THz 3.125GHz spacing";
               }
               enum "1581.29" {
                 description "1581.29 nm/189.587500 THz 3.125/6.25/12.5GHz spacing";
               }
               enum "1581.26" {
                 description "1581.26 nm/189.590625 THz 3.125GHz spacing";
               }
               enum "1581.24" {
                 description "1581.24 nm/189.593750 THz 3.125/6.25GHz spacing";
               }
               enum "1581.21" {
                 description "1581.21 nm/189.596875 THz 3.125GHz spacing";
               }
               enum "1581.18" {
                 description "1581.18 nm/189.600000 THz 3.125/6.25/12.5/50/75/100GHz spacing";
               }
               enum "1581.16" {
                 description "1581.16 nm/189.603125 THz 3.125GHz spacing";
               }
               enum "1581.13" {
                 description "1581.13 nm/189.606250 THz 3.125/6.25GHz spacing";
               }
               enum "1581.11" {
                 description "1581.11 nm/189.609375 THz 3.125GHz spacing";
               }
               enum "1581.08" {
                 description "1581.08 nm/189.612500 THz 3.125/6.25/12.5GHz spacing";
               }
               enum "1581.05" {
                 description "1581.05 nm/189.615625 THz 3.125GHz spacing";
               }
               enum "1581.03" {
                 description "1581.03 nm/189.618750 THz 3.125/6.25GHz spacing";
               }
               enum "1581.00" {
                 description "1581.00 nm/189.621875 THz 3.125GHz spacing";
               }
               enum "1580.98" {
                 description "1580.98 nm/189.625000 THz 3.125/6.25/12.5GHz spacing";
               }
               enum "1580.95" {
                 description "1580.95 nm/189.628125 THz 3.125GHz spacing";
               }
               enum "1580.92" {
                 description "1580.92 nm/189.631250 THz 3.125/6.25GHz spacing";
               }
               enum "1580.90" {
                 description "1580.90 nm/189.634375 THz 3.125GHz spacing";
               }
               enum "1580.87" {
                 description "1580.87 nm/189.637500 THz 3.125/6.25/12.5GHz spacing";
               }
               enum "1580.85" {
                 description "1580.85 nm/189.640625 THz 3.125GHz spacing";
               }
               enum "1580.82" {
                 description "1580.82 nm/189.643750 THz 3.125/6.25GHz spacing";
               }
               enum "1580.79" {
                 description "1580.79 nm/189.646875 THz 3.125GHz spacing";
               }
               enum "1580.77" {
                 description "1580.77 nm/189.650000 THz 3.125/6.25/12.5/50/75GHz spacing";
               }
               enum "1580.74" {
                 description "1580.74 nm/189.653125 THz 3.125GHz spacing";
               }
               enum "1580.71" {
                 description "1580.71 nm/189.656250 THz 3.125/6.25GHz spacing";
               }
               enum "1580.69" {
                 description "1580.69 nm/189.659375 THz 3.125GHz spacing";
               }
               enum "1580.66" {
                 description "1580.66 nm/189.662500 THz 3.125/6.25/12.5GHz spacing";
               }
               enum "1580.64" {
                 description "1580.64 nm/189.665625 THz 3.125GHz spacing";
               }
               enum "1580.61" {
                 description "1580.61 nm/189.668750 THz 3.125/6.25GHz spacing";
               }
               enum "1580.58" {
                 description "1580.58 nm/189.671875 THz 3.125GHz spacing";
               }
               enum "1580.56" {
                 description "1580.56 nm/189.675000 THz 3.125/6.25/12.5GHz spacing";
               }
               enum "1580.53" {
                 description "1580.53 nm/189.678125 THz 3.125GHz spacing";
               }
               enum "1580.51" {
                 description "1580.51 nm/189.681250 THz 3.125/6.25GHz spacing";
               }
               enum "1580.48" {
                 description "1580.48 nm/189.684375 THz 3.125GHz spacing";
               }
               enum "1580.45" {
                 description "1580.45 nm/189.687500 THz 3.125/6.25/12.5GHz spacing";
               }
               enum "1580.43" {
                 description "1580.43 nm/189.690625 THz 3.125GHz spacing";
               }
               enum "1580.40" {
                 description "1580.40 nm/189.693750 THz 3.125/6.25GHz spacing";
               }
               enum "1580.38" {
                 description "1580.38 nm/189.696875 THz 3.125GHz spacing";
               }
               enum "1580.35" {
                 description "1580.35 nm/189.700000 THz 3.125/6.25/12.5/100GHz spacing";
               }
               enum "1580.32" {
                 description "1580.32 nm/189.703125 THz 3.125GHz spacing";
               }
               enum "1580.30" {
                 description "1580.30 nm/189.706250 THz 3.125/6.25GHz spacing";
               }
               enum "1580.27" {
                 description "1580.27 nm/189.709375 THz 3.125GHz spacing";
               }
               enum "1580.25" {
                 description "1580.25 nm/189.712500 THz 3.125/6.25/12.5GHz spacing";
               }
               enum "1580.22" {
                 description "1580.22 nm/189.715625 THz 3.125GHz spacing";
               }
               enum "1580.19" {
                 description "1580.19 nm/189.718750 THz 3.125/6.25GHz spacing";
               }
               enum "1580.17" {
                 description "1580.17 nm/189.721875 THz 3.125GHz spacing";
               }
               enum "1580.14" {
                 description "1580.14 nm/189.725000 THz 3.125/6.25/12.5/75GHz spacing";
               }
               enum "1580.12" {
                 description "1580.12 nm/189.728125 THz 3.125GHz spacing";
               }
               enum "1580.09" {
                 description "1580.09 nm/189.731250 THz 3.125/6.25GHz spacing";
               }
               enum "1580.06" {
                 description "1580.06 nm/189.734375 THz 3.125GHz spacing";
               }
               enum "1580.04" {
                 description "1580.04 nm/189.737500 THz 3.125/6.25/12.5GHz spacing";
               }
               enum "1580.01" {
                 description "1580.01 nm/189.740625 THz 3.125GHz spacing";
               }
               enum "1579.99" {
                 description "1579.99 nm/189.743750 THz 3.125/6.25GHz spacing";
               }
               enum "1579.96" {
                 description "1579.96 nm/189.746875 THz 3.125GHz spacing";
               }
               enum "1579.93" {
                 description "1579.93 nm/189.750000 THz 3.125/6.25/12.5/50GHz spacing";
               }
               enum "1579.91" {
                 description "1579.91 nm/189.753125 THz 3.125GHz spacing";
               }
               enum "1579.88" {
                 description "1579.88 nm/189.756250 THz 3.125/6.25GHz spacing";
               }
               enum "1579.86" {
                 description "1579.86 nm/189.759375 THz 3.125GHz spacing";
               }
               enum "1579.83" {
                 description "1579.83 nm/189.762500 THz 3.125/6.25/12.5GHz spacing";
               }
               enum "1579.80" {
                 description "1579.80 nm/189.765625 THz 3.125GHz spacing";
               }
               enum "1579.78" {
                 description "1579.78 nm/189.768750 THz 3.125/6.25GHz spacing";
               }
               enum "1579.75" {
                 description "1579.75 nm/189.771875 THz 3.125GHz spacing";
               }
               enum "1579.73" {
                 description "1579.73 nm/189.775000 THz 3.125/6.25/12.5GHz spacing";
               }
               enum "1579.70" {
                 description "1579.70 nm/189.778125 THz 3.125GHz spacing";
               }
               enum "1579.67" {
                 description "1579.67 nm/189.781250 THz 3.125/6.25GHz spacing";
               }
               enum "1579.65" {
                 description "1579.65 nm/189.784375 THz 3.125GHz spacing";
               }
               enum "1579.62" {
                 description "1579.62 nm/189.787500 THz 3.125/6.25/12.5GHz spacing";
               }
               enum "1579.60" {
                 description "1579.60 nm/189.790625 THz 3.125GHz spacing";
               }
               enum "1579.57" {
                 description "1579.57 nm/189.793750 THz 3.125/6.25GHz spacing";
               }
               enum "1579.54" {
                 description "1579.54 nm/189.796875 THz 3.125GHz spacing";
               }
               enum "1579.52" {
                 description "1579.52 nm/189.800000 THz 3.125/6.25/12.5/100GHz spacing";
               }
               enum "1579.49" {
                 description "1579.49 nm/189.803125 THz 3.125GHz spacing";
               }
               enum "1579.47" {
                 description "1579.47 nm/189.806250 THz 3.125/6.25GHz spacing";
               }
               enum "1579.44" {
                 description "1579.44 nm/189.809375 THz 3.125GHz spacing";
               }
               enum "1579.41" {
                 description "1579.41 nm/189.812500 THz 3.125/6.25/12.5GHz spacing";
               }
               enum "1579.39" {
                 description "1579.39 nm/189.815625 THz 3.125GHz spacing";
               }
               enum "1579.36" {
                 description "1579.36 nm/189.818750 THz 3.125/6.25GHz spacing";
               }
               enum "1579.34" {
                 description "1579.34 nm/189.821875 THz 3.125GHz spacing";
               }
               enum "1579.31" {
                 description "1579.31 nm/189.825000 THz 3.125/6.25/12.5GHz spacing";
               }
               enum "1579.28" {
                 description "1579.28 nm/189.828125 THz 3.125GHz spacing";
               }
               enum "1579.26" {
                 description "1579.26 nm/189.831250 THz 3.125/6.25GHz spacing";
               }
               enum "1579.23" {
                 description "1579.23 nm/189.834375 THz 3.125GHz spacing";
               }
               enum "1579.21" {
                 description "1579.21 nm/189.837500 THz 3.125/6.25/12.5GHz spacing";
               }
               enum "1579.18" {
                 description "1579.18 nm/189.840625 THz 3.125GHz spacing";
               }
               enum "1579.15" {
                 description "1579.15 nm/189.843750 THz 3.125/6.25GHz spacing";
               }
               enum "1579.13" {
                 description "1579.13 nm/189.846875 THz 3.125GHz spacing";
               }
               enum "1579.10" {
                 description "1579.10 nm/189.850000 THz 3.125/6.25/12.5/50GHz spacing";
               }
               enum "1579.08" {
                 description "1579.08 nm/189.853125 THz 3.125GHz spacing";
               }
               enum "1579.05" {
                 description "1579.05 nm/189.856250 THz 3.125/6.25GHz spacing";
               }
               enum "1579.02" {
                 description "1579.02 nm/189.859375 THz 3.125GHz spacing";
               }
               enum "1579.00" {
                 description "1579.00 nm/189.862500 THz 3.125/6.25/12.5GHz spacing";
               }
               enum "1578.97" {
                 description "1578.97 nm/189.865625 THz 3.125GHz spacing";
               }
               enum "1578.95" {
                 description "1578.95 nm/189.868750 THz 3.125/6.25GHz spacing";
               }
               enum "1578.92" {
                 description "1578.92 nm/189.871875 THz 3.125GHz spacing";
               }
               enum "1578.89" {
                 description "1578.89 nm/189.875000 THz 3.125/6.25/12.5/75GHz spacing";
               }
               enum "1578.87" {
                 description "1578.87 nm/189.878125 THz 3.125GHz spacing";
               }
               enum "1578.84" {
                 description "1578.84 nm/189.881250 THz 3.125/6.25GHz spacing";
               }
               enum "1578.82" {
                 description "1578.82 nm/189.884375 THz 3.125GHz spacing";
               }
               enum "1578.79" {
                 description "1578.79 nm/189.887500 THz 3.125/6.25/12.5GHz spacing";
               }
               enum "1578.76" {
                 description "1578.76 nm/189.890625 THz 3.125GHz spacing";
               }
               enum "1578.74" {
                 description "1578.74 nm/189.893750 THz 3.125/6.25GHz spacing";
               }
               enum "1578.71" {
                 description "1578.71 nm/189.896875 THz 3.125GHz spacing";
               }
               enum "1578.69" {
                 description "1578.69 nm/189.900000 THz 3.125/6.25/12.5/50/75/100GHz spacing";
               }
               enum "1578.66" {
                 description "1578.66 nm/189.903125 THz 3.125GHz spacing";
               }
               enum "1578.63" {
                 description "1578.63 nm/189.906250 THz 3.125/6.25GHz spacing";
               }
               enum "1578.61" {
                 description "1578.61 nm/189.909375 THz 3.125GHz spacing";
               }
               enum "1578.58" {
                 description "1578.58 nm/189.912500 THz 3.125/6.25/12.5GHz spacing";
               }
               enum "1578.56" {
                 description "1578.56 nm/189.915625 THz 3.125GHz spacing";
               }
               enum "1578.53" {
                 description "1578.53 nm/189.918750 THz 3.125/6.25GHz spacing";
               }
               enum "1578.50" {
                 description "1578.50 nm/189.921875 THz 3.125GHz spacing";
               }
               enum "1578.48" {
                 description "1578.48 nm/189.925000 THz 3.125/6.25/12.5GHz spacing";
               }
               enum "1578.45" {
                 description "1578.45 nm/189.928125 THz 3.125GHz spacing";
               }
               enum "1578.43" {
                 description "1578.43 nm/189.931250 THz 3.125/6.25GHz spacing";
               }
               enum "1578.40" {
                 description "1578.40 nm/189.934375 THz 3.125GHz spacing";
               }
               enum "1578.37" {
                 description "1578.37 nm/189.937500 THz 3.125/6.25/12.5GHz spacing";
               }
               enum "1578.35" {
                 description "1578.35 nm/189.940625 THz 3.125GHz spacing";
               }
               enum "1578.32" {
                 description "1578.32 nm/189.943750 THz 3.125/6.25GHz spacing";
               }
               enum "1578.30" {
                 description "1578.30 nm/189.946875 THz 3.125GHz spacing";
               }
               enum "1578.27" {
                 description "1578.27 nm/189.950000 THz 3.125/6.25/12.5/50/75GHz spacing";
               }
               enum "1578.24" {
                 description "1578.24 nm/189.953125 THz 3.125GHz spacing";
               }
               enum "1578.22" {
                 description "1578.22 nm/189.956250 THz 3.125/6.25GHz spacing";
               }
               enum "1578.19" {
                 description "1578.19 nm/189.959375 THz 3.125GHz spacing";
               }
               enum "1578.17" {
                 description "1578.17 nm/189.962500 THz 3.125/6.25/12.5GHz spacing";
               }
               enum "1578.14" {
                 description "1578.14 nm/189.965625 THz 3.125GHz spacing";
               }
               enum "1578.11" {
                 description "1578.11 nm/189.968750 THz 3.125/6.25GHz spacing";
               }
               enum "1578.09" {
                 description "1578.09 nm/189.971875 THz 3.125GHz spacing";
               }
               enum "1578.06" {
                 description "1578.06 nm/189.975000 THz 3.125/6.25/12.5GHz spacing";
               }
               enum "1578.04" {
                 description "1578.04 nm/189.978125 THz 3.125GHz spacing";
               }
               enum "1578.01" {
                 description "1578.01 nm/189.981250 THz 3.125/6.25GHz spacing";
               }
               enum "1577.98" {
                 description "1577.98 nm/189.984375 THz 3.125GHz spacing";
               }
               enum "1577.96" {
                 description "1577.96 nm/189.987500 THz 3.125/6.25/12.5GHz spacing";
               }
               enum "1577.93" {
                 description "1577.93 nm/189.990625 THz 3.125GHz spacing";
               }
               enum "1577.91" {
                 description "1577.91 nm/189.993750 THz 3.125/6.25GHz spacing";
               }
               enum "1577.88" {
                 description "1577.88 nm/189.996875 THz 3.125GHz spacing";
               }
               enum "1577.86" {
                 description "1577.86 nm/190.000000 THz 3.125/6.25/12.5/100GHz spacing";
               }
               enum "1577.83" {
                 description "1577.83 nm/190.003125 THz 3.125GHz spacing";
               }
               enum "1577.80" {
                 description "1577.80 nm/190.006250 THz 3.125/6.25GHz spacing";
               }
               enum "1577.78" {
                 description "1577.78 nm/190.009375 THz 3.125GHz spacing";
               }
               enum "1577.75" {
                 description "1577.75 nm/190.012500 THz 3.125/6.25/12.5GHz spacing";
               }
               enum "1577.73" {
                 description "1577.73 nm/190.015625 THz 3.125GHz spacing";
               }
               enum "1577.70" {
                 description "1577.70 nm/190.018750 THz 3.125/6.25GHz spacing";
               }
               enum "1577.67" {
                 description "1577.67 nm/190.021875 THz 3.125GHz spacing";
               }
               enum "1577.65" {
                 description "1577.65 nm/190.025000 THz 3.125/6.25/12.5/75GHz spacing";
               }
               enum "1577.62" {
                 description "1577.62 nm/190.028125 THz 3.125GHz spacing";
               }
               enum "1577.60" {
                 description "1577.60 nm/190.031250 THz 3.125/6.25GHz spacing";
               }
               enum "1577.57" {
                 description "1577.57 nm/190.034375 THz 3.125GHz spacing";
               }
               enum "1577.54" {
                 description "1577.54 nm/190.037500 THz 3.125/6.25/12.5GHz spacing";
               }
               enum "1577.52" {
                 description "1577.52 nm/190.040625 THz 3.125GHz spacing";
               }
               enum "1577.49" {
                 description "1577.49 nm/190.043750 THz 3.125/6.25GHz spacing";
               }
               enum "1577.47" {
                 description "1577.47 nm/190.046875 THz 3.125GHz spacing";
               }
               enum "1577.44" {
                 description "1577.44 nm/190.050000 THz 3.125/6.25/12.5/50GHz spacing";
               }
               enum "1577.41" {
                 description "1577.41 nm/190.053125 THz 3.125GHz spacing";
               }
               enum "1577.39" {
                 description "1577.39 nm/190.056250 THz 3.125/6.25GHz spacing";
               }
               enum "1577.36" {
                 description "1577.36 nm/190.059375 THz 3.125GHz spacing";
               }
               enum "1577.34" {
                 description "1577.34 nm/190.062500 THz 3.125/6.25/12.5GHz spacing";
               }
               enum "1577.31" {
                 description "1577.31 nm/190.065625 THz 3.125GHz spacing";
               }
               enum "1577.28" {
                 description "1577.28 nm/190.068750 THz 3.125/6.25GHz spacing";
               }
               enum "1577.26" {
                 description "1577.26 nm/190.071875 THz 3.125GHz spacing";
               }
               enum "1577.23" {
                 description "1577.23 nm/190.075000 THz 3.125/6.25/12.5GHz spacing";
               }
               enum "1577.21" {
                 description "1577.21 nm/190.078125 THz 3.125GHz spacing";
               }
               enum "1577.18" {
                 description "1577.18 nm/190.081250 THz 3.125/6.25GHz spacing";
               }
               enum "1577.15" {
                 description "1577.15 nm/190.084375 THz 3.125GHz spacing";
               }
               enum "1577.13" {
                 description "1577.13 nm/190.087500 THz 3.125/6.25/12.5GHz spacing";
               }
               enum "1577.10" {
                 description "1577.10 nm/190.090625 THz 3.125GHz spacing";
               }
               enum "1577.08" {
                 description "1577.08 nm/190.093750 THz 3.125/6.25GHz spacing";
               }
               enum "1577.05" {
                 description "1577.05 nm/190.096875 THz 3.125GHz spacing";
               }
               enum "1577.03" {
                 description "1577.03 nm/190.100000 THz 3.125/6.25/12.5/100GHz spacing";
               }
               enum "1577.00" {
                 description "1577.00 nm/190.103125 THz 3.125GHz spacing";
               }
               enum "1576.97" {
                 description "1576.97 nm/190.106250 THz 3.125/6.25GHz spacing";
               }
               enum "1576.95" {
                 description "1576.95 nm/190.109375 THz 3.125GHz spacing";
               }
               enum "1576.92" {
                 description "1576.92 nm/190.112500 THz 3.125/6.25/12.5GHz spacing";
               }
               enum "1576.90" {
                 description "1576.90 nm/190.115625 THz 3.125GHz spacing";
               }
               enum "1576.87" {
                 description "1576.87 nm/190.118750 THz 3.125/6.25GHz spacing";
               }
               enum "1576.84" {
                 description "1576.84 nm/190.121875 THz 3.125GHz spacing";
               }
               enum "1576.82" {
                 description "1576.82 nm/190.125000 THz 3.125/6.25/12.5GHz spacing";
               }
               enum "1576.79" {
                 description "1576.79 nm/190.128125 THz 3.125GHz spacing";
               }
               enum "1576.77" {
                 description "1576.77 nm/190.131250 THz 3.125/6.25GHz spacing";
               }
               enum "1576.74" {
                 description "1576.74 nm/190.134375 THz 3.125GHz spacing";
               }
               enum "1576.71" {
                 description "1576.71 nm/190.137500 THz 3.125/6.25/12.5GHz spacing";
               }
               enum "1576.69" {
                 description "1576.69 nm/190.140625 THz 3.125GHz spacing";
               }
               enum "1576.66" {
                 description "1576.66 nm/190.143750 THz 3.125/6.25GHz spacing";
               }
               enum "1576.64" {
                 description "1576.64 nm/190.146875 THz 3.125GHz spacing";
               }
               enum "1576.61" {
                 description "1576.61 nm/190.150000 THz 3.125/6.25/12.5/50GHz spacing";
               }
               enum "1576.58" {
                 description "1576.58 nm/190.153125 THz 3.125GHz spacing";
               }
               enum "1576.56" {
                 description "1576.56 nm/190.156250 THz 3.125/6.25GHz spacing";
               }
               enum "1576.53" {
                 description "1576.53 nm/190.159375 THz 3.125GHz spacing";
               }
               enum "1576.51" {
                 description "1576.51 nm/190.162500 THz 3.125/6.25/12.5GHz spacing";
               }
               enum "1576.48" {
                 description "1576.48 nm/190.165625 THz 3.125GHz spacing";
               }
               enum "1576.45" {
                 description "1576.45 nm/190.168750 THz 3.125/6.25GHz spacing";
               }
               enum "1576.43" {
                 description "1576.43 nm/190.171875 THz 3.125GHz spacing";
               }
               enum "1576.40" {
                 description "1576.40 nm/190.175000 THz 3.125/6.25/12.5/75GHz spacing";
               }
               enum "1576.38" {
                 description "1576.38 nm/190.178125 THz 3.125GHz spacing";
               }
               enum "1576.35" {
                 description "1576.35 nm/190.181250 THz 3.125/6.25GHz spacing";
               }
               enum "1576.33" {
                 description "1576.33 nm/190.184375 THz 3.125GHz spacing";
               }
               enum "1576.30" {
                 description "1576.30 nm/190.187500 THz 3.125/6.25/12.5GHz spacing";
               }
               enum "1576.27" {
                 description "1576.27 nm/190.190625 THz 3.125GHz spacing";
               }
               enum "1576.25" {
                 description "1576.25 nm/190.193750 THz 3.125/6.25GHz spacing";
               }
               enum "1576.22" {
                 description "1576.22 nm/190.196875 THz 3.125GHz spacing";
               }
               enum "1576.20" {
                 description "1576.20 nm/190.200000 THz 3.125/6.25/12.5/50/75/100GHz spacing";
               }
               enum "1576.17" {
                 description "1576.17 nm/190.203125 THz 3.125GHz spacing";
               }
               enum "1576.14" {
                 description "1576.14 nm/190.206250 THz 3.125/6.25GHz spacing";
               }
               enum "1576.12" {
                 description "1576.12 nm/190.209375 THz 3.125GHz spacing";
               }
               enum "1576.09" {
                 description "1576.09 nm/190.212500 THz 3.125/6.25/12.5GHz spacing";
               }
               enum "1576.07" {
                 description "1576.07 nm/190.215625 THz 3.125GHz spacing";
               }
               enum "1576.04" {
                 description "1576.04 nm/190.218750 THz 3.125/6.25GHz spacing";
               }
               enum "1576.01" {
                 description "1576.01 nm/190.221875 THz 3.125GHz spacing";
               }
               enum "1575.99" {
                 description "1575.99 nm/190.225000 THz 3.125/6.25/12.5GHz spacing";
               }
               enum "1575.96" {
                 description "1575.96 nm/190.228125 THz 3.125GHz spacing";
               }
               enum "1575.94" {
                 description "1575.94 nm/190.231250 THz 3.125/6.25GHz spacing";
               }
               enum "1575.91" {
                 description "1575.91 nm/190.234375 THz 3.125GHz spacing";
               }
               enum "1575.89" {
                 description "1575.89 nm/190.237500 THz 3.125/6.25/12.5GHz spacing";
               }
               enum "1575.86" {
                 description "1575.86 nm/190.240625 THz 3.125GHz spacing";
               }
               enum "1575.83" {
                 description "1575.83 nm/190.243750 THz 3.125/6.25GHz spacing";
               }
               enum "1575.81" {
                 description "1575.81 nm/190.246875 THz 3.125GHz spacing";
               }
               enum "1575.78" {
                 description "1575.78 nm/190.250000 THz 3.125/6.25/12.5/50/75GHz spacing";
               }
               enum "1575.76" {
                 description "1575.76 nm/190.253125 THz 3.125GHz spacing";
               }
               enum "1575.73" {
                 description "1575.73 nm/190.256250 THz 3.125/6.25GHz spacing";
               }
               enum "1575.70" {
                 description "1575.70 nm/190.259375 THz 3.125GHz spacing";
               }
               enum "1575.68" {
                 description "1575.68 nm/190.262500 THz 3.125/6.25/12.5GHz spacing";
               }
               enum "1575.65" {
                 description "1575.65 nm/190.265625 THz 3.125GHz spacing";
               }
               enum "1575.63" {
                 description "1575.63 nm/190.268750 THz 3.125/6.25GHz spacing";
               }
               enum "1575.60" {
                 description "1575.60 nm/190.271875 THz 3.125GHz spacing";
               }
               enum "1575.57" {
                 description "1575.57 nm/190.275000 THz 3.125/6.25/12.5GHz spacing";
               }
               enum "1575.55" {
                 description "1575.55 nm/190.278125 THz 3.125GHz spacing";
               }
               enum "1575.52" {
                 description "1575.52 nm/190.281250 THz 3.125/6.25GHz spacing";
               }
               enum "1575.50" {
                 description "1575.50 nm/190.284375 THz 3.125GHz spacing";
               }
               enum "1575.47" {
                 description "1575.47 nm/190.287500 THz 3.125/6.25/12.5GHz spacing";
               }
               enum "1575.45" {
                 description "1575.45 nm/190.290625 THz 3.125GHz spacing";
               }
               enum "1575.42" {
                 description "1575.42 nm/190.293750 THz 3.125/6.25GHz spacing";
               }
               enum "1575.39" {
                 description "1575.39 nm/190.296875 THz 3.125GHz spacing";
               }
               enum "1575.37" {
                 description "1575.37 nm/190.300000 THz 3.125/6.25/12.5/100GHz spacing";
               }
               enum "1575.34" {
                 description "1575.34 nm/190.303125 THz 3.125GHz spacing";
               }
               enum "1575.32" {
                 description "1575.32 nm/190.306250 THz 3.125/6.25GHz spacing";
               }
               enum "1575.29" {
                 description "1575.29 nm/190.309375 THz 3.125GHz spacing";
               }
               enum "1575.26" {
                 description "1575.26 nm/190.312500 THz 3.125/6.25/12.5GHz spacing";
               }
               enum "1575.24" {
                 description "1575.24 nm/190.315625 THz 3.125GHz spacing";
               }
               enum "1575.21" {
                 description "1575.21 nm/190.318750 THz 3.125/6.25GHz spacing";
               }
               enum "1575.19" {
                 description "1575.19 nm/190.321875 THz 3.125GHz spacing";
               }
               enum "1575.16" {
                 description "1575.16 nm/190.325000 THz 3.125/6.25/12.5/75GHz spacing";
               }
               enum "1575.13" {
                 description "1575.13 nm/190.328125 THz 3.125GHz spacing";
               }
               enum "1575.11" {
                 description "1575.11 nm/190.331250 THz 3.125/6.25GHz spacing";
               }
               enum "1575.08" {
                 description "1575.08 nm/190.334375 THz 3.125GHz spacing";
               }
               enum "1575.06" {
                 description "1575.06 nm/190.337500 THz 3.125/6.25/12.5GHz spacing";
               }
               enum "1575.03" {
                 description "1575.03 nm/190.340625 THz 3.125GHz spacing";
               }
               enum "1575.01" {
                 description "1575.01 nm/190.343750 THz 3.125/6.25GHz spacing";
               }
               enum "1574.98" {
                 description "1574.98 nm/190.346875 THz 3.125GHz spacing";
               }
               enum "1574.95" {
                 description "1574.95 nm/190.350000 THz 3.125/6.25/12.5/50GHz spacing";
               }
               enum "1574.93" {
                 description "1574.93 nm/190.353125 THz 3.125GHz spacing";
               }
               enum "1574.90" {
                 description "1574.90 nm/190.356250 THz 3.125/6.25GHz spacing";
               }
               enum "1574.88" {
                 description "1574.88 nm/190.359375 THz 3.125GHz spacing";
               }
               enum "1574.85" {
                 description "1574.85 nm/190.362500 THz 3.125/6.25/12.5GHz spacing";
               }
               enum "1574.82" {
                 description "1574.82 nm/190.365625 THz 3.125GHz spacing";
               }
               enum "1574.80" {
                 description "1574.80 nm/190.368750 THz 3.125/6.25GHz spacing";
               }
               enum "1574.77" {
                 description "1574.77 nm/190.371875 THz 3.125GHz spacing";
               }
               enum "1574.75" {
                 description "1574.75 nm/190.375000 THz 3.125/6.25/12.5GHz spacing";
               }
               enum "1574.72" {
                 description "1574.72 nm/190.378125 THz 3.125GHz spacing";
               }
               enum "1574.70" {
                 description "1574.70 nm/190.381250 THz 3.125/6.25GHz spacing";
               }
               enum "1574.67" {
                 description "1574.67 nm/190.384375 THz 3.125GHz spacing";
               }
               enum "1574.64" {
                 description "1574.64 nm/190.387500 THz 3.125/6.25/12.5GHz spacing";
               }
               enum "1574.62" {
                 description "1574.62 nm/190.390625 THz 3.125GHz spacing";
               }
               enum "1574.59" {
                 description "1574.59 nm/190.393750 THz 3.125/6.25GHz spacing";
               }
               enum "1574.57" {
                 description "1574.57 nm/190.396875 THz 3.125GHz spacing";
               }
               enum "1574.54" {
                 description "1574.54 nm/190.400000 THz 3.125/6.25/12.5/100GHz spacing";
               }
               enum "1574.51" {
                 description "1574.51 nm/190.403125 THz 3.125GHz spacing";
               }
               enum "1574.49" {
                 description "1574.49 nm/190.406250 THz 3.125/6.25GHz spacing";
               }
               enum "1574.46" {
                 description "1574.46 nm/190.409375 THz 3.125GHz spacing";
               }
               enum "1574.44" {
                 description "1574.44 nm/190.412500 THz 3.125/6.25/12.5GHz spacing";
               }
               enum "1574.41" {
                 description "1574.41 nm/190.415625 THz 3.125GHz spacing";
               }
               enum "1574.39" {
                 description "1574.39 nm/190.418750 THz 3.125/6.25GHz spacing";
               }
               enum "1574.36" {
                 description "1574.36 nm/190.421875 THz 3.125GHz spacing";
               }
               enum "1574.33" {
                 description "1574.33 nm/190.425000 THz 3.125/6.25/12.5GHz spacing";
               }
               enum "1574.31" {
                 description "1574.31 nm/190.428125 THz 3.125GHz spacing";
               }
               enum "1574.28" {
                 description "1574.28 nm/190.431250 THz 3.125/6.25GHz spacing";
               }
               enum "1574.26" {
                 description "1574.26 nm/190.434375 THz 3.125GHz spacing";
               }
               enum "1574.23" {
                 description "1574.23 nm/190.437500 THz 3.125/6.25/12.5GHz spacing";
               }
               enum "1574.20" {
                 description "1574.20 nm/190.440625 THz 3.125GHz spacing";
               }
               enum "1574.18" {
                 description "1574.18 nm/190.443750 THz 3.125/6.25GHz spacing";
               }
               enum "1574.15" {
                 description "1574.15 nm/190.446875 THz 3.125GHz spacing";
               }
               enum "1574.13" {
                 description "1574.13 nm/190.450000 THz 3.125/6.25/12.5/50GHz spacing";
               }
               enum "1574.10" {
                 description "1574.10 nm/190.453125 THz 3.125GHz spacing";
               }
               enum "1574.08" {
                 description "1574.08 nm/190.456250 THz 3.125/6.25GHz spacing";
               }
               enum "1574.05" {
                 description "1574.05 nm/190.459375 THz 3.125GHz spacing";
               }
               enum "1574.02" {
                 description "1574.02 nm/190.462500 THz 3.125/6.25/12.5GHz spacing";
               }
               enum "1574.00" {
                 description "1574.00 nm/190.465625 THz 3.125GHz spacing";
               }
               enum "1573.97" {
                 description "1573.97 nm/190.468750 THz 3.125/6.25GHz spacing";
               }
               enum "1573.95" {
                 description "1573.95 nm/190.471875 THz 3.125GHz spacing";
               }
               enum "1573.92" {
                 description "1573.92 nm/190.475000 THz 3.125/6.25/12.5/75GHz spacing";
               }
               enum "1573.89" {
                 description "1573.89 nm/190.478125 THz 3.125GHz spacing";
               }
               enum "1573.87" {
                 description "1573.87 nm/190.481250 THz 3.125/6.25GHz spacing";
               }
               enum "1573.84" {
                 description "1573.84 nm/190.484375 THz 3.125GHz spacing";
               }
               enum "1573.82" {
                 description "1573.82 nm/190.487500 THz 3.125/6.25/12.5GHz spacing";
               }
               enum "1573.79" {
                 description "1573.79 nm/190.490625 THz 3.125GHz spacing";
               }
               enum "1573.77" {
                 description "1573.77 nm/190.493750 THz 3.125/6.25GHz spacing";
               }
               enum "1573.74" {
                 description "1573.74 nm/190.496875 THz 3.125GHz spacing";
               }
               enum "1573.71" {
                 description "1573.71 nm/190.500000 THz 3.125/6.25/12.5/50/75/100GHz spacing";
               }
               enum "1573.69" {
                 description "1573.69 nm/190.503125 THz 3.125GHz spacing";
               }
               enum "1573.66" {
                 description "1573.66 nm/190.506250 THz 3.125/6.25GHz spacing";
               }
               enum "1573.64" {
                 description "1573.64 nm/190.509375 THz 3.125GHz spacing";
               }
               enum "1573.61" {
                 description "1573.61 nm/190.512500 THz 3.125/6.25/12.5GHz spacing";
               }
               enum "1573.58" {
                 description "1573.58 nm/190.515625 THz 3.125GHz spacing";
               }
               enum "1573.56" {
                 description "1573.56 nm/190.518750 THz 3.125/6.25GHz spacing";
               }
               enum "1573.53" {
                 description "1573.53 nm/190.521875 THz 3.125GHz spacing";
               }
               enum "1573.51" {
                 description "1573.51 nm/190.525000 THz 3.125/6.25/12.5GHz spacing";
               }
               enum "1573.48" {
                 description "1573.48 nm/190.528125 THz 3.125GHz spacing";
               }
               enum "1573.46" {
                 description "1573.46 nm/190.531250 THz 3.125/6.25GHz spacing";
               }
               enum "1573.43" {
                 description "1573.43 nm/190.534375 THz 3.125GHz spacing";
               }
               enum "1573.40" {
                 description "1573.40 nm/190.537500 THz 3.125/6.25/12.5GHz spacing";
               }
               enum "1573.38" {
                 description "1573.38 nm/190.540625 THz 3.125GHz spacing";
               }
               enum "1573.35" {
                 description "1573.35 nm/190.543750 THz 3.125/6.25GHz spacing";
               }
               enum "1573.33" {
                 description "1573.33 nm/190.546875 THz 3.125GHz spacing";
               }
               enum "1573.30" {
                 description "1573.30 nm/190.550000 THz 3.125/6.25/12.5/50/75GHz spacing";
               }
               enum "1573.27" {
                 description "1573.27 nm/190.553125 THz 3.125GHz spacing";
               }
               enum "1573.25" {
                 description "1573.25 nm/190.556250 THz 3.125/6.25GHz spacing";
               }
               enum "1573.22" {
                 description "1573.22 nm/190.559375 THz 3.125GHz spacing";
               }
               enum "1573.20" {
                 description "1573.20 nm/190.562500 THz 3.125/6.25/12.5GHz spacing";
               }
               enum "1573.17" {
                 description "1573.17 nm/190.565625 THz 3.125GHz spacing";
               }
               enum "1573.15" {
                 description "1573.15 nm/190.568750 THz 3.125/6.25GHz spacing";
               }
               enum "1573.12" {
                 description "1573.12 nm/190.571875 THz 3.125GHz spacing";
               }
               enum "1573.09" {
                 description "1573.09 nm/190.575000 THz 3.125/6.25/12.5GHz spacing";
               }
               enum "1573.07" {
                 description "1573.07 nm/190.578125 THz 3.125GHz spacing";
               }
               enum "1573.04" {
                 description "1573.04 nm/190.581250 THz 3.125/6.25GHz spacing";
               }
               enum "1573.02" {
                 description "1573.02 nm/190.584375 THz 3.125GHz spacing";
               }
               enum "1572.99" {
                 description "1572.99 nm/190.587500 THz 3.125/6.25/12.5GHz spacing";
               }
               enum "1572.97" {
                 description "1572.97 nm/190.590625 THz 3.125GHz spacing";
               }
               enum "1572.94" {
                 description "1572.94 nm/190.593750 THz 3.125/6.25GHz spacing";
               }
               enum "1572.91" {
                 description "1572.91 nm/190.596875 THz 3.125GHz spacing";
               }
               enum "1572.89" {
                 description "1572.89 nm/190.600000 THz 3.125/6.25/12.5/100GHz spacing";
               }
               enum "1572.86" {
                 description "1572.86 nm/190.603125 THz 3.125GHz spacing";
               }
               enum "1572.84" {
                 description "1572.84 nm/190.606250 THz 3.125/6.25GHz spacing";
               }
               enum "1572.81" {
                 description "1572.81 nm/190.609375 THz 3.125GHz spacing";
               }
               enum "1572.78" {
                 description "1572.78 nm/190.612500 THz 3.125/6.25/12.5GHz spacing";
               }
               enum "1572.76" {
                 description "1572.76 nm/190.615625 THz 3.125GHz spacing";
               }
               enum "1572.73" {
                 description "1572.73 nm/190.618750 THz 3.125/6.25GHz spacing";
               }
               enum "1572.71" {
                 description "1572.71 nm/190.621875 THz 3.125GHz spacing";
               }
               enum "1572.68" {
                 description "1572.68 nm/190.625000 THz 3.125/6.25/12.5/75GHz spacing";
               }
               enum "1572.66" {
                 description "1572.66 nm/190.628125 THz 3.125GHz spacing";
               }
               enum "1572.63" {
                 description "1572.63 nm/190.631250 THz 3.125/6.25GHz spacing";
               }
               enum "1572.60" {
                 description "1572.60 nm/190.634375 THz 3.125GHz spacing";
               }
               enum "1572.58" {
                 description "1572.58 nm/190.637500 THz 3.125/6.25/12.5GHz spacing";
               }
               enum "1572.55" {
                 description "1572.55 nm/190.640625 THz 3.125GHz spacing";
               }
               enum "1572.53" {
                 description "1572.53 nm/190.643750 THz 3.125/6.25GHz spacing";
               }
               enum "1572.50" {
                 description "1572.50 nm/190.646875 THz 3.125GHz spacing";
               }
               enum "1572.48" {
                 description "1572.48 nm/190.650000 THz 3.125/6.25/12.5/50GHz spacing";
               }
               enum "1572.45" {
                 description "1572.45 nm/190.653125 THz 3.125GHz spacing";
               }
               enum "1572.42" {
                 description "1572.42 nm/190.656250 THz 3.125/6.25GHz spacing";
               }
               enum "1572.40" {
                 description "1572.40 nm/190.659375 THz 3.125GHz spacing";
               }
               enum "1572.37" {
                 description "1572.37 nm/190.662500 THz 3.125/6.25/12.5GHz spacing";
               }
               enum "1572.35" {
                 description "1572.35 nm/190.665625 THz 3.125GHz spacing";
               }
               enum "1572.32" {
                 description "1572.32 nm/190.668750 THz 3.125/6.25GHz spacing";
               }
               enum "1572.30" {
                 description "1572.30 nm/190.671875 THz 3.125GHz spacing";
               }
               enum "1572.27" {
                 description "1572.27 nm/190.675000 THz 3.125/6.25/12.5GHz spacing";
               }
               enum "1572.24" {
                 description "1572.24 nm/190.678125 THz 3.125GHz spacing";
               }
               enum "1572.22" {
                 description "1572.22 nm/190.681250 THz 3.125/6.25GHz spacing";
               }
               enum "1572.19" {
                 description "1572.19 nm/190.684375 THz 3.125GHz spacing";
               }
               enum "1572.17" {
                 description "1572.17 nm/190.687500 THz 3.125/6.25/12.5GHz spacing";
               }
               enum "1572.14" {
                 description "1572.14 nm/190.690625 THz 3.125GHz spacing";
               }
               enum "1572.11" {
                 description "1572.11 nm/190.693750 THz 3.125/6.25GHz spacing";
               }
               enum "1572.09" {
                 description "1572.09 nm/190.696875 THz 3.125GHz spacing";
               }
               enum "1572.06" {
                 description "1572.06 nm/190.700000 THz 3.125/6.25/12.5/100GHz spacing";
               }
               enum "1572.04" {
                 description "1572.04 nm/190.703125 THz 3.125GHz spacing";
               }
               enum "1572.01" {
                 description "1572.01 nm/190.706250 THz 3.125/6.25GHz spacing";
               }
               enum "1571.99" {
                 description "1571.99 nm/190.709375 THz 3.125GHz spacing";
               }
               enum "1571.96" {
                 description "1571.96 nm/190.712500 THz 3.125/6.25/12.5GHz spacing";
               }
               enum "1571.93" {
                 description "1571.93 nm/190.715625 THz 3.125GHz spacing";
               }
               enum "1571.91" {
                 description "1571.91 nm/190.718750 THz 3.125/6.25GHz spacing";
               }
               enum "1571.88" {
                 description "1571.88 nm/190.721875 THz 3.125GHz spacing";
               }
               enum "1571.86" {
                 description "1571.86 nm/190.725000 THz 3.125/6.25/12.5GHz spacing";
               }
               enum "1571.83" {
                 description "1571.83 nm/190.728125 THz 3.125GHz spacing";
               }
               enum "1571.81" {
                 description "1571.81 nm/190.731250 THz 3.125/6.25GHz spacing";
               }
               enum "1571.78" {
                 description "1571.78 nm/190.734375 THz 3.125GHz spacing";
               }
               enum "1571.75" {
                 description "1571.75 nm/190.737500 THz 3.125/6.25/12.5GHz spacing";
               }
               enum "1571.73" {
                 description "1571.73 nm/190.740625 THz 3.125GHz spacing";
               }
               enum "1571.70" {
                 description "1571.70 nm/190.743750 THz 3.125/6.25GHz spacing";
               }
               enum "1571.68" {
                 description "1571.68 nm/190.746875 THz 3.125GHz spacing";
               }
               enum "1571.65" {
                 description "1571.65 nm/190.750000 THz 3.125/6.25/12.5/50GHz spacing";
               }
               enum "1571.63" {
                 description "1571.63 nm/190.753125 THz 3.125GHz spacing";
               }
               enum "1571.60" {
                 description "1571.60 nm/190.756250 THz 3.125/6.25GHz spacing";
               }
               enum "1571.57" {
                 description "1571.57 nm/190.759375 THz 3.125GHz spacing";
               }
               enum "1571.55" {
                 description "1571.55 nm/190.762500 THz 3.125/6.25/12.5GHz spacing";
               }
               enum "1571.52" {
                 description "1571.52 nm/190.765625 THz 3.125GHz spacing";
               }
               enum "1571.50" {
                 description "1571.50 nm/190.768750 THz 3.125/6.25GHz spacing";
               }
               enum "1571.47" {
                 description "1571.47 nm/190.771875 THz 3.125GHz spacing";
               }
               enum "1571.45" {
                 description "1571.45 nm/190.775000 THz 3.125/6.25/12.5/75GHz spacing";
               }
               enum "1571.42" {
                 description "1571.42 nm/190.778125 THz 3.125GHz spacing";
               }
               enum "1571.39" {
                 description "1571.39 nm/190.781250 THz 3.125/6.25GHz spacing";
               }
               enum "1571.37" {
                 description "1571.37 nm/190.784375 THz 3.125GHz spacing";
               }
               enum "1571.34" {
                 description "1571.34 nm/190.787500 THz 3.125/6.25/12.5GHz spacing";
               }
               enum "1571.32" {
                 description "1571.32 nm/190.790625 THz 3.125GHz spacing";
               }
               enum "1571.29" {
                 description "1571.29 nm/190.793750 THz 3.125/6.25GHz spacing";
               }
               enum "1571.27" {
                 description "1571.27 nm/190.796875 THz 3.125GHz spacing";
               }
               enum "1571.24" {
                 description "1571.24 nm/190.800000 THz 3.125/6.25/12.5/50/75/100GHz spacing";
               }
               enum "1571.21" {
                 description "1571.21 nm/190.803125 THz 3.125GHz spacing";
               }
               enum "1571.19" {
                 description "1571.19 nm/190.806250 THz 3.125/6.25GHz spacing";
               }
               enum "1571.16" {
                 description "1571.16 nm/190.809375 THz 3.125GHz spacing";
               }
               enum "1571.14" {
                 description "1571.14 nm/190.812500 THz 3.125/6.25/12.5GHz spacing";
               }
               enum "1571.11" {
                 description "1571.11 nm/190.815625 THz 3.125GHz spacing";
               }
               enum "1571.08" {
                 description "1571.08 nm/190.818750 THz 3.125/6.25GHz spacing";
               }
               enum "1571.06" {
                 description "1571.06 nm/190.821875 THz 3.125GHz spacing";
               }
               enum "1571.03" {
                 description "1571.03 nm/190.825000 THz 3.125/6.25/12.5GHz spacing";
               }
               enum "1571.01" {
                 description "1571.01 nm/190.828125 THz 3.125GHz spacing";
               }
               enum "1570.98" {
                 description "1570.98 nm/190.831250 THz 3.125/6.25GHz spacing";
               }
               enum "1570.96" {
                 description "1570.96 nm/190.834375 THz 3.125GHz spacing";
               }
               enum "1570.93" {
                 description "1570.93 nm/190.837500 THz 3.125/6.25/12.5GHz spacing";
               }
               enum "1570.90" {
                 description "1570.90 nm/190.840625 THz 3.125GHz spacing";
               }
               enum "1570.88" {
                 description "1570.88 nm/190.843750 THz 3.125/6.25GHz spacing";
               }
               enum "1570.85" {
                 description "1570.85 nm/190.846875 THz 3.125GHz spacing";
               }
               enum "1570.83" {
                 description "1570.83 nm/190.850000 THz 3.125/6.25/12.5/50/75GHz spacing";
               }
               enum "1570.80" {
                 description "1570.80 nm/190.853125 THz 3.125GHz spacing";
               }
               enum "1570.78" {
                 description "1570.78 nm/190.856250 THz 3.125/6.25GHz spacing";
               }
               enum "1570.75" {
                 description "1570.75 nm/190.859375 THz 3.125GHz spacing";
               }
               enum "1570.72" {
                 description "1570.72 nm/190.862500 THz 3.125/6.25/12.5GHz spacing";
               }
               enum "1570.70" {
                 description "1570.70 nm/190.865625 THz 3.125GHz spacing";
               }
               enum "1570.67" {
                 description "1570.67 nm/190.868750 THz 3.125/6.25GHz spacing";
               }
               enum "1570.65" {
                 description "1570.65 nm/190.871875 THz 3.125GHz spacing";
               }
               enum "1570.62" {
                 description "1570.62 nm/190.875000 THz 3.125/6.25/12.5GHz spacing";
               }
               enum "1570.60" {
                 description "1570.60 nm/190.878125 THz 3.125GHz spacing";
               }
               enum "1570.57" {
                 description "1570.57 nm/190.881250 THz 3.125/6.25GHz spacing";
               }
               enum "1570.54" {
                 description "1570.54 nm/190.884375 THz 3.125GHz spacing";
               }
               enum "1570.52" {
                 description "1570.52 nm/190.887500 THz 3.125/6.25/12.5GHz spacing";
               }
               enum "1570.49" {
                 description "1570.49 nm/190.890625 THz 3.125GHz spacing";
               }
               enum "1570.47" {
                 description "1570.47 nm/190.893750 THz 3.125/6.25GHz spacing";
               }
               enum "1570.44" {
                 description "1570.44 nm/190.896875 THz 3.125GHz spacing";
               }
               enum "1570.42" {
                 description "1570.42 nm/190.900000 THz 3.125/6.25/12.5/100GHz spacing";
               }
               enum "1570.39" {
                 description "1570.39 nm/190.903125 THz 3.125GHz spacing";
               }
               enum "1570.36" {
                 description "1570.36 nm/190.906250 THz 3.125/6.25GHz spacing";
               }
               enum "1570.34" {
                 description "1570.34 nm/190.909375 THz 3.125GHz spacing";
               }
               enum "1570.31" {
                 description "1570.31 nm/190.912500 THz 3.125/6.25/12.5GHz spacing";
               }
               enum "1570.29" {
                 description "1570.29 nm/190.915625 THz 3.125GHz spacing";
               }
               enum "1570.26" {
                 description "1570.26 nm/190.918750 THz 3.125/6.25GHz spacing";
               }
               enum "1570.24" {
                 description "1570.24 nm/190.921875 THz 3.125GHz spacing";
               }
               enum "1570.21" {
                 description "1570.21 nm/190.925000 THz 3.125/6.25/12.5/75GHz spacing";
               }
               enum "1570.18" {
                 description "1570.18 nm/190.928125 THz 3.125GHz spacing";
               }
               enum "1570.16" {
                 description "1570.16 nm/190.931250 THz 3.125/6.25GHz spacing";
               }
               enum "1570.13" {
                 description "1570.13 nm/190.934375 THz 3.125GHz spacing";
               }
               enum "1570.11" {
                 description "1570.11 nm/190.937500 THz 3.125/6.25/12.5GHz spacing";
               }
               enum "1570.08" {
                 description "1570.08 nm/190.940625 THz 3.125GHz spacing";
               }
               enum "1570.06" {
                 description "1570.06 nm/190.943750 THz 3.125/6.25GHz spacing";
               }
               enum "1570.03" {
                 description "1570.03 nm/190.946875 THz 3.125GHz spacing";
               }
               enum "1570.01" {
                 description "1570.01 nm/190.950000 THz 3.125/6.25/12.5/50GHz spacing";
               }
               enum "1569.98" {
                 description "1569.98 nm/190.953125 THz 3.125GHz spacing";
               }
               enum "1569.95" {
                 description "1569.95 nm/190.956250 THz 3.125/6.25GHz spacing";
               }
               enum "1569.93" {
                 description "1569.93 nm/190.959375 THz 3.125GHz spacing";
               }
               enum "1569.90" {
                 description "1569.90 nm/190.962500 THz 3.125/6.25/12.5GHz spacing";
               }
               enum "1569.88" {
                 description "1569.88 nm/190.965625 THz 3.125GHz spacing";
               }
               enum "1569.85" {
                 description "1569.85 nm/190.968750 THz 3.125/6.25GHz spacing";
               }
               enum "1569.83" {
                 description "1569.83 nm/190.971875 THz 3.125GHz spacing";
               }
               enum "1569.80" {
                 description "1569.80 nm/190.975000 THz 3.125/6.25/12.5GHz spacing";
               }
               enum "1569.77" {
                 description "1569.77 nm/190.978125 THz 3.125GHz spacing";
               }
               enum "1569.75" {
                 description "1569.75 nm/190.981250 THz 3.125/6.25GHz spacing";
               }
               enum "1569.72" {
                 description "1569.72 nm/190.984375 THz 3.125GHz spacing";
               }
               enum "1569.70" {
                 description "1569.70 nm/190.987500 THz 3.125/6.25/12.5GHz spacing";
               }
               enum "1569.67" {
                 description "1569.67 nm/190.990625 THz 3.125GHz spacing";
               }
               enum "1569.65" {
                 description "1569.65 nm/190.993750 THz 3.125/6.25GHz spacing";
               }
               enum "1569.62" {
                 description "1569.62 nm/190.996875 THz 3.125GHz spacing";
               }
               enum "1569.59" {
                 description "1569.59 nm/191.000000 THz 3.125/6.25/12.5/100GHz spacing";
               }
               enum "1568.77" {
                 description "1568.77 nm/191.1003 THz 50/100Ghz spacing";
               }
               enum "1568.36" {
                 description "1568.36 nm/191.150000 THz 3.125/6.25/12.5/50/75GHz spacing";
               }
               enum "1568.34" {
                 description "1568.34 nm/191.153125 THz 3.125GHz spacing";
               }
               enum "1568.31" {
                 description "1568.31 nm/191.156250 THz 3.125/6.25GHz spacing";
               }
               enum "1568.29" {
                 description "1568.29 nm/191.159375 THz 3.125GHz spacing";
               }
               enum "1568.26" {
                 description "1568.26 nm/191.162500 THz 3.125/6.25/12.5GHz spacing";
               }
               enum "1568.23" {
                 description "1568.23 nm/191.165625 THz 3.125GHz spacing";
               }
               enum "1568.21" {
                 description "1568.21 nm/191.168750 THz 3.125/6.25GHz spacing";
               }
               enum "1568.18" {
                 description "1568.18 nm/191.171875 THz 3.125GHz spacing";
               }
               enum "1568.16" {
                 description "1568.16 nm/191.175000 THz 3.125/6.25/12.5/75GHz spacing";
               }
               enum "1568.13" {
                 description "1568.13 nm/191.178125 THz 3.125GHz spacing";
               }
               enum "1568.11" {
                 description "1568.11 nm/191.181250 THz 3.125/6.25GHz spacing";
               }
               enum "1568.08" {
                 description "1568.08 nm/191.184375 THz 3.125GHz spacing";
               }
               enum "1568.05" {
                 description "1568.05 nm/191.187500 THz 3.125/6.25/12.5GHz spacing";
               }
               enum "1568.03" {
                 description "1568.03 nm/191.190625 THz 3.125GHz spacing";
               }
               enum "1568.00" {
                 description "1568.00 nm/191.193750 THz 3.125/6.25GHz spacing";
               }
               enum "1567.98" {
                 description "1567.98 nm/191.196875 THz 3.125GHz spacing";
               }
               enum "1567.95" {
                 description "1567.95 nm/191.200000 THz 3.125/6.25/12.5/100GHz spacing";
               }
               enum "1567.93" {
                 description "1567.93 nm/191.203125 THz 3.125GHz spacing";
               }
               enum "1567.90" {
                 description "1567.90 nm/191.206250 THz 3.125/6.25GHz spacing";
               }
               enum "1567.88" {
                 description "1567.88 nm/191.209375 THz 3.125GHz spacing";
               }
               enum "1567.85" {
                 description "1567.85 nm/191.212500 THz 3.125/6.25/12.5GHz spacing";
               }
               enum "1567.82" {
                 description "1567.82 nm/191.215625 THz 3.125GHz spacing";
               }
               enum "1567.80" {
                 description "1567.80 nm/191.218750 THz 3.125/6.25GHz spacing";
               }
               enum "1567.77" {
                 description "1567.77 nm/191.221875 THz 3.125GHz spacing";
               }
               enum "1567.75" {
                 description "1567.75 nm/191.225000 THz 3.125/6.25/12.5/75GHz spacing";
               }
               enum "1567.72" {
                 description "1567.72 nm/191.228125 THz 3.125GHz spacing";
               }
               enum "1567.70" {
                 description "1567.70 nm/191.231250 THz 3.125/6.25GHz spacing";
               }
               enum "1567.67" {
                 description "1567.67 nm/191.234375 THz 3.125GHz spacing";
               }
               enum "1567.64" {
                 description "1567.64 nm/191.237500 THz 3.125/6.25/12.5GHz spacing";
               }
               enum "1567.62" {
                 description "1567.62 nm/191.240625 THz 3.125GHz spacing";
               }
               enum "1567.59" {
                 description "1567.59 nm/191.243750 THz 3.125/6.25GHz spacing";
               }
               enum "1567.57" {
                 description "1567.57 nm/191.246875 THz 3.125GHz spacing";
               }
               enum "1567.54" {
                 description "1567.54 nm/191.250000 THz 3.125/6.25/12.5/50/75GHz spacing";
               }
               enum "1567.52" {
                 description "1567.52 nm/191.253125 THz 3.125GHz spacing";
               }
               enum "1567.49" {
                 description "1567.49 nm/191.256250 THz 3.125/6.25GHz spacing";
               }
               enum "1567.47" {
                 description "1567.47 nm/191.259375 THz 3.125GHz spacing";
               }
               enum "1567.44" {
                 description "1567.44 nm/191.262500 THz 3.125/6.25/12.5GHz spacing";
               }
               enum "1567.41" {
                 description "1567.41 nm/191.265625 THz 3.125GHz spacing";
               }
               enum "1567.39" {
                 description "1567.39 nm/191.268750 THz 3.125/6.25GHz spacing";
               }
               enum "1567.36" {
                 description "1567.36 nm/191.271875 THz 3.125GHz spacing";
               }
               enum "1567.34" {
                 description "1567.34 nm/191.275000 THz 3.125/6.25/12.5GHz spacing";
               }
               enum "1567.31" {
                 description "1567.31 nm/191.278125 THz 3.125GHz spacing";
               }
               enum "1567.29" {
                 description "1567.29 nm/191.281250 THz 3.125/6.25GHz spacing";
               }
               enum "1567.26" {
                 description "1567.26 nm/191.284375 THz 3.125GHz spacing";
               }
               enum "1567.23" {
                 description "1567.23 nm/191.287500 THz 3.125/6.25/12.5GHz spacing";
               }
               enum "1567.21" {
                 description "1567.21 nm/191.290625 THz 3.125GHz spacing";
               }
               enum "1567.18" {
                 description "1567.18 nm/191.293750 THz 3.125/6.25GHz spacing";
               }
               enum "1567.16" {
                 description "1567.16 nm/191.296875 THz 3.125GHz spacing";
               }
               enum "1567.13" {
                 description "1567.13 nm/191.300000 THz 3.125/6.25/12.5/100GHz spacing";
               }
               enum "1567.11" {
                 description "1567.11 nm/191.303125 THz 3.125GHz spacing";
               }
               enum "1567.08" {
                 description "1567.08 nm/191.306250 THz 3.125/6.25GHz spacing";
               }
               enum "1567.06" {
                 description "1567.06 nm/191.309375 THz 3.125GHz spacing";
               }
               enum "1567.03" {
                 description "1567.03 nm/191.312500 THz 3.125/6.25/12.5GHz spacing";
               }
               enum "1567.00" {
                 description "1567.00 nm/191.315625 THz 3.125GHz spacing";
               }
               enum "1566.98" {
                 description "1566.98 nm/191.318750 THz 3.125/6.25GHz spacing";
               }
               enum "1566.95" {
                 description "1566.95 nm/191.321875 THz 3.125GHz spacing";
               }
               enum "1566.93" {
                 description "1566.93 nm/191.325000 THz 3.125/6.25/12.5/75GHz spacing";
               }
               enum "1566.90" {
                 description "1566.90 nm/191.328125 THz 3.125GHz spacing";
               }
               enum "1566.88" {
                 description "1566.88 nm/191.331250 THz 3.125/6.25GHz spacing";
               }
               enum "1566.85" {
                 description "1566.85 nm/191.334375 THz 3.125GHz spacing";
               }
               enum "1566.83" {
                 description "1566.83 nm/191.337500 THz 3.125/6.25/12.5GHz spacing";
               }
               enum "1566.80" {
                 description "1566.80 nm/191.340625 THz 3.125GHz spacing";
               }
               enum "1566.77" {
                 description "1566.77 nm/191.343750 THz 3.125/6.25GHz spacing";
               }
               enum "1566.75" {
                 description "1566.75 nm/191.346875 THz 3.125GHz spacing";
               }
               enum "1566.72" {
                 description "1566.72 nm/191.350000 THz 3.125/6.25/12.5/50GHz spacing";
               }
               enum "1566.70" {
                 description "1566.70 nm/191.353125 THz 3.125GHz spacing";
               }
               enum "1566.67" {
                 description "1566.67 nm/191.356250 THz 3.125/6.25GHz spacing";
               }
               enum "1566.65" {
                 description "1566.65 nm/191.359375 THz 3.125GHz spacing";
               }
               enum "1566.62" {
                 description "1566.62 nm/191.362500 THz 3.125/6.25/12.5GHz spacing";
               }
               enum "1566.60" {
                 description "1566.60 nm/191.365625 THz 3.125GHz spacing";
               }
               enum "1566.57" {
                 description "1566.57 nm/191.368750 THz 3.125/6.25GHz spacing";
               }
               enum "1566.54" {
                 description "1566.54 nm/191.371875 THz 3.125GHz spacing";
               }
               enum "1566.52" {
                 description "1566.52 nm/191.375000 THz 3.125/6.25/12.5GHz spacing";
               }
               enum "1566.49" {
                 description "1566.49 nm/191.378125 THz 3.125GHz spacing";
               }
               enum "1566.47" {
                 description "1566.47 nm/191.381250 THz 3.125/6.25GHz spacing";
               }
               enum "1566.44" {
                 description "1566.44 nm/191.384375 THz 3.125GHz spacing";
               }
               enum "1566.42" {
                 description "1566.42 nm/191.387500 THz 3.125/6.25/12.5GHz spacing";
               }
               enum "1566.39" {
                 description "1566.39 nm/191.390625 THz 3.125GHz spacing";
               }
               enum "1566.36" {
                 description "1566.36 nm/191.393750 THz 3.125/6.25GHz spacing";
               }
               enum "1566.34" {
                 description "1566.34 nm/191.396875 THz 3.125GHz spacing";
               }
               enum "1566.31" {
                 description "1566.31 nm/191.400000 THz 3.125/6.25/12.5/50/75/100GHz spacing";
               }
               enum "1566.29" {
                 description "1566.29 nm/191.403125 THz 3.125GHz spacing";
               }
               enum "1566.26" {
                 description "1566.26 nm/191.406250 THz 3.125/6.25GHz spacing";
               }
               enum "1566.24" {
                 description "1566.24 nm/191.409375 THz 3.125GHz spacing";
               }
               enum "1566.21" {
                 description "1566.21 nm/191.412500 THz 3.125/6.25/12.5GHz spacing";
               }
               enum "1566.19" {
                 description "1566.19 nm/191.415625 THz 3.125GHz spacing";
               }
               enum "1566.16" {
                 description "1566.16 nm/191.418750 THz 3.125/6.25GHz spacing";
               }
               enum "1566.13" {
                 description "1566.13 nm/191.421875 THz 3.125GHz spacing";
               }
               enum "1566.11" {
                 description "1566.11 nm/191.425000 THz 3.125/6.25/12.5GHz spacing";
               }
               enum "1566.08" {
                 description "1566.08 nm/191.428125 THz 3.125GHz spacing";
               }
               enum "1566.06" {
                 description "1566.06 nm/191.431250 THz 3.125/6.25GHz spacing";
               }
               enum "1566.03" {
                 description "1566.03 nm/191.434375 THz 3.125GHz spacing";
               }
               enum "1566.01" {
                 description "1566.01 nm/191.437500 THz 3.125/6.25/12.5GHz spacing";
               }
               enum "1565.98" {
                 description "1565.98 nm/191.440625 THz 3.125GHz spacing";
               }
               enum "1565.96" {
                 description "1565.96 nm/191.443750 THz 3.125/6.25GHz spacing";
               }
               enum "1565.93" {
                 description "1565.93 nm/191.446875 THz 3.125GHz spacing";
               }
               enum "1565.90" {
                 description "1565.90 nm/191.450000 THz 3.125/6.25/12.5/50GHz spacing";
               }
               enum "1565.88" {
                 description "1565.88 nm/191.453125 THz 3.125GHz spacing";
               }
               enum "1565.85" {
                 description "1565.85 nm/191.456250 THz 3.125/6.25GHz spacing";
               }
               enum "1565.83" {
                 description "1565.83 nm/191.459375 THz 3.125GHz spacing";
               }
               enum "1565.80" {
                 description "1565.80 nm/191.462500 THz 3.125/6.25/12.5GHz spacing";
               }
               enum "1565.78" {
                 description "1565.78 nm/191.465625 THz 3.125GHz spacing";
               }
               enum "1565.75" {
                 description "1565.75 nm/191.468750 THz 3.125/6.25GHz spacing";
               }
               enum "1565.73" {
                 description "1565.73 nm/191.471875 THz 3.125GHz spacing";
               }
               enum "1565.70" {
                 description "1565.70 nm/191.475000 THz 3.125/6.25/12.5/75GHz spacing";
               }
               enum "1565.67" {
                 description "1565.67 nm/191.478125 THz 3.125GHz spacing";
               }
               enum "1565.65" {
                 description "1565.65 nm/191.481250 THz 3.125/6.25GHz spacing";
               }
               enum "1565.62" {
                 description "1565.62 nm/191.484375 THz 3.125GHz spacing";
               }
               enum "1565.60" {
                 description "1565.60 nm/191.487500 THz 3.125/6.25/12.5GHz spacing";
               }
               enum "1565.57" {
                 description "1565.57 nm/191.490625 THz 3.125GHz spacing";
               }
               enum "1565.55" {
                 description "1565.55 nm/191.493750 THz 3.125/6.25GHz spacing";
               }
               enum "1565.52" {
                 description "1565.52 nm/191.496875 THz 3.125GHz spacing";
               }
               enum "1565.50" {
                 description "1565.50 nm/191.500000 THz 3.125/6.25/12.5/100GHz spacing";
               }
               enum "1565.47" {
                 description "1565.47 nm/191.503125 THz 3.125GHz spacing";
               }
               enum "1565.44" {
                 description "1565.44 nm/191.506250 THz 3.125/6.25GHz spacing";
               }
               enum "1565.42" {
                 description "1565.42 nm/191.509375 THz 3.125GHz spacing";
               }
               enum "1565.39" {
                 description "1565.39 nm/191.512500 THz 3.125/6.25/12.5GHz spacing";
               }
               enum "1565.37" {
                 description "1565.37 nm/191.515625 THz 3.125GHz spacing";
               }
               enum "1565.34" {
                 description "1565.34 nm/191.518750 THz 3.125/6.25GHz spacing";
               }
               enum "1565.32" {
                 description "1565.32 nm/191.521875 THz 3.125GHz spacing";
               }
               enum "1565.29" {
                 description "1565.29 nm/191.525000 THz 3.125/6.25/12.5GHz spacing";
               }
               enum "1565.27" {
                 description "1565.27 nm/191.528125 THz 3.125GHz spacing";
               }
               enum "1565.24" {
                 description "1565.24 nm/191.531250 THz 3.125/6.25GHz spacing";
               }
               enum "1565.21" {
                 description "1565.21 nm/191.534375 THz 3.125GHz spacing";
               }
               enum "1565.19" {
                 description "1565.19 nm/191.537500 THz 3.125/6.25/12.5GHz spacing";
               }
               enum "1565.16" {
                 description "1565.16 nm/191.540625 THz 3.125GHz spacing";
               }
               enum "1565.14" {
                 description "1565.14 nm/191.543750 THz 3.125/6.25GHz spacing";
               }
               enum "1565.11" {
                 description "1565.11 nm/191.546875 THz 3.125GHz spacing";
               }
               enum "1565.09" {
                 description "1565.09 nm/191.550000 THz 3.125/6.25/12.5/50/75GHz spacing";
               }
               enum "1565.06" {
                 description "1565.06 nm/191.553125 THz 3.125GHz spacing";
               }
               enum "1565.04" {
                 description "1565.04 nm/191.556250 THz 3.125/6.25GHz spacing";
               }
               enum "1565.01" {
                 description "1565.01 nm/191.559375 THz 3.125GHz spacing";
               }
               enum "1564.99" {
                 description "1564.99 nm/191.562500 THz 3.125/6.25/12.5GHz spacing";
               }
               enum "1564.96" {
                 description "1564.96 nm/191.565625 THz 3.125GHz spacing";
               }
               enum "1564.93" {
                 description "1564.93 nm/191.568750 THz 3.125/6.25GHz spacing";
               }
               enum "1564.91" {
                 description "1564.91 nm/191.571875 THz 3.125GHz spacing";
               }
               enum "1564.88" {
                 description "1564.88 nm/191.575000 THz 3.125/6.25/12.5GHz spacing";
               }
               enum "1564.86" {
                 description "1564.86 nm/191.578125 THz 3.125GHz spacing";
               }
               enum "1564.83" {
                 description "1564.83 nm/191.581250 THz 3.125/6.25GHz spacing";
               }
               enum "1564.81" {
                 description "1564.81 nm/191.584375 THz 3.125GHz spacing";
               }
               enum "1564.78" {
                 description "1564.78 nm/191.587500 THz 3.125/6.25/12.5GHz spacing";
               }
               enum "1564.76" {
                 description "1564.76 nm/191.590625 THz 3.125GHz spacing";
               }
               enum "1564.73" {
                 description "1564.73 nm/191.593750 THz 3.125/6.25GHz spacing";
               }
               enum "1564.70" {
                 description "1564.70 nm/191.596875 THz 3.125GHz spacing";
               }
               enum "1564.68" {
                 description "1564.68 nm/191.600000 THz 3.125/6.25/12.5/100GHz spacing";
               }
               enum "1564.65" {
                 description "1564.65 nm/191.603125 THz 3.125GHz spacing";
               }
               enum "1564.63" {
                 description "1564.63 nm/191.606250 THz 3.125/6.25GHz spacing";
               }
               enum "1564.60" {
                 description "1564.60 nm/191.609375 THz 3.125GHz spacing";
               }
               enum "1564.58" {
                 description "1564.58 nm/191.612500 THz 3.125/6.25/12.5GHz spacing";
               }
               enum "1564.55" {
                 description "1564.55 nm/191.615625 THz 3.125GHz spacing";
               }
               enum "1564.53" {
                 description "1564.53 nm/191.618750 THz 3.125/6.25GHz spacing";
               }
               enum "1564.50" {
                 description "1564.50 nm/191.621875 THz 3.125GHz spacing";
               }
               enum "1564.47" {
                 description "1564.47 nm/191.625000 THz 3.125/6.25/12.5/75GHz spacing";
               }
               enum "1564.45" {
                 description "1564.45 nm/191.628125 THz 3.125GHz spacing";
               }
               enum "1564.42" {
                 description "1564.42 nm/191.631250 THz 3.125/6.25GHz spacing";
               }
               enum "1564.40" {
                 description "1564.40 nm/191.634375 THz 3.125GHz spacing";
               }
               enum "1564.37" {
                 description "1564.37 nm/191.637500 THz 3.125/6.25/12.5GHz spacing";
               }
               enum "1564.35" {
                 description "1564.35 nm/191.640625 THz 3.125GHz spacing";
               }
               enum "1564.32" {
                 description "1564.32 nm/191.643750 THz 3.125/6.25GHz spacing";
               }
               enum "1564.30" {
                 description "1564.30 nm/191.646875 THz 3.125GHz spacing";
               }
               enum "1564.27" {
                 description "1564.27 nm/191.650000 THz 3.125/6.25/12.5/50GHz spacing";
               }
               enum "1564.25" {
                 description "1564.25 nm/191.653125 THz 3.125GHz spacing";
               }
               enum "1564.22" {
                 description "1564.22 nm/191.656250 THz 3.125/6.25GHz spacing";
               }
               enum "1564.19" {
                 description "1564.19 nm/191.659375 THz 3.125GHz spacing";
               }
               enum "1564.17" {
                 description "1564.17 nm/191.662500 THz 3.125/6.25/12.5GHz spacing";
               }
               enum "1564.14" {
                 description "1564.14 nm/191.665625 THz 3.125GHz spacing";
               }
               enum "1564.12" {
                 description "1564.12 nm/191.668750 THz 3.125/6.25GHz spacing";
               }
               enum "1564.09" {
                 description "1564.09 nm/191.671875 THz 3.125GHz spacing";
               }
               enum "1564.07" {
                 description "1564.07 nm/191.675000 THz 3.125/6.25/12.5GHz spacing";
               }
               enum "1564.04" {
                 description "1564.04 nm/191.678125 THz 3.125GHz spacing";
               }
               enum "1564.02" {
                 description "1564.02 nm/191.681250 THz 3.125/6.25GHz spacing";
               }
               enum "1563.99" {
                 description "1563.99 nm/191.684375 THz 3.125GHz spacing";
               }
               enum "1563.96" {
                 description "1563.96 nm/191.687500 THz 3.125/6.25/12.5GHz spacing";
               }
               enum "1563.94" {
                 description "1563.94 nm/191.690625 THz 3.125GHz spacing";
               }
               enum "1563.91" {
                 description "1563.91 nm/191.693750 THz 3.125/6.25GHz spacing";
               }
               enum "1563.89" {
                 description "1563.89 nm/191.696875 THz 3.125GHz spacing";
               }
               enum "1563.86" {
                 description "1563.86 nm/191.700000 THz 3.125/6.25/12.5/50/75/100GHz spacing";
               }
               enum "1563.84" {
                 description "1563.84 nm/191.703125 THz 3.125GHz spacing";
               }
               enum "1563.81" {
                 description "1563.81 nm/191.706250 THz 3.125/6.25GHz spacing";
               }
               enum "1563.79" {
                 description "1563.79 nm/191.709375 THz 3.125GHz spacing";
               }
               enum "1563.76" {
                 description "1563.76 nm/191.712500 THz 3.125/6.25/12.5GHz spacing";
               }
               enum "1563.74" {
                 description "1563.74 nm/191.715625 THz 3.125GHz spacing";
               }
               enum "1563.71" {
                 description "1563.71 nm/191.718750 THz 3.125/6.25GHz spacing";
               }
               enum "1563.68" {
                 description "1563.68 nm/191.721875 THz 3.125GHz spacing";
               }
               enum "1563.66" {
                 description "1563.66 nm/191.725000 THz 3.125/6.25/12.5GHz spacing";
               }
               enum "1563.63" {
                 description "1563.63 nm/191.728125 THz 3.125GHz spacing";
               }
               enum "1563.61" {
                 description "1563.61 nm/191.731250 THz 3.125/6.25GHz spacing";
               }
               enum "1563.58" {
                 description "1563.58 nm/191.734375 THz 3.125GHz spacing";
               }
               enum "1563.56" {
                 description "1563.56 nm/191.737500 THz 3.125/6.25/12.5GHz spacing";
               }
               enum "1563.53" {
                 description "1563.53 nm/191.740625 THz 3.125GHz spacing";
               }
               enum "1563.51" {
                 description "1563.51 nm/191.743750 THz 3.125/6.25GHz spacing";
               }
               enum "1563.48" {
                 description "1563.48 nm/191.746875 THz 3.125GHz spacing";
               }
               enum "1563.45" {
                 description "1563.45 nm/191.750000 THz 3.125/6.25/12.5/50GHz spacing";
               }
               enum "1563.43" {
                 description "1563.43 nm/191.753125 THz 3.125GHz spacing";
               }
               enum "1563.40" {
                 description "1563.40 nm/191.756250 THz 3.125/6.25GHz spacing";
               }
               enum "1563.38" {
                 description "1563.38 nm/191.759375 THz 3.125GHz spacing";
               }
               enum "1563.35" {
                 description "1563.35 nm/191.762500 THz 3.125/6.25/12.5GHz spacing";
               }
               enum "1563.33" {
                 description "1563.33 nm/191.765625 THz 3.125GHz spacing";
               }
               enum "1563.30" {
                 description "1563.30 nm/191.768750 THz 3.125/6.25GHz spacing";
               }
               enum "1563.28" {
                 description "1563.28 nm/191.771875 THz 3.125GHz spacing";
               }
               enum "1563.25" {
                 description "1563.25 nm/191.775000 THz 3.125/6.25/12.5/75GHz spacing";
               }
               enum "1563.23" {
                 description "1563.23 nm/191.778125 THz 3.125GHz spacing";
               }
               enum "1563.20" {
                 description "1563.20 nm/191.781250 THz 3.125/6.25GHz spacing";
               }
               enum "1563.17" {
                 description "1563.17 nm/191.784375 THz 3.125GHz spacing";
               }
               enum "1563.15" {
                 description "1563.15 nm/191.787500 THz 3.125/6.25/12.5GHz spacing";
               }
               enum "1563.12" {
                 description "1563.12 nm/191.790625 THz 3.125GHz spacing";
               }
               enum "1563.10" {
                 description "1563.10 nm/191.793750 THz 3.125/6.25GHz spacing";
               }
               enum "1563.07" {
                 description "1563.07 nm/191.796875 THz 3.125GHz spacing";
               }
               enum "1563.05" {
                 description "1563.05 nm/191.800000 THz 3.125/6.25/12.5/100GHz spacing";
               }
               enum "1563.02" {
                 description "1563.02 nm/191.803125 THz 3.125GHz spacing";
               }
               enum "1563.00" {
                 description "1563.00 nm/191.806250 THz 3.125/6.25GHz spacing";
               }
               enum "1562.97" {
                 description "1562.97 nm/191.809375 THz 3.125GHz spacing";
               }
               enum "1562.95" {
                 description "1562.95 nm/191.812500 THz 3.125/6.25/12.5GHz spacing";
               }
               enum "1562.92" {
                 description "1562.92 nm/191.815625 THz 3.125GHz spacing";
               }
               enum "1562.89" {
                 description "1562.89 nm/191.818750 THz 3.125/6.25GHz spacing";
               }
               enum "1562.87" {
                 description "1562.87 nm/191.821875 THz 3.125GHz spacing";
               }
               enum "1562.84" {
                 description "1562.84 nm/191.825000 THz 3.125/6.25/12.5GHz spacing";
               }
               enum "1562.82" {
                 description "1562.82 nm/191.828125 THz 3.125GHz spacing";
               }
               enum "1562.79" {
                 description "1562.79 nm/191.831250 THz 3.125/6.25GHz spacing";
               }
               enum "1562.77" {
                 description "1562.77 nm/191.834375 THz 3.125GHz spacing";
               }
               enum "1562.74" {
                 description "1562.74 nm/191.837500 THz 3.125/6.25/12.5GHz spacing";
               }
               enum "1562.72" {
                 description "1562.72 nm/191.840625 THz 3.125GHz spacing";
               }
               enum "1562.69" {
                 description "1562.69 nm/191.843750 THz 3.125/6.25GHz spacing";
               }
               enum "1562.67" {
                 description "1562.67 nm/191.846875 THz 3.125GHz spacing";
               }
               enum "1562.64" {
                 description "1562.64 nm/191.850000 THz 3.125/6.25/12.5/50/75GHz spacing";
               }
               enum "1562.61" {
                 description "1562.61 nm/191.853125 THz 3.125GHz spacing";
               }
               enum "1562.59" {
                 description "1562.59 nm/191.856250 THz 3.125/6.25GHz spacing";
               }
               enum "1562.56" {
                 description "1562.56 nm/191.859375 THz 3.125GHz spacing";
               }
               enum "1562.54" {
                 description "1562.54 nm/191.862500 THz 3.125/6.25/12.5GHz spacing";
               }
               enum "1562.51" {
                 description "1562.51 nm/191.865625 THz 3.125GHz spacing";
               }
               enum "1562.49" {
                 description "1562.49 nm/191.868750 THz 3.125/6.25GHz spacing";
               }
               enum "1562.46" {
                 description "1562.46 nm/191.871875 THz 3.125GHz spacing";
               }
               enum "1562.44" {
                 description "1562.44 nm/191.875000 THz 3.125/6.25/12.5GHz spacing";
               }
               enum "1562.41" {
                 description "1562.41 nm/191.878125 THz 3.125GHz spacing";
               }
               enum "1562.39" {
                 description "1562.39 nm/191.881250 THz 3.125/6.25GHz spacing";
               }
               enum "1562.36" {
                 description "1562.36 nm/191.884375 THz 3.125GHz spacing";
               }
               enum "1562.33" {
                 description "1562.33 nm/191.887500 THz 3.125/6.25/12.5GHz spacing";
               }
               enum "1562.31" {
                 description "1562.31 nm/191.890625 THz 3.125GHz spacing";
               }
               enum "1562.28" {
                 description "1562.28 nm/191.893750 THz 3.125/6.25GHz spacing";
               }
               enum "1562.26" {
                 description "1562.26 nm/191.896875 THz 3.125GHz spacing";
               }
               enum "1562.23" {
                 description "1562.23 nm/191.900000 THz 3.125/6.25/12.5/100GHz spacing";
               }
               enum "1562.21" {
                 description "1562.21 nm/191.903125 THz 3.125GHz spacing";
               }
               enum "1562.18" {
                 description "1562.18 nm/191.906250 THz 3.125/6.25GHz spacing";
               }
               enum "1562.16" {
                 description "1562.16 nm/191.909375 THz 3.125GHz spacing";
               }
               enum "1562.13" {
                 description "1562.13 nm/191.912500 THz 3.125/6.25/12.5GHz spacing";
               }
               enum "1562.11" {
                 description "1562.11 nm/191.915625 THz 3.125GHz spacing";
               }
               enum "1562.08" {
                 description "1562.08 nm/191.918750 THz 3.125/6.25GHz spacing";
               }
               enum "1562.05" {
                 description "1562.05 nm/191.921875 THz 3.125GHz spacing";
               }
               enum "1562.03" {
                 description "1562.03 nm/191.925000 THz 3.125/6.25/12.5/75GHz spacing";
               }
               enum "1562.00" {
                 description "1562.00 nm/191.928125 THz 3.125GHz spacing";
               }
               enum "1561.98" {
                 description "1561.98 nm/191.931250 THz 3.125/6.25GHz spacing";
               }
               enum "1561.95" {
                 description "1561.95 nm/191.934375 THz 3.125GHz spacing";
               }
               enum "1561.93" {
                 description "1561.93 nm/191.937500 THz 3.125/6.25/12.5GHz spacing";
               }
               enum "1561.90" {
                 description "1561.90 nm/191.940625 THz 3.125GHz spacing";
               }
               enum "1561.88" {
                 description "1561.88 nm/191.943750 THz 3.125/6.25GHz spacing";
               }
               enum "1561.85" {
                 description "1561.85 nm/191.946875 THz 3.125GHz spacing";
               }
               enum "1561.83" {
                 description "1561.83 nm/191.950000 THz 3.125/6.25/12.5/50GHz spacing";
               }
               enum "1561.80" {
                 description "1561.80 nm/191.953125 THz 3.125GHz spacing";
               }
               enum "1561.77" {
                 description "1561.77 nm/191.956250 THz 3.125/6.25GHz spacing";
               }
               enum "1561.75" {
                 description "1561.75 nm/191.959375 THz 3.125GHz spacing";
               }
               enum "1561.72" {
                 description "1561.72 nm/191.962500 THz 3.125/6.25/12.5GHz spacing";
               }
               enum "1561.70" {
                 description "1561.70 nm/191.965625 THz 3.125GHz spacing";
               }
               enum "1561.67" {
                 description "1561.67 nm/191.968750 THz 3.125/6.25GHz spacing";
               }
               enum "1561.65" {
                 description "1561.65 nm/191.971875 THz 3.125GHz spacing";
               }
               enum "1561.62" {
                 description "1561.62 nm/191.975000 THz 3.125/6.25/12.5GHz spacing";
               }
               enum "1561.60" {
                 description "1561.60 nm/191.978125 THz 3.125GHz spacing";
               }
               enum "1561.57" {
                 description "1561.57 nm/191.981250 THz 3.125/6.25GHz spacing";
               }
               enum "1561.55" {
                 description "1561.55 nm/191.984375 THz 3.125GHz spacing";
               }
               enum "1561.52" {
                 description "1561.52 nm/191.987500 THz 3.125/6.25/12.5GHz spacing";
               }
               enum "1561.50" {
                 description "1561.50 nm/191.990625 THz 3.125GHz spacing";
               }
               enum "1561.47" {
                 description "1561.47 nm/191.993750 THz 3.125/6.25GHz spacing";
               }
               enum "1561.44" {
                 description "1561.44 nm/191.996875 THz 3.125GHz spacing";
               }
               enum "1561.42" {
                 description "1561.42 nm/192.000000 THz 3.125/6.25/12.5/50/75/100GHz spacing";
               }
               enum "1561.39" {
                 description "1561.39 nm/192.003125 THz 3.125GHz spacing";
               }
               enum "1561.37" {
                 description "1561.37 nm/192.006250 THz 3.125/6.25GHz spacing";
               }
               enum "1561.34" {
                 description "1561.34 nm/192.009375 THz 3.125GHz spacing";
               }
               enum "1561.32" {
                 description "1561.32 nm/192.012500 THz 3.125/6.25/12.5GHz spacing";
               }
               enum "1561.29" {
                 description "1561.29 nm/192.015625 THz 3.125GHz spacing";
               }
               enum "1561.27" {
                 description "1561.27 nm/192.018750 THz 3.125/6.25GHz spacing";
               }
               enum "1561.24" {
                 description "1561.24 nm/192.021875 THz 3.125GHz spacing";
               }
               enum "1561.22" {
                 description "1561.22 nm/192.025000 THz 3.125/6.25/12.5GHz spacing";
               }
               enum "1561.19" {
                 description "1561.19 nm/192.028125 THz 3.125GHz spacing";
               }
               enum "1561.16" {
                 description "1561.16 nm/192.031250 THz 3.125/6.25GHz spacing";
               }
               enum "1561.14" {
                 description "1561.14 nm/192.034375 THz 3.125GHz spacing";
               }
               enum "1561.11" {
                 description "1561.11 nm/192.037500 THz 3.125/6.25/12.5GHz spacing";
               }
               enum "1561.09" {
                 description "1561.09 nm/192.040625 THz 3.125GHz spacing";
               }
               enum "1561.06" {
                 description "1561.06 nm/192.043750 THz 3.125/6.25GHz spacing";
               }
               enum "1561.04" {
                 description "1561.04 nm/192.046875 THz 3.125GHz spacing";
               }
               enum "1561.01" {
                 description "1561.01 nm/192.050000 THz 3.125/6.25/12.5/50GHz spacing";
               }
               enum "1560.99" {
                 description "1560.99 nm/192.053125 THz 3.125GHz spacing";
               }
               enum "1560.96" {
                 description "1560.96 nm/192.056250 THz 3.125/6.25GHz spacing";
               }
               enum "1560.94" {
                 description "1560.94 nm/192.059375 THz 3.125GHz spacing";
               }
               enum "1560.91" {
                 description "1560.91 nm/192.062500 THz 3.125/6.25/12.5GHz spacing";
               }
               enum "1560.89" {
                 description "1560.89 nm/192.065625 THz 3.125GHz spacing";
               }
               enum "1560.86" {
                 description "1560.86 nm/192.068750 THz 3.125/6.25GHz spacing";
               }
               enum "1560.83" {
                 description "1560.83 nm/192.071875 THz 3.125GHz spacing";
               }
               enum "1560.81" {
                 description "1560.81 nm/192.075000 THz 3.125/6.25/12.5/75GHz spacing";
               }
               enum "1560.78" {
                 description "1560.78 nm/192.078125 THz 3.125GHz spacing";
               }
               enum "1560.76" {
                 description "1560.76 nm/192.081250 THz 3.125/6.25GHz spacing";
               }
               enum "1560.73" {
                 description "1560.73 nm/192.084375 THz 3.125GHz spacing";
               }
               enum "1560.71" {
                 description "1560.71 nm/192.087500 THz 3.125/6.25/12.5GHz spacing";
               }
               enum "1560.68" {
                 description "1560.68 nm/192.090625 THz 3.125GHz spacing";
               }
               enum "1560.66" {
                 description "1560.66 nm/192.093750 THz 3.125/6.25GHz spacing";
               }
               enum "1560.63" {
                 description "1560.63 nm/192.096875 THz 3.125GHz spacing";
               }
               enum "1560.61" {
                 description "1560.61 nm/192.100000 THz 3.125/6.25/12.5/100GHz spacing";
               }
               enum "1560.58" {
                 description "1560.58 nm/192.103125 THz 3.125GHz spacing";
               }
               enum "1560.56" {
                 description "1560.56 nm/192.106250 THz 3.125/6.25GHz spacing";
               }
               enum "1560.53" {
                 description "1560.53 nm/192.109375 THz 3.125GHz spacing";
               }
               enum "1560.50" {
                 description "1560.50 nm/192.112500 THz 3.125/6.25/12.5GHz spacing";
               }
               enum "1560.48" {
                 description "1560.48 nm/192.115625 THz 3.125GHz spacing";
               }
               enum "1560.45" {
                 description "1560.45 nm/192.118750 THz 3.125/6.25GHz spacing";
               }
               enum "1560.43" {
                 description "1560.43 nm/192.121875 THz 3.125GHz spacing";
               }
               enum "1560.40" {
                 description "1560.40 nm/192.125000 THz 3.125/6.25/12.5GHz spacing";
               }
               enum "1560.38" {
                 description "1560.38 nm/192.128125 THz 3.125GHz spacing";
               }
               enum "1560.35" {
                 description "1560.35 nm/192.131250 THz 3.125/6.25GHz spacing";
               }
               enum "1560.33" {
                 description "1560.33 nm/192.134375 THz 3.125GHz spacing";
               }
               enum "1560.30" {
                 description "1560.30 nm/192.137500 THz 3.125/6.25/12.5GHz spacing";
               }
               enum "1560.28" {
                 description "1560.28 nm/192.140625 THz 3.125GHz spacing";
               }
               enum "1560.25" {
                 description "1560.25 nm/192.143750 THz 3.125/6.25GHz spacing";
               }
               enum "1560.23" {
                 description "1560.23 nm/192.146875 THz 3.125GHz spacing";
               }
               enum "1560.20" {
                 description "1560.20 nm/192.150000 THz 3.125/6.25/12.5/50/75GHz spacing";
               }
               enum "1560.17" {
                 description "1560.17 nm/192.153125 THz 3.125GHz spacing";
               }
               enum "1560.15" {
                 description "1560.15 nm/192.156250 THz 3.125/6.25GHz spacing";
               }
               enum "1560.12" {
                 description "1560.12 nm/192.159375 THz 3.125GHz spacing";
               }
               enum "1560.10" {
                 description "1560.10 nm/192.162500 THz 3.125/6.25/12.5GHz spacing";
               }
               enum "1560.07" {
                 description "1560.07 nm/192.165625 THz 3.125GHz spacing";
               }
               enum "1560.05" {
                 description "1560.05 nm/192.168750 THz 3.125/6.25GHz spacing";
               }
               enum "1560.02" {
                 description "1560.02 nm/192.171875 THz 3.125GHz spacing";
               }
               enum "1560.00" {
                 description "1560.00 nm/192.175000 THz 3.125/6.25/12.5GHz spacing";
               }
               enum "1559.97" {
                 description "1559.97 nm/192.178125 THz 3.125GHz spacing";
               }
               enum "1559.95" {
                 description "1559.95 nm/192.181250 THz 3.125/6.25GHz spacing";
               }
               enum "1559.92" {
                 description "1559.92 nm/192.184375 THz 3.125GHz spacing";
               }
               enum "1559.90" {
                 description "1559.90 nm/192.187500 THz 3.125/6.25/12.5GHz spacing";
               }
               enum "1559.87" {
                 description "1559.87 nm/192.190625 THz 3.125GHz spacing";
               }
               enum "1559.84" {
                 description "1559.84 nm/192.193750 THz 3.125/6.25GHz spacing";
               }
               enum "1559.82" {
                 description "1559.82 nm/192.196875 THz 3.125GHz spacing";
               }
               enum "1559.79" {
                 description "1559.79 nm/192.200000 THz 3.125/6.25/12.5/100GHz spacing";
               }
               enum "1559.77" {
                 description "1559.77 nm/192.203125 THz 3.125GHz spacing";
               }
               enum "1559.74" {
                 description "1559.74 nm/192.206250 THz 3.125/6.25GHz spacing";
               }
               enum "1559.72" {
                 description "1559.72 nm/192.209375 THz 3.125GHz spacing";
               }
               enum "1559.69" {
                 description "1559.69 nm/192.212500 THz 3.125/6.25/12.5GHz spacing";
               }
               enum "1559.67" {
                 description "1559.67 nm/192.215625 THz 3.125GHz spacing";
               }
               enum "1559.64" {
                 description "1559.64 nm/192.218750 THz 3.125/6.25GHz spacing";
               }
               enum "1559.62" {
                 description "1559.62 nm/192.221875 THz 3.125GHz spacing";
               }
               enum "1559.59" {
                 description "1559.59 nm/192.225000 THz 3.125/6.25/12.5/75GHz spacing";
               }
               enum "1559.57" {
                 description "1559.57 nm/192.228125 THz 3.125GHz spacing";
               }
               enum "1559.54" {
                 description "1559.54 nm/192.231250 THz 3.125/6.25GHz spacing";
               }
               enum "1559.52" {
                 description "1559.52 nm/192.234375 THz 3.125GHz spacing";
               }
               enum "1559.49" {
                 description "1559.49 nm/192.237500 THz 3.125/6.25/12.5GHz spacing";
               }
               enum "1559.46" {
                 description "1559.46 nm/192.240625 THz 3.125GHz spacing";
               }
               enum "1559.44" {
                 description "1559.44 nm/192.243750 THz 3.125/6.25GHz spacing";
               }
               enum "1559.41" {
                 description "1559.41 nm/192.246875 THz 3.125GHz spacing";
               }
               enum "1559.39" {
                 description "1559.39 nm/192.250000 THz 3.125/6.25/12.5/50GHz spacing";
               }
               enum "1559.36" {
                 description "1559.36 nm/192.253125 THz 3.125GHz spacing";
               }
               enum "1559.34" {
                 description "1559.34 nm/192.256250 THz 3.125/6.25GHz spacing";
               }
               enum "1559.31" {
                 description "1559.31 nm/192.259375 THz 3.125GHz spacing";
               }
               enum "1559.29" {
                 description "1559.29 nm/192.262500 THz 3.125/6.25/12.5GHz spacing";
               }
               enum "1559.26" {
                 description "1559.26 nm/192.265625 THz 3.125GHz spacing";
               }
               enum "1559.24" {
                 description "1559.24 nm/192.268750 THz 3.125/6.25GHz spacing";
               }
               enum "1559.21" {
                 description "1559.21 nm/192.271875 THz 3.125GHz spacing";
               }
               enum "1559.19" {
                 description "1559.19 nm/192.275000 THz 3.125/6.25/12.5GHz spacing";
               }
               enum "1559.16" {
                 description "1559.16 nm/192.278125 THz 3.125GHz spacing";
               }
               enum "1559.14" {
                 description "1559.14 nm/192.281250 THz 3.125/6.25GHz spacing";
               }
               enum "1559.11" {
                 description "1559.11 nm/192.284375 THz 3.125GHz spacing";
               }
               enum "1559.08" {
                 description "1559.08 nm/192.287500 THz 3.125/6.25/12.5GHz spacing";
               }
               enum "1559.06" {
                 description "1559.06 nm/192.290625 THz 3.125GHz spacing";
               }
               enum "1559.03" {
                 description "1559.03 nm/192.293750 THz 3.125/6.25GHz spacing";
               }
               enum "1559.01" {
                 description "1559.01 nm/192.296875 THz 3.125GHz spacing";
               }
               enum "1558.98" {
                 description "1558.98 nm/192.300000 THz 3.125/6.25/12.5/50/75/100GHz spacing";
               }
               enum "1558.96" {
                 description "1558.96 nm/192.303125 THz 3.125GHz spacing";
               }
               enum "1558.93" {
                 description "1558.93 nm/192.306250 THz 3.125/6.25GHz spacing";
               }
               enum "1558.91" {
                 description "1558.91 nm/192.309375 THz 3.125GHz spacing";
               }
               enum "1558.88" {
                 description "1558.88 nm/192.312500 THz 3.125/6.25/12.5GHz spacing";
               }
               enum "1558.86" {
                 description "1558.86 nm/192.315625 THz 3.125GHz spacing";
               }
               enum "1558.83" {
                 description "1558.83 nm/192.318750 THz 3.125/6.25GHz spacing";
               }
               enum "1558.81" {
                 description "1558.81 nm/192.321875 THz 3.125GHz spacing";
               }
               enum "1558.78" {
                 description "1558.78 nm/192.325000 THz 3.125/6.25/12.5GHz spacing";
               }
               enum "1558.76" {
                 description "1558.76 nm/192.328125 THz 3.125GHz spacing";
               }
               enum "1558.73" {
                 description "1558.73 nm/192.331250 THz 3.125/6.25GHz spacing";
               }
               enum "1558.70" {
                 description "1558.70 nm/192.334375 THz 3.125GHz spacing";
               }
               enum "1558.68" {
                 description "1558.68 nm/192.337500 THz 3.125/6.25/12.5GHz spacing";
               }
               enum "1558.65" {
                 description "1558.65 nm/192.340625 THz 3.125GHz spacing";
               }
               enum "1558.63" {
                 description "1558.63 nm/192.343750 THz 3.125/6.25GHz spacing";
               }
               enum "1558.60" {
                 description "1558.60 nm/192.346875 THz 3.125GHz spacing";
               }
               enum "1558.58" {
                 description "1558.58 nm/192.350000 THz 3.125/6.25/12.5/50GHz spacing";
               }
               enum "1558.55" {
                 description "1558.55 nm/192.353125 THz 3.125GHz spacing";
               }
               enum "1558.53" {
                 description "1558.53 nm/192.356250 THz 3.125/6.25GHz spacing";
               }
               enum "1558.50" {
                 description "1558.50 nm/192.359375 THz 3.125GHz spacing";
               }
               enum "1558.48" {
                 description "1558.48 nm/192.362500 THz 3.125/6.25/12.5GHz spacing";
               }
               enum "1558.45" {
                 description "1558.45 nm/192.365625 THz 3.125GHz spacing";
               }
               enum "1558.43" {
                 description "1558.43 nm/192.368750 THz 3.125/6.25GHz spacing";
               }
               enum "1558.40" {
                 description "1558.40 nm/192.371875 THz 3.125GHz spacing";
               }
               enum "1558.38" {
                 description "1558.38 nm/192.375000 THz 3.125/6.25/12.5/75GHz spacing";
               }
               enum "1558.35" {
                 description "1558.35 nm/192.378125 THz 3.125GHz spacing";
               }
               enum "1558.32" {
                 description "1558.32 nm/192.381250 THz 3.125/6.25GHz spacing";
               }
               enum "1558.30" {
                 description "1558.30 nm/192.384375 THz 3.125GHz spacing";
               }
               enum "1558.27" {
                 description "1558.27 nm/192.387500 THz 3.125/6.25/12.5GHz spacing";
               }
               enum "1558.25" {
                 description "1558.25 nm/192.390625 THz 3.125GHz spacing";
               }
               enum "1558.22" {
                 description "1558.22 nm/192.393750 THz 3.125/6.25GHz spacing";
               }
               enum "1558.20" {
                 description "1558.20 nm/192.396875 THz 3.125GHz spacing";
               }
               enum "1558.17" {
                 description "1558.17 nm/192.400000 THz 3.125/6.25/12.5/100GHz spacing";
               }
               enum "1558.15" {
                 description "1558.15 nm/192.403125 THz 3.125GHz spacing";
               }
               enum "1558.12" {
                 description "1558.12 nm/192.406250 THz 3.125/6.25GHz spacing";
               }
               enum "1558.10" {
                 description "1558.10 nm/192.409375 THz 3.125GHz spacing";
               }
               enum "1558.07" {
                 description "1558.07 nm/192.412500 THz 3.125/6.25/12.5GHz spacing";
               }
               enum "1558.05" {
                 description "1558.05 nm/192.415625 THz 3.125GHz spacing";
               }
               enum "1558.02" {
                 description "1558.02 nm/192.418750 THz 3.125/6.25GHz spacing";
               }
               enum "1558.00" {
                 description "1558.00 nm/192.421875 THz 3.125GHz spacing";
               }
               enum "1557.97" {
                 description "1557.97 nm/192.425000 THz 3.125/6.25/12.5GHz spacing";
               }
               enum "1557.95" {
                 description "1557.95 nm/192.428125 THz 3.125GHz spacing";
               }
               enum "1557.92" {
                 description "1557.92 nm/192.431250 THz 3.125/6.25GHz spacing";
               }
               enum "1557.89" {
                 description "1557.89 nm/192.434375 THz 3.125GHz spacing";
               }
               enum "1557.87" {
                 description "1557.87 nm/192.437500 THz 3.125/6.25/12.5GHz spacing";
               }
               enum "1557.84" {
                 description "1557.84 nm/192.440625 THz 3.125GHz spacing";
               }
               enum "1557.82" {
                 description "1557.82 nm/192.443750 THz 3.125/6.25GHz spacing";
               }
               enum "1557.79" {
                 description "1557.79 nm/192.446875 THz 3.125GHz spacing";
               }
               enum "1557.77" {
                 description "1557.77 nm/192.450000 THz 3.125/6.25/12.5/50/75GHz spacing";
               }
               enum "1557.74" {
                 description "1557.74 nm/192.453125 THz 3.125GHz spacing";
               }
               enum "1557.72" {
                 description "1557.72 nm/192.456250 THz 3.125/6.25GHz spacing";
               }
               enum "1557.69" {
                 description "1557.69 nm/192.459375 THz 3.125GHz spacing";
               }
               enum "1557.67" {
                 description "1557.67 nm/192.462500 THz 3.125/6.25/12.5GHz spacing";
               }
               enum "1557.64" {
                 description "1557.64 nm/192.465625 THz 3.125GHz spacing";
               }
               enum "1557.62" {
                 description "1557.62 nm/192.468750 THz 3.125/6.25GHz spacing";
               }
               enum "1557.59" {
                 description "1557.59 nm/192.471875 THz 3.125GHz spacing";
               }
               enum "1557.57" {
                 description "1557.57 nm/192.475000 THz 3.125/6.25/12.5GHz spacing";
               }
               enum "1557.54" {
                 description "1557.54 nm/192.478125 THz 3.125GHz spacing";
               }
               enum "1557.52" {
                 description "1557.52 nm/192.481250 THz 3.125/6.25GHz spacing";
               }
               enum "1557.49" {
                 description "1557.49 nm/192.484375 THz 3.125GHz spacing";
               }
               enum "1557.46" {
                 description "1557.46 nm/192.487500 THz 3.125/6.25/12.5GHz spacing";
               }
               enum "1557.44" {
                 description "1557.44 nm/192.490625 THz 3.125GHz spacing";
               }
               enum "1557.41" {
                 description "1557.41 nm/192.493750 THz 3.125/6.25GHz spacing";
               }
               enum "1557.39" {
                 description "1557.39 nm/192.496875 THz 3.125GHz spacing";
               }
               enum "1557.36" {
                 description "1557.36 nm/192.500000 THz 3.125/6.25/12.5/100GHz spacing";
               }
               enum "1557.34" {
                 description "1557.34 nm/192.503125 THz 3.125GHz spacing";
               }
               enum "1557.31" {
                 description "1557.31 nm/192.506250 THz 3.125/6.25GHz spacing";
               }
               enum "1557.29" {
                 description "1557.29 nm/192.509375 THz 3.125GHz spacing";
               }
               enum "1557.26" {
                 description "1557.26 nm/192.512500 THz 3.125/6.25/12.5GHz spacing";
               }
               enum "1557.24" {
                 description "1557.24 nm/192.515625 THz 3.125GHz spacing";
               }
               enum "1557.21" {
                 description "1557.21 nm/192.518750 THz 3.125/6.25GHz spacing";
               }
               enum "1557.19" {
                 description "1557.19 nm/192.521875 THz 3.125GHz spacing";
               }
               enum "1557.16" {
                 description "1557.16 nm/192.525000 THz 3.125/6.25/12.5/75GHz spacing";
               }
               enum "1557.14" {
                 description "1557.14 nm/192.528125 THz 3.125GHz spacing";
               }
               enum "1557.11" {
                 description "1557.11 nm/192.531250 THz 3.125/6.25GHz spacing";
               }
               enum "1557.09" {
                 description "1557.09 nm/192.534375 THz 3.125GHz spacing";
               }
               enum "1557.06" {
                 description "1557.06 nm/192.537500 THz 3.125/6.25/12.5GHz spacing";
               }
               enum "1557.03" {
                 description "1557.03 nm/192.540625 THz 3.125GHz spacing";
               }
               enum "1557.01" {
                 description "1557.01 nm/192.543750 THz 3.125/6.25GHz spacing";
               }
               enum "1556.98" {
                 description "1556.98 nm/192.546875 THz 3.125GHz spacing";
               }
               enum "1556.96" {
                 description "1556.96 nm/192.550000 THz 3.125/6.25/12.5/50GHz spacing";
               }
               enum "1556.93" {
                 description "1556.93 nm/192.553125 THz 3.125GHz spacing";
               }
               enum "1556.91" {
                 description "1556.91 nm/192.556250 THz 3.125/6.25GHz spacing";
               }
               enum "1556.88" {
                 description "1556.88 nm/192.559375 THz 3.125GHz spacing";
               }
               enum "1556.86" {
                 description "1556.86 nm/192.562500 THz 3.125/6.25/12.5GHz spacing";
               }
               enum "1556.83" {
                 description "1556.83 nm/192.565625 THz 3.125GHz spacing";
               }
               enum "1556.81" {
                 description "1556.81 nm/192.568750 THz 3.125/6.25GHz spacing";
               }
               enum "1556.78" {
                 description "1556.78 nm/192.571875 THz 3.125GHz spacing";
               }
               enum "1556.76" {
                 description "1556.76 nm/192.575000 THz 3.125/6.25/12.5GHz spacing";
               }
               enum "1556.73" {
                 description "1556.73 nm/192.578125 THz 3.125GHz spacing";
               }
               enum "1556.71" {
                 description "1556.71 nm/192.581250 THz 3.125/6.25GHz spacing";
               }
               enum "1556.68" {
                 description "1556.68 nm/192.584375 THz 3.125GHz spacing";
               }
               enum "1556.66" {
                 description "1556.66 nm/192.587500 THz 3.125/6.25/12.5GHz spacing";
               }
               enum "1556.63" {
                 description "1556.63 nm/192.590625 THz 3.125GHz spacing";
               }
               enum "1556.61" {
                 description "1556.61 nm/192.593750 THz 3.125/6.25GHz spacing";
               }
               enum "1556.58" {
                 description "1556.58 nm/192.596875 THz 3.125GHz spacing";
               }
               enum "1556.55" {
                 description "1556.55 nm/192.600000 THz 3.125/6.25/12.5/50/75/100GHz spacing";
               }
               enum "1556.53" {
                 description "1556.53 nm/192.603125 THz 3.125GHz spacing";
               }
               enum "1556.50" {
                 description "1556.50 nm/192.606250 THz 3.125/6.25GHz spacing";
               }
               enum "1556.48" {
                 description "1556.48 nm/192.609375 THz 3.125GHz spacing";
               }
               enum "1556.45" {
                 description "1556.45 nm/192.612500 THz 3.125/6.25/12.5GHz spacing";
               }
               enum "1556.43" {
                 description "1556.43 nm/192.615625 THz 3.125GHz spacing";
               }
               enum "1556.40" {
                 description "1556.40 nm/192.618750 THz 3.125/6.25GHz spacing";
               }
               enum "1556.38" {
                 description "1556.38 nm/192.621875 THz 3.125GHz spacing";
               }
               enum "1556.35" {
                 description "1556.35 nm/192.625000 THz 3.125/6.25/12.5GHz spacing";
               }
               enum "1556.33" {
                 description "1556.33 nm/192.628125 THz 3.125GHz spacing";
               }
               enum "1556.30" {
                 description "1556.30 nm/192.631250 THz 3.125/6.25GHz spacing";
               }
               enum "1556.28" {
                 description "1556.28 nm/192.634375 THz 3.125GHz spacing";
               }
               enum "1556.25" {
                 description "1556.25 nm/192.637500 THz 3.125/6.25/12.5GHz spacing";
               }
               enum "1556.23" {
                 description "1556.23 nm/192.640625 THz 3.125GHz spacing";
               }
               enum "1556.20" {
                 description "1556.20 nm/192.643750 THz 3.125/6.25GHz spacing";
               }
               enum "1556.18" {
                 description "1556.18 nm/192.646875 THz 3.125GHz spacing";
               }
               enum "1556.15" {
                 description "1556.15 nm/192.650000 THz 3.125/6.25/12.5/50GHz spacing";
               }
               enum "1556.13" {
                 description "1556.13 nm/192.653125 THz 3.125GHz spacing";
               }
               enum "1556.10" {
                 description "1556.10 nm/192.656250 THz 3.125/6.25GHz spacing";
               }
               enum "1556.08" {
                 description "1556.08 nm/192.659375 THz 3.125GHz spacing";
               }
               enum "1556.05" {
                 description "1556.05 nm/192.662500 THz 3.125/6.25/12.5GHz spacing";
               }
               enum "1556.02" {
                 description "1556.02 nm/192.665625 THz 3.125GHz spacing";
               }
               enum "1556.00" {
                 description "1556.00 nm/192.668750 THz 3.125/6.25GHz spacing";
               }
               enum "1555.97" {
                 description "1555.97 nm/192.671875 THz 3.125GHz spacing";
               }
               enum "1555.95" {
                 description "1555.95 nm/192.675000 THz 3.125/6.25/12.5/75GHz spacing";
               }
               enum "1555.92" {
                 description "1555.92 nm/192.678125 THz 3.125GHz spacing";
               }
               enum "1555.90" {
                 description "1555.90 nm/192.681250 THz 3.125/6.25GHz spacing";
               }
               enum "1555.87" {
                 description "1555.87 nm/192.684375 THz 3.125GHz spacing";
               }
               enum "1555.85" {
                 description "1555.85 nm/192.687500 THz 3.125/6.25/12.5GHz spacing";
               }
               enum "1555.82" {
                 description "1555.82 nm/192.690625 THz 3.125GHz spacing";
               }
               enum "1555.80" {
                 description "1555.80 nm/192.693750 THz 3.125/6.25GHz spacing";
               }
               enum "1555.77" {
                 description "1555.77 nm/192.696875 THz 3.125GHz spacing";
               }
               enum "1555.75" {
                 description "1555.75 nm/192.700000 THz 3.125/6.25/12.5/100GHz spacing";
               }
               enum "1555.72" {
                 description "1555.72 nm/192.703125 THz 3.125GHz spacing";
               }
               enum "1555.70" {
                 description "1555.70 nm/192.706250 THz 3.125/6.25GHz spacing";
               }
               enum "1555.67" {
                 description "1555.67 nm/192.709375 THz 3.125GHz spacing";
               }
               enum "1555.65" {
                 description "1555.65 nm/192.712500 THz 3.125/6.25/12.5GHz spacing";
               }
               enum "1555.62" {
                 description "1555.62 nm/192.715625 THz 3.125GHz spacing";
               }
               enum "1555.60" {
                 description "1555.60 nm/192.718750 THz 3.125/6.25GHz spacing";
               }
               enum "1555.57" {
                 description "1555.57 nm/192.721875 THz 3.125GHz spacing";
               }
               enum "1555.55" {
                 description "1555.55 nm/192.725000 THz 3.125/6.25/12.5GHz spacing";
               }
               enum "1555.52" {
                 description "1555.52 nm/192.728125 THz 3.125GHz spacing";
               }
               enum "1555.49" {
                 description "1555.49 nm/192.731250 THz 3.125/6.25GHz spacing";
               }
               enum "1555.47" {
                 description "1555.47 nm/192.734375 THz 3.125GHz spacing";
               }
               enum "1555.44" {
                 description "1555.44 nm/192.737500 THz 3.125/6.25/12.5GHz spacing";
               }
               enum "1555.42" {
                 description "1555.42 nm/192.740625 THz 3.125GHz spacing";
               }
               enum "1555.39" {
                 description "1555.39 nm/192.743750 THz 3.125/6.25GHz spacing";
               }
               enum "1555.37" {
                 description "1555.37 nm/192.746875 THz 3.125GHz spacing";
               }
               enum "1555.34" {
                 description "1555.34 nm/192.750000 THz 3.125/6.25/12.5/50/75GHz spacing";
               }
               enum "1555.32" {
                 description "1555.32 nm/192.753125 THz 3.125GHz spacing";
               }
               enum "1555.29" {
                 description "1555.29 nm/192.756250 THz 3.125/6.25GHz spacing";
               }
               enum "1555.27" {
                 description "1555.27 nm/192.759375 THz 3.125GHz spacing";
               }
               enum "1555.24" {
                 description "1555.24 nm/192.762500 THz 3.125/6.25/12.5GHz spacing";
               }
               enum "1555.22" {
                 description "1555.22 nm/192.765625 THz 3.125GHz spacing";
               }
               enum "1555.19" {
                 description "1555.19 nm/192.768750 THz 3.125/6.25GHz spacing";
               }
               enum "1555.17" {
                 description "1555.17 nm/192.771875 THz 3.125GHz spacing";
               }
               enum "1555.14" {
                 description "1555.14 nm/192.775000 THz 3.125/6.25/12.5GHz spacing";
               }
               enum "1555.12" {
                 description "1555.12 nm/192.778125 THz 3.125GHz spacing";
               }
               enum "1555.09" {
                 description "1555.09 nm/192.781250 THz 3.125/6.25GHz spacing";
               }
               enum "1555.07" {
                 description "1555.07 nm/192.784375 THz 3.125GHz spacing";
               }
               enum "1555.04" {
                 description "1555.04 nm/192.787500 THz 3.125/6.25/12.5GHz spacing";
               }
               enum "1555.02" {
                 description "1555.02 nm/192.790625 THz 3.125GHz spacing";
               }
               enum "1554.99" {
                 description "1554.99 nm/192.793750 THz 3.125/6.25GHz spacing";
               }
               enum "1554.97" {
                 description "1554.97 nm/192.796875 THz 3.125GHz spacing";
               }
               enum "1554.94" {
                 description "1554.94 nm/192.800000 THz 3.125/6.25/12.5/100GHz spacing";
               }
               enum "1554.91" {
                 description "1554.91 nm/192.803125 THz 3.125GHz spacing";
               }
               enum "1554.89" {
                 description "1554.89 nm/192.806250 THz 3.125/6.25GHz spacing";
               }
               enum "1554.86" {
                 description "1554.86 nm/192.809375 THz 3.125GHz spacing";
               }
               enum "1554.84" {
                 description "1554.84 nm/192.812500 THz 3.125/6.25/12.5GHz spacing";
               }
               enum "1554.81" {
                 description "1554.81 nm/192.815625 THz 3.125GHz spacing";
               }
               enum "1554.79" {
                 description "1554.79 nm/192.818750 THz 3.125/6.25GHz spacing";
               }
               enum "1554.76" {
                 description "1554.76 nm/192.821875 THz 3.125GHz spacing";
               }
               enum "1554.74" {
                 description "1554.74 nm/192.825000 THz 3.125/6.25/12.5/75GHz spacing";
               }
               enum "1554.71" {
                 description "1554.71 nm/192.828125 THz 3.125GHz spacing";
               }
               enum "1554.69" {
                 description "1554.69 nm/192.831250 THz 3.125/6.25GHz spacing";
               }
               enum "1554.66" {
                 description "1554.66 nm/192.834375 THz 3.125GHz spacing";
               }
               enum "1554.64" {
                 description "1554.64 nm/192.837500 THz 3.125/6.25/12.5GHz spacing";
               }
               enum "1554.61" {
                 description "1554.61 nm/192.840625 THz 3.125GHz spacing";
               }
               enum "1554.59" {
                 description "1554.59 nm/192.843750 THz 3.125/6.25GHz spacing";
               }
               enum "1554.56" {
                 description "1554.56 nm/192.846875 THz 3.125GHz spacing";
               }
               enum "1554.54" {
                 description "1554.54 nm/192.850000 THz 3.125/6.25/12.5/50GHz spacing";
               }
               enum "1554.51" {
                 description "1554.51 nm/192.853125 THz 3.125GHz spacing";
               }
               enum "1554.49" {
                 description "1554.49 nm/192.856250 THz 3.125/6.25GHz spacing";
               }
               enum "1554.46" {
                 description "1554.46 nm/192.859375 THz 3.125GHz spacing";
               }
               enum "1554.44" {
                 description "1554.44 nm/192.862500 THz 3.125/6.25/12.5GHz spacing";
               }
               enum "1554.41" {
                 description "1554.41 nm/192.865625 THz 3.125GHz spacing";
               }
               enum "1554.39" {
                 description "1554.39 nm/192.868750 THz 3.125/6.25GHz spacing";
               }
               enum "1554.36" {
                 description "1554.36 nm/192.871875 THz 3.125GHz spacing";
               }
               enum "1554.34" {
                 description "1554.34 nm/192.875000 THz 3.125/6.25/12.5GHz spacing";
               }
               enum "1554.31" {
                 description "1554.31 nm/192.878125 THz 3.125GHz spacing";
               }
               enum "1554.29" {
                 description "1554.29 nm/192.881250 THz 3.125/6.25GHz spacing";
               }
               enum "1554.26" {
                 description "1554.26 nm/192.884375 THz 3.125GHz spacing";
               }
               enum "1554.23" {
                 description "1554.23 nm/192.887500 THz 3.125/6.25/12.5GHz spacing";
               }
               enum "1554.21" {
                 description "1554.21 nm/192.890625 THz 3.125GHz spacing";
               }
               enum "1554.18" {
                 description "1554.18 nm/192.893750 THz 3.125/6.25GHz spacing";
               }
               enum "1554.16" {
                 description "1554.16 nm/192.896875 THz 3.125GHz spacing";
               }
               enum "1554.13" {
                 description "1554.13 nm/192.900000 THz 3.125/6.25/12.5/50/75/100GHz spacing";
               }
               enum "1554.11" {
                 description "1554.11 nm/192.903125 THz 3.125GHz spacing";
               }
               enum "1554.08" {
                 description "1554.08 nm/192.906250 THz 3.125/6.25GHz spacing";
               }
               enum "1554.06" {
                 description "1554.06 nm/192.909375 THz 3.125GHz spacing";
               }
               enum "1554.03" {
                 description "1554.03 nm/192.912500 THz 3.125/6.25/12.5GHz spacing";
               }
               enum "1554.01" {
                 description "1554.01 nm/192.915625 THz 3.125GHz spacing";
               }
               enum "1553.98" {
                 description "1553.98 nm/192.918750 THz 3.125/6.25GHz spacing";
               }
               enum "1553.96" {
                 description "1553.96 nm/192.921875 THz 3.125GHz spacing";
               }
               enum "1553.93" {
                 description "1553.93 nm/192.925000 THz 3.125/6.25/12.5GHz spacing";
               }
               enum "1553.91" {
                 description "1553.91 nm/192.928125 THz 3.125GHz spacing";
               }
               enum "1553.88" {
                 description "1553.88 nm/192.931250 THz 3.125/6.25GHz spacing";
               }
               enum "1553.86" {
                 description "1553.86 nm/192.934375 THz 3.125GHz spacing";
               }
               enum "1553.83" {
                 description "1553.83 nm/192.937500 THz 3.125/6.25/12.5GHz spacing";
               }
               enum "1553.81" {
                 description "1553.81 nm/192.940625 THz 3.125GHz spacing";
               }
               enum "1553.78" {
                 description "1553.78 nm/192.943750 THz 3.125/6.25GHz spacing";
               }
               enum "1553.76" {
                 description "1553.76 nm/192.946875 THz 3.125GHz spacing";
               }
               enum "1553.73" {
                 description "1553.73 nm/192.950000 THz 3.125/6.25/12.5/50GHz spacing";
               }
               enum "1553.71" {
                 description "1553.71 nm/192.953125 THz 3.125GHz spacing";
               }
               enum "1553.68" {
                 description "1553.68 nm/192.956250 THz 3.125/6.25GHz spacing";
               }
               enum "1553.66" {
                 description "1553.66 nm/192.959375 THz 3.125GHz spacing";
               }
               enum "1553.63" {
                 description "1553.63 nm/192.962500 THz 3.125/6.25/12.5GHz spacing";
               }
               enum "1553.61" {
                 description "1553.61 nm/192.965625 THz 3.125GHz spacing";
               }
               enum "1553.58" {
                 description "1553.58 nm/192.968750 THz 3.125/6.25GHz spacing";
               }
               enum "1553.56" {
                 description "1553.56 nm/192.971875 THz 3.125GHz spacing";
               }
               enum "1553.53" {
                 description "1553.53 nm/192.975000 THz 3.125/6.25/12.5/75GHz spacing";
               }
               enum "1553.50" {
                 description "1553.50 nm/192.978125 THz 3.125GHz spacing";
               }
               enum "1553.48" {
                 description "1553.48 nm/192.981250 THz 3.125/6.25GHz spacing";
               }
               enum "1553.45" {
                 description "1553.45 nm/192.984375 THz 3.125GHz spacing";
               }
               enum "1553.43" {
                 description "1553.43 nm/192.987500 THz 3.125/6.25/12.5GHz spacing";
               }
               enum "1553.40" {
                 description "1553.40 nm/192.990625 THz 3.125GHz spacing";
               }
               enum "1553.38" {
                 description "1553.38 nm/192.993750 THz 3.125/6.25GHz spacing";
               }
               enum "1553.35" {
                 description "1553.35 nm/192.996875 THz 3.125GHz spacing";
               }
               enum "1553.33" {
                 description "1553.33 nm/193.000000 THz 3.125/6.25/12.5/100GHz spacing";
               }
               enum "1553.30" {
                 description "1553.30 nm/193.003125 THz 3.125GHz spacing";
               }
               enum "1553.28" {
                 description "1553.28 nm/193.006250 THz 3.125/6.25GHz spacing";
               }
               enum "1553.25" {
                 description "1553.25 nm/193.009375 THz 3.125GHz spacing";
               }
               enum "1553.23" {
                 description "1553.23 nm/193.012500 THz 3.125/6.25/12.5GHz spacing";
               }
               enum "1553.20" {
                 description "1553.20 nm/193.015625 THz 3.125GHz spacing";
               }
               enum "1553.18" {
                 description "1553.18 nm/193.018750 THz 3.125/6.25GHz spacing";
               }
               enum "1553.15" {
                 description "1553.15 nm/193.021875 THz 3.125GHz spacing";
               }
               enum "1553.13" {
                 description "1553.13 nm/193.025000 THz 3.125/6.25/12.5GHz spacing";
               }
               enum "1553.10" {
                 description "1553.10 nm/193.028125 THz 3.125GHz spacing";
               }
               enum "1553.08" {
                 description "1553.08 nm/193.031250 THz 3.125/6.25GHz spacing";
               }
               enum "1553.05" {
                 description "1553.05 nm/193.034375 THz 3.125GHz spacing";
               }
               enum "1553.03" {
                 description "1553.03 nm/193.037500 THz 3.125/6.25/12.5GHz spacing";
               }
               enum "1553.00" {
                 description "1553.00 nm/193.040625 THz 3.125GHz spacing";
               }
               enum "1552.98" {
                 description "1552.98 nm/193.043750 THz 3.125/6.25GHz spacing";
               }
               enum "1552.95" {
                 description "1552.95 nm/193.046875 THz 3.125GHz spacing";
               }
               enum "1552.93" {
                 description "1552.93 nm/193.050000 THz 3.125/6.25/12.5/50/75GHz spacing";
               }
               enum "1552.90" {
                 description "1552.90 nm/193.053125 THz 3.125GHz spacing";
               }
               enum "1552.88" {
                 description "1552.88 nm/193.056250 THz 3.125/6.25GHz spacing";
               }
               enum "1552.85" {
                 description "1552.85 nm/193.059375 THz 3.125GHz spacing";
               }
               enum "1552.83" {
                 description "1552.83 nm/193.062500 THz 3.125/6.25/12.5GHz spacing";
               }
               enum "1552.80" {
                 description "1552.80 nm/193.065625 THz 3.125GHz spacing";
               }
               enum "1552.78" {
                 description "1552.78 nm/193.068750 THz 3.125/6.25GHz spacing";
               }
               enum "1552.75" {
                 description "1552.75 nm/193.071875 THz 3.125GHz spacing";
               }
               enum "1552.73" {
                 description "1552.73 nm/193.075000 THz 3.125/6.25/12.5GHz spacing";
               }
               enum "1552.70" {
                 description "1552.70 nm/193.078125 THz 3.125GHz spacing";
               }
               enum "1552.68" {
                 description "1552.68 nm/193.081250 THz 3.125/6.25GHz spacing";
               }
               enum "1552.65" {
                 description "1552.65 nm/193.084375 THz 3.125GHz spacing";
               }
               enum "1552.62" {
                 description "1552.62 nm/193.087500 THz 3.125/6.25/12.5GHz spacing";
               }
               enum "1552.60" {
                 description "1552.60 nm/193.090625 THz 3.125GHz spacing";
               }
               enum "1552.57" {
                 description "1552.57 nm/193.093750 THz 3.125/6.25GHz spacing";
               }
               enum "1552.55" {
                 description "1552.55 nm/193.096875 THz 3.125GHz spacing";
               }
               enum "1552.52" {
                 description "1552.52 nm/193.100000 THz 3.125/6.25/12.5/100GHz spacing";
               }
               enum "1552.50" {
                 description "1552.50 nm/193.103125 THz 3.125GHz spacing";
               }
               enum "1552.47" {
                 description "1552.47 nm/193.106250 THz 3.125/6.25GHz spacing";
               }
               enum "1552.45" {
                 description "1552.45 nm/193.109375 THz 3.125GHz spacing";
               }
               enum "1552.42" {
                 description "1552.42 nm/193.112500 THz 3.125/6.25/12.5GHz spacing";
               }
               enum "1552.40" {
                 description "1552.40 nm/193.115625 THz 3.125GHz spacing";
               }
               enum "1552.37" {
                 description "1552.37 nm/193.118750 THz 3.125/6.25GHz spacing";
               }
               enum "1552.35" {
                 description "1552.35 nm/193.121875 THz 3.125GHz spacing";
               }
               enum "1552.32" {
                 description "1552.32 nm/193.125000 THz 3.125/6.25/12.5/75GHz spacing";
               }
               enum "1552.30" {
                 description "1552.30 nm/193.128125 THz 3.125GHz spacing";
               }
               enum "1552.27" {
                 description "1552.27 nm/193.131250 THz 3.125/6.25GHz spacing";
               }
               enum "1552.25" {
                 description "1552.25 nm/193.134375 THz 3.125GHz spacing";
               }
               enum "1552.22" {
                 description "1552.22 nm/193.137500 THz 3.125/6.25/12.5GHz spacing";
               }
               enum "1552.20" {
                 description "1552.20 nm/193.140625 THz 3.125GHz spacing";
               }
               enum "1552.17" {
                 description "1552.17 nm/193.143750 THz 3.125/6.25GHz spacing";
               }
               enum "1552.15" {
                 description "1552.15 nm/193.146875 THz 3.125GHz spacing";
               }
               enum "1552.12" {
                 description "1552.12 nm/193.150000 THz 3.125/6.25/12.5/50GHz spacing";
               }
               enum "1552.10" {
                 description "1552.10 nm/193.153125 THz 3.125GHz spacing";
               }
               enum "1552.07" {
                 description "1552.07 nm/193.156250 THz 3.125/6.25GHz spacing";
               }
               enum "1552.05" {
                 description "1552.05 nm/193.159375 THz 3.125GHz spacing";
               }
               enum "1552.02" {
                 description "1552.02 nm/193.162500 THz 3.125/6.25/12.5GHz spacing";
               }
               enum "1552.00" {
                 description "1552.00 nm/193.165625 THz 3.125GHz spacing";
               }
               enum "1551.97" {
                 description "1551.97 nm/193.168750 THz 3.125/6.25GHz spacing";
               }
               enum "1551.95" {
                 description "1551.95 nm/193.171875 THz 3.125GHz spacing";
               }
               enum "1551.92" {
                 description "1551.92 nm/193.175000 THz 3.125/6.25/12.5GHz spacing";
               }
               enum "1551.90" {
                 description "1551.90 nm/193.178125 THz 3.125GHz spacing";
               }
               enum "1551.87" {
                 description "1551.87 nm/193.181250 THz 3.125/6.25GHz spacing";
               }
               enum "1551.85" {
                 description "1551.85 nm/193.184375 THz 3.125GHz spacing";
               }
               enum "1551.82" {
                 description "1551.82 nm/193.187500 THz 3.125/6.25/12.5GHz spacing";
               }
               enum "1551.80" {
                 description "1551.80 nm/193.190625 THz 3.125GHz spacing";
               }
               enum "1551.77" {
                 description "1551.77 nm/193.193750 THz 3.125/6.25GHz spacing";
               }
               enum "1551.75" {
                 description "1551.75 nm/193.196875 THz 3.125GHz spacing";
               }
               enum "1551.72" {
                 description "1551.72 nm/193.200000 THz 3.125/6.25/12.5/50/75/100GHz spacing";
               }
               enum "1551.70" {
                 description "1551.70 nm/193.203125 THz 3.125GHz spacing";
               }
               enum "1551.67" {
                 description "1551.67 nm/193.206250 THz 3.125/6.25GHz spacing";
               }
               enum "1551.65" {
                 description "1551.65 nm/193.209375 THz 3.125GHz spacing";
               }
               enum "1551.62" {
                 description "1551.62 nm/193.212500 THz 3.125/6.25/12.5GHz spacing";
               }
               enum "1551.60" {
                 description "1551.60 nm/193.215625 THz 3.125GHz spacing";
               }
               enum "1551.57" {
                 description "1551.57 nm/193.218750 THz 3.125/6.25GHz spacing";
               }
               enum "1551.55" {
                 description "1551.55 nm/193.221875 THz 3.125GHz spacing";
               }
               enum "1551.52" {
                 description "1551.52 nm/193.225000 THz 3.125/6.25/12.5GHz spacing";
               }
               enum "1551.49" {
                 description "1551.49 nm/193.228125 THz 3.125GHz spacing";
               }
               enum "1551.47" {
                 description "1551.47 nm/193.231250 THz 3.125/6.25GHz spacing";
               }
               enum "1551.44" {
                 description "1551.44 nm/193.234375 THz 3.125GHz spacing";
               }
               enum "1551.42" {
                 description "1551.42 nm/193.237500 THz 3.125/6.25/12.5GHz spacing";
               }
               enum "1551.39" {
                 description "1551.39 nm/193.240625 THz 3.125GHz spacing";
               }
               enum "1551.37" {
                 description "1551.37 nm/193.243750 THz 3.125/6.25GHz spacing";
               }
               enum "1551.34" {
                 description "1551.34 nm/193.246875 THz 3.125GHz spacing";
               }
               enum "1551.32" {
                 description "1551.32 nm/193.250000 THz 3.125/6.25/12.5/50GHz spacing";
               }
               enum "1551.29" {
                 description "1551.29 nm/193.253125 THz 3.125GHz spacing";
               }
               enum "1551.27" {
                 description "1551.27 nm/193.256250 THz 3.125/6.25GHz spacing";
               }
               enum "1551.24" {
                 description "1551.24 nm/193.259375 THz 3.125GHz spacing";
               }
               enum "1551.22" {
                 description "1551.22 nm/193.262500 THz 3.125/6.25/12.5GHz spacing";
               }
               enum "1551.19" {
                 description "1551.19 nm/193.265625 THz 3.125GHz spacing";
               }
               enum "1551.17" {
                 description "1551.17 nm/193.268750 THz 3.125/6.25GHz spacing";
               }
               enum "1551.14" {
                 description "1551.14 nm/193.271875 THz 3.125GHz spacing";
               }
               enum "1551.12" {
                 description "1551.12 nm/193.275000 THz 3.125/6.25/12.5/75GHz spacing";
               }
               enum "1551.09" {
                 description "1551.09 nm/193.278125 THz 3.125GHz spacing";
               }
               enum "1551.07" {
                 description "1551.07 nm/193.281250 THz 3.125/6.25GHz spacing";
               }
               enum "1551.04" {
                 description "1551.04 nm/193.284375 THz 3.125GHz spacing";
               }
               enum "1551.02" {
                 description "1551.02 nm/193.287500 THz 3.125/6.25/12.5GHz spacing";
               }
               enum "1550.99" {
                 description "1550.99 nm/193.290625 THz 3.125GHz spacing";
               }
               enum "1550.97" {
                 description "1550.97 nm/193.293750 THz 3.125/6.25GHz spacing";
               }
               enum "1550.94" {
                 description "1550.94 nm/193.296875 THz 3.125GHz spacing";
               }
               enum "1550.92" {
                 description "1550.92 nm/193.300000 THz 3.125/6.25/12.5/100GHz spacing";
               }
               enum "1550.89" {
                 description "1550.89 nm/193.303125 THz 3.125GHz spacing";
               }
               enum "1550.87" {
                 description "1550.87 nm/193.306250 THz 3.125/6.25GHz spacing";
               }
               enum "1550.84" {
                 description "1550.84 nm/193.309375 THz 3.125GHz spacing";
               }
               enum "1550.82" {
                 description "1550.82 nm/193.312500 THz 3.125/6.25/12.5GHz spacing";
               }
               enum "1550.79" {
                 description "1550.79 nm/193.315625 THz 3.125GHz spacing";
               }
               enum "1550.77" {
                 description "1550.77 nm/193.318750 THz 3.125/6.25GHz spacing";
               }
               enum "1550.74" {
                 description "1550.74 nm/193.321875 THz 3.125GHz spacing";
               }
               enum "1550.72" {
                 description "1550.72 nm/193.325000 THz 3.125/6.25/12.5GHz spacing";
               }
               enum "1550.69" {
                 description "1550.69 nm/193.328125 THz 3.125GHz spacing";
               }
               enum "1550.67" {
                 description "1550.67 nm/193.331250 THz 3.125/6.25GHz spacing";
               }
               enum "1550.64" {
                 description "1550.64 nm/193.334375 THz 3.125GHz spacing";
               }
               enum "1550.62" {
                 description "1550.62 nm/193.337500 THz 3.125/6.25/12.5GHz spacing";
               }
               enum "1550.59" {
                 description "1550.59 nm/193.340625 THz 3.125GHz spacing";
               }
               enum "1550.57" {
                 description "1550.57 nm/193.343750 THz 3.125/6.25GHz spacing";
               }
               enum "1550.54" {
                 description "1550.54 nm/193.346875 THz 3.125GHz spacing";
               }
               enum "1550.52" {
                 description "1550.52 nm/193.350000 THz 3.125/6.25/12.5/50/75GHz spacing";
               }
               enum "1550.49" {
                 description "1550.49 nm/193.353125 THz 3.125GHz spacing";
               }
               enum "1550.47" {
                 description "1550.47 nm/193.356250 THz 3.125/6.25GHz spacing";
               }
               enum "1550.44" {
                 description "1550.44 nm/193.359375 THz 3.125GHz spacing";
               }
               enum "1550.42" {
                 description "1550.42 nm/193.362500 THz 3.125/6.25/12.5GHz spacing";
               }
               enum "1550.39" {
                 description "1550.39 nm/193.365625 THz 3.125GHz spacing";
               }
               enum "1550.37" {
                 description "1550.37 nm/193.368750 THz 3.125/6.25GHz spacing";
               }
               enum "1550.34" {
                 description "1550.34 nm/193.371875 THz 3.125GHz spacing";
               }
               enum "1550.32" {
                 description "1550.32 nm/193.375000 THz 3.125/6.25/12.5GHz spacing";
               }
               enum "1550.29" {
                 description "1550.29 nm/193.378125 THz 3.125GHz spacing";
               }
               enum "1550.27" {
                 description "1550.27 nm/193.381250 THz 3.125/6.25GHz spacing";
               }
               enum "1550.24" {
                 description "1550.24 nm/193.384375 THz 3.125GHz spacing";
               }
               enum "1550.22" {
                 description "1550.22 nm/193.387500 THz 3.125/6.25/12.5GHz spacing";
               }
               enum "1550.19" {
                 description "1550.19 nm/193.390625 THz 3.125GHz spacing";
               }
               enum "1550.17" {
                 description "1550.17 nm/193.393750 THz 3.125/6.25GHz spacing";
               }
               enum "1550.14" {
                 description "1550.14 nm/193.396875 THz 3.125GHz spacing";
               }
               enum "1550.12" {
                 description "1550.12 nm/193.400000 THz 3.125/6.25/12.5/100GHz spacing";
               }
               enum "1550.09" {
                 description "1550.09 nm/193.403125 THz 3.125GHz spacing";
               }
               enum "1550.07" {
                 description "1550.07 nm/193.406250 THz 3.125/6.25GHz spacing";
               }
               enum "1550.04" {
                 description "1550.04 nm/193.409375 THz 3.125GHz spacing";
               }
               enum "1550.02" {
                 description "1550.02 nm/193.412500 THz 3.125/6.25/12.5GHz spacing";
               }
               enum "1549.99" {
                 description "1549.99 nm/193.415625 THz 3.125GHz spacing";
               }
               enum "1549.97" {
                 description "1549.97 nm/193.418750 THz 3.125/6.25GHz spacing";
               }
               enum "1549.94" {
                 description "1549.94 nm/193.421875 THz 3.125GHz spacing";
               }
               enum "1549.92" {
                 description "1549.92 nm/193.425000 THz 3.125/6.25/12.5/75GHz spacing";
               }
               enum "1549.89" {
                 description "1549.89 nm/193.428125 THz 3.125GHz spacing";
               }
               enum "1549.87" {
                 description "1549.87 nm/193.431250 THz 3.125/6.25GHz spacing";
               }
               enum "1549.84" {
                 description "1549.84 nm/193.434375 THz 3.125GHz spacing";
               }
               enum "1549.82" {
                 description "1549.82 nm/193.437500 THz 3.125/6.25/12.5GHz spacing";
               }
               enum "1549.79" {
                 description "1549.79 nm/193.440625 THz 3.125GHz spacing";
               }
               enum "1549.77" {
                 description "1549.77 nm/193.443750 THz 3.125/6.25GHz spacing";
               }
               enum "1549.74" {
                 description "1549.74 nm/193.446875 THz 3.125GHz spacing";
               }
               enum "1549.72" {
                 description "1549.72 nm/193.450000 THz 3.125/6.25/12.5/50GHz spacing";
               }
               enum "1549.69" {
                 description "1549.69 nm/193.453125 THz 3.125GHz spacing";
               }
               enum "1549.67" {
                 description "1549.67 nm/193.456250 THz 3.125/6.25GHz spacing";
               }
               enum "1549.64" {
                 description "1549.64 nm/193.459375 THz 3.125GHz spacing";
               }
               enum "1549.62" {
                 description "1549.62 nm/193.462500 THz 3.125/6.25/12.5GHz spacing";
               }
               enum "1549.59" {
                 description "1549.59 nm/193.465625 THz 3.125GHz spacing";
               }
               enum "1549.57" {
                 description "1549.57 nm/193.468750 THz 3.125/6.25GHz spacing";
               }
               enum "1549.54" {
                 description "1549.54 nm/193.471875 THz 3.125GHz spacing";
               }
               enum "1549.52" {
                 description "1549.52 nm/193.475000 THz 3.125/6.25/12.5GHz spacing";
               }
               enum "1549.49" {
                 description "1549.49 nm/193.478125 THz 3.125GHz spacing";
               }
               enum "1549.47" {
                 description "1549.47 nm/193.481250 THz 3.125/6.25GHz spacing";
               }
               enum "1549.44" {
                 description "1549.44 nm/193.484375 THz 3.125GHz spacing";
               }
               enum "1549.42" {
                 description "1549.42 nm/193.487500 THz 3.125/6.25/12.5GHz spacing";
               }
               enum "1549.39" {
                 description "1549.39 nm/193.490625 THz 3.125GHz spacing";
               }
               enum "1549.37" {
                 description "1549.37 nm/193.493750 THz 3.125/6.25GHz spacing";
               }
               enum "1549.34" {
                 description "1549.34 nm/193.496875 THz 3.125GHz spacing";
               }
               enum "1549.32" {
                 description "1549.32 nm/193.500000 THz 3.125/6.25/12.5/50/75/100GHz spacing";
               }
               enum "1549.29" {
                 description "1549.29 nm/193.503125 THz 3.125GHz spacing";
               }
               enum "1549.26" {
                 description "1549.26 nm/193.506250 THz 3.125/6.25GHz spacing";
               }
               enum "1549.24" {
                 description "1549.24 nm/193.509375 THz 3.125GHz spacing";
               }
               enum "1549.21" {
                 description "1549.21 nm/193.512500 THz 3.125/6.25/12.5GHz spacing";
               }
               enum "1549.19" {
                 description "1549.19 nm/193.515625 THz 3.125GHz spacing";
               }
               enum "1549.16" {
                 description "1549.16 nm/193.518750 THz 3.125/6.25GHz spacing";
               }
               enum "1549.14" {
                 description "1549.14 nm/193.521875 THz 3.125GHz spacing";
               }
               enum "1549.11" {
                 description "1549.11 nm/193.525000 THz 3.125/6.25/12.5GHz spacing";
               }
               enum "1549.09" {
                 description "1549.09 nm/193.528125 THz 3.125GHz spacing";
               }
               enum "1549.06" {
                 description "1549.06 nm/193.531250 THz 3.125/6.25GHz spacing";
               }
               enum "1549.04" {
                 description "1549.04 nm/193.534375 THz 3.125GHz spacing";
               }
               enum "1549.01" {
                 description "1549.01 nm/193.537500 THz 3.125/6.25/12.5GHz spacing";
               }
               enum "1548.99" {
                 description "1548.99 nm/193.540625 THz 3.125GHz spacing";
               }
               enum "1548.96" {
                 description "1548.96 nm/193.543750 THz 3.125/6.25GHz spacing";
               }
               enum "1548.94" {
                 description "1548.94 nm/193.546875 THz 3.125GHz spacing";
               }
               enum "1548.91" {
                 description "1548.91 nm/193.550000 THz 3.125/6.25/12.5/50GHz spacing";
               }
               enum "1548.89" {
                 description "1548.89 nm/193.553125 THz 3.125GHz spacing";
               }
               enum "1548.86" {
                 description "1548.86 nm/193.556250 THz 3.125/6.25GHz spacing";
               }
               enum "1548.84" {
                 description "1548.84 nm/193.559375 THz 3.125GHz spacing";
               }
               enum "1548.81" {
                 description "1548.81 nm/193.562500 THz 3.125/6.25/12.5GHz spacing";
               }
               enum "1548.79" {
                 description "1548.79 nm/193.565625 THz 3.125GHz spacing";
               }
               enum "1548.76" {
                 description "1548.76 nm/193.568750 THz 3.125/6.25GHz spacing";
               }
               enum "1548.74" {
                 description "1548.74 nm/193.571875 THz 3.125GHz spacing";
               }
               enum "1548.71" {
                 description "1548.71 nm/193.575000 THz 3.125/6.25/12.5/75GHz spacing";
               }
               enum "1548.69" {
                 description "1548.69 nm/193.578125 THz 3.125GHz spacing";
               }
               enum "1548.66" {
                 description "1548.66 nm/193.581250 THz 3.125/6.25GHz spacing";
               }
               enum "1548.64" {
                 description "1548.64 nm/193.584375 THz 3.125GHz spacing";
               }
               enum "1548.61" {
                 description "1548.61 nm/193.587500 THz 3.125/6.25/12.5GHz spacing";
               }
               enum "1548.59" {
                 description "1548.59 nm/193.590625 THz 3.125GHz spacing";
               }
               enum "1548.56" {
                 description "1548.56 nm/193.593750 THz 3.125/6.25GHz spacing";
               }
               enum "1548.54" {
                 description "1548.54 nm/193.596875 THz 3.125GHz spacing";
               }
               enum "1548.51" {
                 description "1548.51 nm/193.600000 THz 3.125/6.25/12.5/100GHz spacing";
               }
               enum "1548.49" {
                 description "1548.49 nm/193.603125 THz 3.125GHz spacing";
               }
               enum "1548.46" {
                 description "1548.46 nm/193.606250 THz 3.125/6.25GHz spacing";
               }
               enum "1548.44" {
                 description "1548.44 nm/193.609375 THz 3.125GHz spacing";
               }
               enum "1548.41" {
                 description "1548.41 nm/193.612500 THz 3.125/6.25/12.5GHz spacing";
               }
               enum "1548.39" {
                 description "1548.39 nm/193.615625 THz 3.125GHz spacing";
               }
               enum "1548.36" {
                 description "1548.36 nm/193.618750 THz 3.125/6.25GHz spacing";
               }
               enum "1548.34" {
                 description "1548.34 nm/193.621875 THz 3.125GHz spacing";
               }
               enum "1548.31" {
                 description "1548.31 nm/193.625000 THz 3.125/6.25/12.5GHz spacing";
               }
               enum "1548.29" {
                 description "1548.29 nm/193.628125 THz 3.125GHz spacing";
               }
               enum "1548.26" {
                 description "1548.26 nm/193.631250 THz 3.125/6.25GHz spacing";
               }
               enum "1548.24" {
                 description "1548.24 nm/193.634375 THz 3.125GHz spacing";
               }
               enum "1548.21" {
                 description "1548.21 nm/193.637500 THz 3.125/6.25/12.5GHz spacing";
               }
               enum "1548.19" {
                 description "1548.19 nm/193.640625 THz 3.125GHz spacing";
               }
               enum "1548.16" {
                 description "1548.16 nm/193.643750 THz 3.125/6.25GHz spacing";
               }
               enum "1548.14" {
                 description "1548.14 nm/193.646875 THz 3.125GHz spacing";
               }
               enum "1548.11" {
                 description "1548.11 nm/193.650000 THz 3.125/6.25/12.5/50/75GHz spacing";
               }
               enum "1548.09" {
                 description "1548.09 nm/193.653125 THz 3.125GHz spacing";
               }
               enum "1548.06" {
                 description "1548.06 nm/193.656250 THz 3.125/6.25GHz spacing";
               }
               enum "1548.04" {
                 description "1548.04 nm/193.659375 THz 3.125GHz spacing";
               }
               enum "1548.02" {
                 description "1548.02 nm/193.662500 THz 3.125/6.25/12.5GHz spacing";
               }
               enum "1547.99" {
                 description "1547.99 nm/193.665625 THz 3.125GHz spacing";
               }
               enum "1547.97" {
                 description "1547.97 nm/193.668750 THz 3.125/6.25GHz spacing";
               }
               enum "1547.94" {
                 description "1547.94 nm/193.671875 THz 3.125GHz spacing";
               }
               enum "1547.92" {
                 description "1547.92 nm/193.675000 THz 3.125/6.25/12.5GHz spacing";
               }
               enum "1547.89" {
                 description "1547.89 nm/193.678125 THz 3.125GHz spacing";
               }
               enum "1547.87" {
                 description "1547.87 nm/193.681250 THz 3.125/6.25GHz spacing";
               }
               enum "1547.84" {
                 description "1547.84 nm/193.684375 THz 3.125GHz spacing";
               }
               enum "1547.82" {
                 description "1547.82 nm/193.687500 THz 3.125/6.25/12.5GHz spacing";
               }
               enum "1547.79" {
                 description "1547.79 nm/193.690625 THz 3.125GHz spacing";
               }
               enum "1547.77" {
                 description "1547.77 nm/193.693750 THz 3.125/6.25GHz spacing";
               }
               enum "1547.74" {
                 description "1547.74 nm/193.696875 THz 3.125GHz spacing";
               }
               enum "1547.72" {
                 description "1547.72 nm/193.700000 THz 3.125/6.25/12.5/100GHz spacing";
               }
               enum "1547.69" {
                 description "1547.69 nm/193.703125 THz 3.125GHz spacing";
               }
               enum "1547.67" {
                 description "1547.67 nm/193.706250 THz 3.125/6.25GHz spacing";
               }
               enum "1547.64" {
                 description "1547.64 nm/193.709375 THz 3.125GHz spacing";
               }
               enum "1547.62" {
                 description "1547.62 nm/193.712500 THz 3.125/6.25/12.5GHz spacing";
               }
               enum "1547.59" {
                 description "1547.59 nm/193.715625 THz 3.125GHz spacing";
               }
               enum "1547.57" {
                 description "1547.57 nm/193.718750 THz 3.125/6.25GHz spacing";
               }
               enum "1547.54" {
                 description "1547.54 nm/193.721875 THz 3.125GHz spacing";
               }
               enum "1547.52" {
                 description "1547.52 nm/193.725000 THz 3.125/6.25/12.5/75GHz spacing";
               }
               enum "1547.49" {
                 description "1547.49 nm/193.728125 THz 3.125GHz spacing";
               }
               enum "1547.47" {
                 description "1547.47 nm/193.731250 THz 3.125/6.25GHz spacing";
               }
               enum "1547.44" {
                 description "1547.44 nm/193.734375 THz 3.125GHz spacing";
               }
               enum "1547.42" {
                 description "1547.42 nm/193.737500 THz 3.125/6.25/12.5GHz spacing";
               }
               enum "1547.39" {
                 description "1547.39 nm/193.740625 THz 3.125GHz spacing";
               }
               enum "1547.37" {
                 description "1547.37 nm/193.743750 THz 3.125/6.25GHz spacing";
               }
               enum "1547.34" {
                 description "1547.34 nm/193.746875 THz 3.125GHz spacing";
               }
               enum "1547.32" {
                 description "1547.32 nm/193.750000 THz 3.125/6.25/12.5/50GHz spacing";
               }
               enum "1547.29" {
                 description "1547.29 nm/193.753125 THz 3.125GHz spacing";
               }
               enum "1547.27" {
                 description "1547.27 nm/193.756250 THz 3.125/6.25GHz spacing";
               }
               enum "1547.24" {
                 description "1547.24 nm/193.759375 THz 3.125GHz spacing";
               }
               enum "1547.22" {
                 description "1547.22 nm/193.762500 THz 3.125/6.25/12.5GHz spacing";
               }
               enum "1547.19" {
                 description "1547.19 nm/193.765625 THz 3.125GHz spacing";
               }
               enum "1547.17" {
                 description "1547.17 nm/193.768750 THz 3.125/6.25GHz spacing";
               }
               enum "1547.14" {
                 description "1547.14 nm/193.771875 THz 3.125GHz spacing";
               }
               enum "1547.12" {
                 description "1547.12 nm/193.775000 THz 3.125/6.25/12.5GHz spacing";
               }
               enum "1547.09" {
                 description "1547.09 nm/193.778125 THz 3.125GHz spacing";
               }
               enum "1547.07" {
                 description "1547.07 nm/193.781250 THz 3.125/6.25GHz spacing";
               }
               enum "1547.04" {
                 description "1547.04 nm/193.784375 THz 3.125GHz spacing";
               }
               enum "1547.02" {
                 description "1547.02 nm/193.787500 THz 3.125/6.25/12.5GHz spacing";
               }
               enum "1546.99" {
                 description "1546.99 nm/193.790625 THz 3.125GHz spacing";
               }
               enum "1546.97" {
                 description "1546.97 nm/193.793750 THz 3.125/6.25GHz spacing";
               }
               enum "1546.94" {
                 description "1546.94 nm/193.796875 THz 3.125GHz spacing";
               }
               enum "1546.92" {
                 description "1546.92 nm/193.800000 THz 3.125/6.25/12.5/50/75/100GHz spacing";
               }
               enum "1546.89" {
                 description "1546.89 nm/193.803125 THz 3.125GHz spacing";
               }
               enum "1546.87" {
                 description "1546.87 nm/193.806250 THz 3.125/6.25GHz spacing";
               }
               enum "1546.84" {
                 description "1546.84 nm/193.809375 THz 3.125GHz spacing";
               }
               enum "1546.82" {
                 description "1546.82 nm/193.812500 THz 3.125/6.25/12.5GHz spacing";
               }
               enum "1546.79" {
                 description "1546.79 nm/193.815625 THz 3.125GHz spacing";
               }
               enum "1546.77" {
                 description "1546.77 nm/193.818750 THz 3.125/6.25GHz spacing";
               }
               enum "1546.74" {
                 description "1546.74 nm/193.821875 THz 3.125GHz spacing";
               }
               enum "1546.72" {
                 description "1546.72 nm/193.825000 THz 3.125/6.25/12.5GHz spacing";
               }
               enum "1546.69" {
                 description "1546.69 nm/193.828125 THz 3.125GHz spacing";
               }
               enum "1546.67" {
                 description "1546.67 nm/193.831250 THz 3.125/6.25GHz spacing";
               }
               enum "1546.64" {
                 description "1546.64 nm/193.834375 THz 3.125GHz spacing";
               }
               enum "1546.62" {
                 description "1546.62 nm/193.837500 THz 3.125/6.25/12.5GHz spacing";
               }
               enum "1546.59" {
                 description "1546.59 nm/193.840625 THz 3.125GHz spacing";
               }
               enum "1546.57" {
                 description "1546.57 nm/193.843750 THz 3.125/6.25GHz spacing";
               }
               enum "1546.54" {
                 description "1546.54 nm/193.846875 THz 3.125GHz spacing";
               }
               enum "1546.52" {
                 description "1546.52 nm/193.850000 THz 3.125/6.25/12.5/50GHz spacing";
               }
               enum "1546.49" {
                 description "1546.49 nm/193.853125 THz 3.125GHz spacing";
               }
               enum "1546.47" {
                 description "1546.47 nm/193.856250 THz 3.125/6.25GHz spacing";
               }
               enum "1546.44" {
                 description "1546.44 nm/193.859375 THz 3.125GHz spacing";
               }
               enum "1546.42" {
                 description "1546.42 nm/193.862500 THz 3.125/6.25/12.5GHz spacing";
               }
               enum "1546.39" {
                 description "1546.39 nm/193.865625 THz 3.125GHz spacing";
               }
               enum "1546.37" {
                 description "1546.37 nm/193.868750 THz 3.125/6.25GHz spacing";
               }
               enum "1546.34" {
                 description "1546.34 nm/193.871875 THz 3.125GHz spacing";
               }
               enum "1546.32" {
                 description "1546.32 nm/193.875000 THz 3.125/6.25/12.5/75GHz spacing";
               }
               enum "1546.29" {
                 description "1546.29 nm/193.878125 THz 3.125GHz spacing";
               }
               enum "1546.27" {
                 description "1546.27 nm/193.881250 THz 3.125/6.25GHz spacing";
               }
               enum "1546.24" {
                 description "1546.24 nm/193.884375 THz 3.125GHz spacing";
               }
               enum "1546.22" {
                 description "1546.22 nm/193.887500 THz 3.125/6.25/12.5GHz spacing";
               }
               enum "1546.19" {
                 description "1546.19 nm/193.890625 THz 3.125GHz spacing";
               }
               enum "1546.17" {
                 description "1546.17 nm/193.893750 THz 3.125/6.25GHz spacing";
               }
               enum "1546.14" {
                 description "1546.14 nm/193.896875 THz 3.125GHz spacing";
               }
               enum "1546.12" {
                 description "1546.12 nm/193.900000 THz 3.125/6.25/12.5/100GHz spacing";
               }
               enum "1546.09" {
                 description "1546.09 nm/193.903125 THz 3.125GHz spacing";
               }
               enum "1546.07" {
                 description "1546.07 nm/193.906250 THz 3.125/6.25GHz spacing";
               }
               enum "1546.04" {
                 description "1546.04 nm/193.909375 THz 3.125GHz spacing";
               }
               enum "1546.02" {
                 description "1546.02 nm/193.912500 THz 3.125/6.25/12.5GHz spacing";
               }
               enum "1545.99" {
                 description "1545.99 nm/193.915625 THz 3.125GHz spacing";
               }
               enum "1545.97" {
                 description "1545.97 nm/193.918750 THz 3.125/6.25GHz spacing";
               }
               enum "1545.94" {
                 description "1545.94 nm/193.921875 THz 3.125GHz spacing";
               }
               enum "1545.92" {
                 description "1545.92 nm/193.925000 THz 3.125/6.25/12.5GHz spacing";
               }
               enum "1545.89" {
                 description "1545.89 nm/193.928125 THz 3.125GHz spacing";
               }
               enum "1545.87" {
                 description "1545.87 nm/193.931250 THz 3.125/6.25GHz spacing";
               }
               enum "1545.84" {
                 description "1545.84 nm/193.934375 THz 3.125GHz spacing";
               }
               enum "1545.82" {
                 description "1545.82 nm/193.937500 THz 3.125/6.25/12.5GHz spacing";
               }
               enum "1545.80" {
                 description "1545.80 nm/193.940625 THz 3.125GHz spacing";
               }
               enum "1545.77" {
                 description "1545.77 nm/193.943750 THz 3.125/6.25GHz spacing";
               }
               enum "1545.75" {
                 description "1545.75 nm/193.946875 THz 3.125GHz spacing";
               }
               enum "1545.72" {
                 description "1545.72 nm/193.950000 THz 3.125/6.25/12.5/50/75GHz spacing";
               }
               enum "1545.70" {
                 description "1545.70 nm/193.953125 THz 3.125GHz spacing";
               }
               enum "1545.67" {
                 description "1545.67 nm/193.956250 THz 3.125/6.25GHz spacing";
               }
               enum "1545.65" {
                 description "1545.65 nm/193.959375 THz 3.125GHz spacing";
               }
               enum "1545.62" {
                 description "1545.62 nm/193.962500 THz 3.125/6.25/12.5GHz spacing";
               }
               enum "1545.60" {
                 description "1545.60 nm/193.965625 THz 3.125GHz spacing";
               }
               enum "1545.57" {
                 description "1545.57 nm/193.968750 THz 3.125/6.25GHz spacing";
               }
               enum "1545.55" {
                 description "1545.55 nm/193.971875 THz 3.125GHz spacing";
               }
               enum "1545.52" {
                 description "1545.52 nm/193.975000 THz 3.125/6.25/12.5GHz spacing";
               }
               enum "1545.50" {
                 description "1545.50 nm/193.978125 THz 3.125GHz spacing";
               }
               enum "1545.47" {
                 description "1545.47 nm/193.981250 THz 3.125/6.25GHz spacing";
               }
               enum "1545.45" {
                 description "1545.45 nm/193.984375 THz 3.125GHz spacing";
               }
               enum "1545.42" {
                 description "1545.42 nm/193.987500 THz 3.125/6.25/12.5GHz spacing";
               }
               enum "1545.40" {
                 description "1545.40 nm/193.990625 THz 3.125GHz spacing";
               }
               enum "1545.37" {
                 description "1545.37 nm/193.993750 THz 3.125/6.25GHz spacing";
               }
               enum "1545.35" {
                 description "1545.35 nm/193.996875 THz 3.125GHz spacing";
               }
               enum "1545.32" {
                 description "1545.32 nm/194.000000 THz 3.125/6.25/12.5/100GHz spacing";
               }
               enum "1545.30" {
                 description "1545.30 nm/194.003125 THz 3.125GHz spacing";
               }
               enum "1545.27" {
                 description "1545.27 nm/194.006250 THz 3.125/6.25GHz spacing";
               }
               enum "1545.25" {
                 description "1545.25 nm/194.009375 THz 3.125GHz spacing";
               }
               enum "1545.22" {
                 description "1545.22 nm/194.012500 THz 3.125/6.25/12.5GHz spacing";
               }
               enum "1545.20" {
                 description "1545.20 nm/194.015625 THz 3.125GHz spacing";
               }
               enum "1545.17" {
                 description "1545.17 nm/194.018750 THz 3.125/6.25GHz spacing";
               }
               enum "1545.15" {
                 description "1545.15 nm/194.021875 THz 3.125GHz spacing";
               }
               enum "1545.12" {
                 description "1545.12 nm/194.025000 THz 3.125/6.25/12.5/75GHz spacing";
               }
               enum "1545.10" {
                 description "1545.10 nm/194.028125 THz 3.125GHz spacing";
               }
               enum "1545.07" {
                 description "1545.07 nm/194.031250 THz 3.125/6.25GHz spacing";
               }
               enum "1545.05" {
                 description "1545.05 nm/194.034375 THz 3.125GHz spacing";
               }
               enum "1545.02" {
                 description "1545.02 nm/194.037500 THz 3.125/6.25/12.5GHz spacing";
               }
               enum "1545.00" {
                 description "1545.00 nm/194.040625 THz 3.125GHz spacing";
               }
               enum "1544.97" {
                 description "1544.97 nm/194.043750 THz 3.125/6.25GHz spacing";
               }
               enum "1544.95" {
                 description "1544.95 nm/194.046875 THz 3.125GHz spacing";
               }
               enum "1544.92" {
                 description "1544.92 nm/194.050000 THz 3.125/6.25/12.5/50GHz spacing";
               }
               enum "1544.90" {
                 description "1544.90 nm/194.053125 THz 3.125GHz spacing";
               }
               enum "1544.87" {
                 description "1544.87 nm/194.056250 THz 3.125/6.25GHz spacing";
               }
               enum "1544.85" {
                 description "1544.85 nm/194.059375 THz 3.125GHz spacing";
               }
               enum "1544.82" {
                 description "1544.82 nm/194.062500 THz 3.125/6.25/12.5GHz spacing";
               }
               enum "1544.80" {
                 description "1544.80 nm/194.065625 THz 3.125GHz spacing";
               }
               enum "1544.77" {
                 description "1544.77 nm/194.068750 THz 3.125/6.25GHz spacing";
               }
               enum "1544.75" {
                 description "1544.75 nm/194.071875 THz 3.125GHz spacing";
               }
               enum "1544.72" {
                 description "1544.72 nm/194.075000 THz 3.125/6.25/12.5GHz spacing";
               }
               enum "1544.70" {
                 description "1544.70 nm/194.078125 THz 3.125GHz spacing";
               }
               enum "1544.68" {
                 description "1544.68 nm/194.081250 THz 3.125/6.25GHz spacing";
               }
               enum "1544.65" {
                 description "1544.65 nm/194.084375 THz 3.125GHz spacing";
               }
               enum "1544.63" {
                 description "1544.63 nm/194.087500 THz 3.125/6.25/12.5GHz spacing";
               }
               enum "1544.60" {
                 description "1544.60 nm/194.090625 THz 3.125GHz spacing";
               }
               enum "1544.58" {
                 description "1544.58 nm/194.093750 THz 3.125/6.25GHz spacing";
               }
               enum "1544.55" {
                 description "1544.55 nm/194.096875 THz 3.125GHz spacing";
               }
               enum "1544.53" {
                 description "1544.53 nm/194.100000 THz 3.125/6.25/12.5/50/75/100GHz spacing";
               }
               enum "1544.50" {
                 description "1544.50 nm/194.103125 THz 3.125GHz spacing";
               }
               enum "1544.48" {
                 description "1544.48 nm/194.106250 THz 3.125/6.25GHz spacing";
               }
               enum "1544.45" {
                 description "1544.45 nm/194.109375 THz 3.125GHz spacing";
               }
               enum "1544.43" {
                 description "1544.43 nm/194.112500 THz 3.125/6.25/12.5GHz spacing";
               }
               enum "1544.40" {
                 description "1544.40 nm/194.115625 THz 3.125GHz spacing";
               }
               enum "1544.38" {
                 description "1544.38 nm/194.118750 THz 3.125/6.25GHz spacing";
               }
               enum "1544.35" {
                 description "1544.35 nm/194.121875 THz 3.125GHz spacing";
               }
               enum "1544.33" {
                 description "1544.33 nm/194.125000 THz 3.125/6.25/12.5GHz spacing";
               }
               enum "1544.30" {
                 description "1544.30 nm/194.128125 THz 3.125GHz spacing";
               }
               enum "1544.28" {
                 description "1544.28 nm/194.131250 THz 3.125/6.25GHz spacing";
               }
               enum "1544.25" {
                 description "1544.25 nm/194.134375 THz 3.125GHz spacing";
               }
               enum "1544.23" {
                 description "1544.23 nm/194.137500 THz 3.125/6.25/12.5GHz spacing";
               }
               enum "1544.20" {
                 description "1544.20 nm/194.140625 THz 3.125GHz spacing";
               }
               enum "1544.18" {
                 description "1544.18 nm/194.143750 THz 3.125/6.25GHz spacing";
               }
               enum "1544.15" {
                 description "1544.15 nm/194.146875 THz 3.125GHz spacing";
               }
               enum "1544.13" {
                 description "1544.13 nm/194.150000 THz 3.125/6.25/12.5/50GHz spacing";
               }
               enum "1544.10" {
                 description "1544.10 nm/194.153125 THz 3.125GHz spacing";
               }
               enum "1544.08" {
                 description "1544.08 nm/194.156250 THz 3.125/6.25GHz spacing";
               }
               enum "1544.05" {
                 description "1544.05 nm/194.159375 THz 3.125GHz spacing";
               }
               enum "1544.03" {
                 description "1544.03 nm/194.162500 THz 3.125/6.25/12.5GHz spacing";
               }
               enum "1544.00" {
                 description "1544.00 nm/194.165625 THz 3.125GHz spacing";
               }
               enum "1543.98" {
                 description "1543.98 nm/194.168750 THz 3.125/6.25GHz spacing";
               }
               enum "1543.95" {
                 description "1543.95 nm/194.171875 THz 3.125GHz spacing";
               }
               enum "1543.93" {
                 description "1543.93 nm/194.175000 THz 3.125/6.25/12.5/75GHz spacing";
               }
               enum "1543.90" {
                 description "1543.90 nm/194.178125 THz 3.125GHz spacing";
               }
               enum "1543.88" {
                 description "1543.88 nm/194.181250 THz 3.125/6.25GHz spacing";
               }
               enum "1543.85" {
                 description "1543.85 nm/194.184375 THz 3.125GHz spacing";
               }
               enum "1543.83" {
                 description "1543.83 nm/194.187500 THz 3.125/6.25/12.5GHz spacing";
               }
               enum "1543.81" {
                 description "1543.81 nm/194.190625 THz 3.125GHz spacing";
               }
               enum "1543.78" {
                 description "1543.78 nm/194.193750 THz 3.125/6.25GHz spacing";
               }
               enum "1543.76" {
                 description "1543.76 nm/194.196875 THz 3.125GHz spacing";
               }
               enum "1543.73" {
                 description "1543.73 nm/194.200000 THz 3.125/6.25/12.5/100GHz spacing";
               }
               enum "1543.71" {
                 description "1543.71 nm/194.203125 THz 3.125GHz spacing";
               }
               enum "1543.68" {
                 description "1543.68 nm/194.206250 THz 3.125/6.25GHz spacing";
               }
               enum "1543.66" {
                 description "1543.66 nm/194.209375 THz 3.125GHz spacing";
               }
               enum "1543.63" {
                 description "1543.63 nm/194.212500 THz 3.125/6.25/12.5GHz spacing";
               }
               enum "1543.61" {
                 description "1543.61 nm/194.215625 THz 3.125GHz spacing";
               }
               enum "1543.58" {
                 description "1543.58 nm/194.218750 THz 3.125/6.25GHz spacing";
               }
               enum "1543.56" {
                 description "1543.56 nm/194.221875 THz 3.125GHz spacing";
               }
               enum "1543.53" {
                 description "1543.53 nm/194.225000 THz 3.125/6.25/12.5GHz spacing";
               }
               enum "1543.51" {
                 description "1543.51 nm/194.228125 THz 3.125GHz spacing";
               }
               enum "1543.48" {
                 description "1543.48 nm/194.231250 THz 3.125/6.25GHz spacing";
               }
               enum "1543.46" {
                 description "1543.46 nm/194.234375 THz 3.125GHz spacing";
               }
               enum "1543.43" {
                 description "1543.43 nm/194.237500 THz 3.125/6.25/12.5GHz spacing";
               }
               enum "1543.41" {
                 description "1543.41 nm/194.240625 THz 3.125GHz spacing";
               }
               enum "1543.38" {
                 description "1543.38 nm/194.243750 THz 3.125/6.25GHz spacing";
               }
               enum "1543.36" {
                 description "1543.36 nm/194.246875 THz 3.125GHz spacing";
               }
               enum "1543.33" {
                 description "1543.33 nm/194.250000 THz 3.125/6.25/12.5/50/75GHz spacing";
               }
               enum "1543.31" {
                 description "1543.31 nm/194.253125 THz 3.125GHz spacing";
               }
               enum "1543.28" {
                 description "1543.28 nm/194.256250 THz 3.125/6.25GHz spacing";
               }
               enum "1543.26" {
                 description "1543.26 nm/194.259375 THz 3.125GHz spacing";
               }
               enum "1543.23" {
                 description "1543.23 nm/194.262500 THz 3.125/6.25/12.5GHz spacing";
               }
               enum "1543.21" {
                 description "1543.21 nm/194.265625 THz 3.125GHz spacing";
               }
               enum "1543.18" {
                 description "1543.18 nm/194.268750 THz 3.125/6.25GHz spacing";
               }
               enum "1543.16" {
                 description "1543.16 nm/194.271875 THz 3.125GHz spacing";
               }
               enum "1543.13" {
                 description "1543.13 nm/194.275000 THz 3.125/6.25/12.5GHz spacing";
               }
               enum "1543.11" {
                 description "1543.11 nm/194.278125 THz 3.125GHz spacing";
               }
               enum "1543.08" {
                 description "1543.08 nm/194.281250 THz 3.125/6.25GHz spacing";
               }
               enum "1543.06" {
                 description "1543.06 nm/194.284375 THz 3.125GHz spacing";
               }
               enum "1543.04" {
                 description "1543.04 nm/194.287500 THz 3.125/6.25/12.5GHz spacing";
               }
               enum "1543.01" {
                 description "1543.01 nm/194.290625 THz 3.125GHz spacing";
               }
               enum "1542.99" {
                 description "1542.99 nm/194.293750 THz 3.125/6.25GHz spacing";
               }
               enum "1542.96" {
                 description "1542.96 nm/194.296875 THz 3.125GHz spacing";
               }
               enum "1542.94" {
                 description "1542.94 nm/194.300000 THz 3.125/6.25/12.5/100GHz spacing";
               }
               enum "1542.91" {
                 description "1542.91 nm/194.303125 THz 3.125GHz spacing";
               }
               enum "1542.89" {
                 description "1542.89 nm/194.306250 THz 3.125/6.25GHz spacing";
               }
               enum "1542.86" {
                 description "1542.86 nm/194.309375 THz 3.125GHz spacing";
               }
               enum "1542.84" {
                 description "1542.84 nm/194.312500 THz 3.125/6.25/12.5GHz spacing";
               }
               enum "1542.81" {
                 description "1542.81 nm/194.315625 THz 3.125GHz spacing";
               }
               enum "1542.79" {
                 description "1542.79 nm/194.318750 THz 3.125/6.25GHz spacing";
               }
               enum "1542.76" {
                 description "1542.76 nm/194.321875 THz 3.125GHz spacing";
               }
               enum "1542.74" {
                 description "1542.74 nm/194.325000 THz 3.125/6.25/12.5/75GHz spacing";
               }
               enum "1542.71" {
                 description "1542.71 nm/194.328125 THz 3.125GHz spacing";
               }
               enum "1542.69" {
                 description "1542.69 nm/194.331250 THz 3.125/6.25GHz spacing";
               }
               enum "1542.66" {
                 description "1542.66 nm/194.334375 THz 3.125GHz spacing";
               }
               enum "1542.64" {
                 description "1542.64 nm/194.337500 THz 3.125/6.25/12.5GHz spacing";
               }
               enum "1542.61" {
                 description "1542.61 nm/194.340625 THz 3.125GHz spacing";
               }
               enum "1542.59" {
                 description "1542.59 nm/194.343750 THz 3.125/6.25GHz spacing";
               }
               enum "1542.56" {
                 description "1542.56 nm/194.346875 THz 3.125GHz spacing";
               }
               enum "1542.54" {
                 description "1542.54 nm/194.350000 THz 3.125/6.25/12.5/50GHz spacing";
               }
               enum "1542.51" {
                 description "1542.51 nm/194.353125 THz 3.125GHz spacing";
               }
               enum "1542.49" {
                 description "1542.49 nm/194.356250 THz 3.125/6.25GHz spacing";
               }
               enum "1542.46" {
                 description "1542.46 nm/194.359375 THz 3.125GHz spacing";
               }
               enum "1542.44" {
                 description "1542.44 nm/194.362500 THz 3.125/6.25/12.5GHz spacing";
               }
               enum "1542.42" {
                 description "1542.42 nm/194.365625 THz 3.125GHz spacing";
               }
               enum "1542.39" {
                 description "1542.39 nm/194.368750 THz 3.125/6.25GHz spacing";
               }
               enum "1542.37" {
                 description "1542.37 nm/194.371875 THz 3.125GHz spacing";
               }
               enum "1542.34" {
                 description "1542.34 nm/194.375000 THz 3.125/6.25/12.5GHz spacing";
               }
               enum "1542.32" {
                 description "1542.32 nm/194.378125 THz 3.125GHz spacing";
               }
               enum "1542.29" {
                 description "1542.29 nm/194.381250 THz 3.125/6.25GHz spacing";
               }
               enum "1542.27" {
                 description "1542.27 nm/194.384375 THz 3.125GHz spacing";
               }
               enum "1542.24" {
                 description "1542.24 nm/194.387500 THz 3.125/6.25/12.5GHz spacing";
               }
               enum "1542.22" {
                 description "1542.22 nm/194.390625 THz 3.125GHz spacing";
               }
               enum "1542.19" {
                 description "1542.19 nm/194.393750 THz 3.125/6.25GHz spacing";
               }
               enum "1542.17" {
                 description "1542.17 nm/194.396875 THz 3.125GHz spacing";
               }
               enum "1542.14" {
                 description "1542.14 nm/194.400000 THz 3.125/6.25/12.5/50/75/100GHz spacing";
               }
               enum "1542.12" {
                 description "1542.12 nm/194.403125 THz 3.125GHz spacing";
               }
               enum "1542.09" {
                 description "1542.09 nm/194.406250 THz 3.125/6.25GHz spacing";
               }
               enum "1542.07" {
                 description "1542.07 nm/194.409375 THz 3.125GHz spacing";
               }
               enum "1542.04" {
                 description "1542.04 nm/194.412500 THz 3.125/6.25/12.5GHz spacing";
               }
               enum "1542.02" {
                 description "1542.02 nm/194.415625 THz 3.125GHz spacing";
               }
               enum "1541.99" {
                 description "1541.99 nm/194.418750 THz 3.125/6.25GHz spacing";
               }
               enum "1541.97" {
                 description "1541.97 nm/194.421875 THz 3.125GHz spacing";
               }
               enum "1541.94" {
                 description "1541.94 nm/194.425000 THz 3.125/6.25/12.5GHz spacing";
               }
               enum "1541.92" {
                 description "1541.92 nm/194.428125 THz 3.125GHz spacing";
               }
               enum "1541.89" {
                 description "1541.89 nm/194.431250 THz 3.125/6.25GHz spacing";
               }
               enum "1541.87" {
                 description "1541.87 nm/194.434375 THz 3.125GHz spacing";
               }
               enum "1541.84" {
                 description "1541.84 nm/194.437500 THz 3.125/6.25/12.5GHz spacing";
               }
               enum "1541.82" {
                 description "1541.82 nm/194.440625 THz 3.125GHz spacing";
               }
               enum "1541.80" {
                 description "1541.80 nm/194.443750 THz 3.125/6.25GHz spacing";
               }
               enum "1541.77" {
                 description "1541.77 nm/194.446875 THz 3.125GHz spacing";
               }
               enum "1541.75" {
                 description "1541.75 nm/194.450000 THz 3.125/6.25/12.5/50GHz spacing";
               }
               enum "1541.72" {
                 description "1541.72 nm/194.453125 THz 3.125GHz spacing";
               }
               enum "1541.70" {
                 description "1541.70 nm/194.456250 THz 3.125/6.25GHz spacing";
               }
               enum "1541.67" {
                 description "1541.67 nm/194.459375 THz 3.125GHz spacing";
               }
               enum "1541.65" {
                 description "1541.65 nm/194.462500 THz 3.125/6.25/12.5GHz spacing";
               }
               enum "1541.62" {
                 description "1541.62 nm/194.465625 THz 3.125GHz spacing";
               }
               enum "1541.60" {
                 description "1541.60 nm/194.468750 THz 3.125/6.25GHz spacing";
               }
               enum "1541.57" {
                 description "1541.57 nm/194.471875 THz 3.125GHz spacing";
               }
               enum "1541.55" {
                 description "1541.55 nm/194.475000 THz 3.125/6.25/12.5/75GHz spacing";
               }
               enum "1541.52" {
                 description "1541.52 nm/194.478125 THz 3.125GHz spacing";
               }
               enum "1541.50" {
                 description "1541.50 nm/194.481250 THz 3.125/6.25GHz spacing";
               }
               enum "1541.47" {
                 description "1541.47 nm/194.484375 THz 3.125GHz spacing";
               }
               enum "1541.45" {
                 description "1541.45 nm/194.487500 THz 3.125/6.25/12.5GHz spacing";
               }
               enum "1541.42" {
                 description "1541.42 nm/194.490625 THz 3.125GHz spacing";
               }
               enum "1541.40" {
                 description "1541.40 nm/194.493750 THz 3.125/6.25GHz spacing";
               }
               enum "1541.37" {
                 description "1541.37 nm/194.496875 THz 3.125GHz spacing";
               }
               enum "1541.35" {
                 description "1541.35 nm/194.500000 THz 3.125/6.25/12.5/100GHz spacing";
               }
               enum "1541.32" {
                 description "1541.32 nm/194.503125 THz 3.125GHz spacing";
               }
               enum "1541.30" {
                 description "1541.30 nm/194.506250 THz 3.125/6.25GHz spacing";
               }
               enum "1541.28" {
                 description "1541.28 nm/194.509375 THz 3.125GHz spacing";
               }
               enum "1541.25" {
                 description "1541.25 nm/194.512500 THz 3.125/6.25/12.5GHz spacing";
               }
               enum "1541.23" {
                 description "1541.23 nm/194.515625 THz 3.125GHz spacing";
               }
               enum "1541.20" {
                 description "1541.20 nm/194.518750 THz 3.125/6.25GHz spacing";
               }
               enum "1541.18" {
                 description "1541.18 nm/194.521875 THz 3.125GHz spacing";
               }
               enum "1541.15" {
                 description "1541.15 nm/194.525000 THz 3.125/6.25/12.5GHz spacing";
               }
               enum "1541.13" {
                 description "1541.13 nm/194.528125 THz 3.125GHz spacing";
               }
               enum "1541.10" {
                 description "1541.10 nm/194.531250 THz 3.125/6.25GHz spacing";
               }
               enum "1541.08" {
                 description "1541.08 nm/194.534375 THz 3.125GHz spacing";
               }
               enum "1541.05" {
                 description "1541.05 nm/194.537500 THz 3.125/6.25/12.5GHz spacing";
               }
               enum "1541.03" {
                 description "1541.03 nm/194.540625 THz 3.125GHz spacing";
               }
               enum "1541.00" {
                 description "1541.00 nm/194.543750 THz 3.125/6.25GHz spacing";
               }
               enum "1540.98" {
                 description "1540.98 nm/194.546875 THz 3.125GHz spacing";
               }
               enum "1540.95" {
                 description "1540.95 nm/194.550000 THz 3.125/6.25/12.5/50/75GHz spacing";
               }
               enum "1540.93" {
                 description "1540.93 nm/194.553125 THz 3.125GHz spacing";
               }
               enum "1540.90" {
                 description "1540.90 nm/194.556250 THz 3.125/6.25GHz spacing";
               }
               enum "1540.88" {
                 description "1540.88 nm/194.559375 THz 3.125GHz spacing";
               }
               enum "1540.85" {
                 description "1540.85 nm/194.562500 THz 3.125/6.25/12.5GHz spacing";
               }
               enum "1540.83" {
                 description "1540.83 nm/194.565625 THz 3.125GHz spacing";
               }
               enum "1540.80" {
                 description "1540.80 nm/194.568750 THz 3.125/6.25GHz spacing";
               }
               enum "1540.78" {
                 description "1540.78 nm/194.571875 THz 3.125GHz spacing";
               }
               enum "1540.76" {
                 description "1540.76 nm/194.575000 THz 3.125/6.25/12.5GHz spacing";
               }
               enum "1540.73" {
                 description "1540.73 nm/194.578125 THz 3.125GHz spacing";
               }
               enum "1540.71" {
                 description "1540.71 nm/194.581250 THz 3.125/6.25GHz spacing";
               }
               enum "1540.68" {
                 description "1540.68 nm/194.584375 THz 3.125GHz spacing";
               }
               enum "1540.66" {
                 description "1540.66 nm/194.587500 THz 3.125/6.25/12.5GHz spacing";
               }
               enum "1540.63" {
                 description "1540.63 nm/194.590625 THz 3.125GHz spacing";
               }
               enum "1540.61" {
                 description "1540.61 nm/194.593750 THz 3.125/6.25GHz spacing";
               }
               enum "1540.58" {
                 description "1540.58 nm/194.596875 THz 3.125GHz spacing";
               }
               enum "1540.56" {
                 description "1540.56 nm/194.600000 THz 3.125/6.25/12.5/100GHz spacing";
               }
               enum "1540.53" {
                 description "1540.53 nm/194.603125 THz 3.125GHz spacing";
               }
               enum "1540.51" {
                 description "1540.51 nm/194.606250 THz 3.125/6.25GHz spacing";
               }
               enum "1540.48" {
                 description "1540.48 nm/194.609375 THz 3.125GHz spacing";
               }
               enum "1540.46" {
                 description "1540.46 nm/194.612500 THz 3.125/6.25/12.5GHz spacing";
               }
               enum "1540.43" {
                 description "1540.43 nm/194.615625 THz 3.125GHz spacing";
               }
               enum "1540.41" {
                 description "1540.41 nm/194.618750 THz 3.125/6.25GHz spacing";
               }
               enum "1540.38" {
                 description "1540.38 nm/194.621875 THz 3.125GHz spacing";
               }
               enum "1540.36" {
                 description "1540.36 nm/194.625000 THz 3.125/6.25/12.5/75GHz spacing";
               }
               enum "1540.33" {
                 description "1540.33 nm/194.628125 THz 3.125GHz spacing";
               }
               enum "1540.31" {
                 description "1540.31 nm/194.631250 THz 3.125/6.25GHz spacing";
               }
               enum "1540.29" {
                 description "1540.29 nm/194.634375 THz 3.125GHz spacing";
               }
               enum "1540.26" {
                 description "1540.26 nm/194.637500 THz 3.125/6.25/12.5GHz spacing";
               }
               enum "1540.24" {
                 description "1540.24 nm/194.640625 THz 3.125GHz spacing";
               }
               enum "1540.21" {
                 description "1540.21 nm/194.643750 THz 3.125/6.25GHz spacing";
               }
               enum "1540.19" {
                 description "1540.19 nm/194.646875 THz 3.125GHz spacing";
               }
               enum "1540.16" {
                 description "1540.16 nm/194.650000 THz 3.125/6.25/12.5/50GHz spacing";
               }
               enum "1540.14" {
                 description "1540.14 nm/194.653125 THz 3.125GHz spacing";
               }
               enum "1540.11" {
                 description "1540.11 nm/194.656250 THz 3.125/6.25GHz spacing";
               }
               enum "1540.09" {
                 description "1540.09 nm/194.659375 THz 3.125GHz spacing";
               }
               enum "1540.06" {
                 description "1540.06 nm/194.662500 THz 3.125/6.25/12.5GHz spacing";
               }
               enum "1540.04" {
                 description "1540.04 nm/194.665625 THz 3.125GHz spacing";
               }
               enum "1540.01" {
                 description "1540.01 nm/194.668750 THz 3.125/6.25GHz spacing";
               }
               enum "1539.99" {
                 description "1539.99 nm/194.671875 THz 3.125GHz spacing";
               }
               enum "1539.96" {
                 description "1539.96 nm/194.675000 THz 3.125/6.25/12.5/75GHz spacing";
               }
               enum "1539.94" {
                 description "1539.94 nm/194.678125 THz 3.125GHz spacing";
               }
               enum "1539.91" {
                 description "1539.91 nm/194.681250 THz 3.125/6.25GHz spacing";
               }
               enum "1539.89" {
                 description "1539.89 nm/194.684375 THz 3.125GHz spacing";
               }
               enum "1539.86" {
                 description "1539.86 nm/194.687500 THz 3.125/6.25/12.5GHz spacing";
               }
               enum "1539.84" {
                 description "1539.84 nm/194.690625 THz 3.125GHz spacing";
               }
               enum "1539.82" {
                 description "1539.82 nm/194.693750 THz 3.125/6.25GHz spacing";
               }
               enum "1539.79" {
                 description "1539.79 nm/194.696875 THz 3.125GHz spacing";
               }
               enum "1539.77" {
                 description "1539.77 nm/194.700000 THz 3.125/6.25/12.5/50/75/100GHz spacing";
               }
               enum "1539.74" {
                 description "1539.74 nm/194.703125 THz 3.125GHz spacing";
               }
               enum "1539.72" {
                 description "1539.72 nm/194.706250 THz 3.125/6.25GHz spacing";
               }
               enum "1539.69" {
                 description "1539.69 nm/194.709375 THz 3.125GHz spacing";
               }
               enum "1539.67" {
                 description "1539.67 nm/194.712500 THz 3.125/6.25/12.5GHz spacing";
               }
               enum "1539.64" {
                 description "1539.64 nm/194.715625 THz 3.125GHz spacing";
               }
               enum "1539.62" {
                 description "1539.62 nm/194.718750 THz 3.125/6.25GHz spacing";
               }
               enum "1539.59" {
                 description "1539.59 nm/194.721875 THz 3.125GHz spacing";
               }
               enum "1539.57" {
                 description "1539.57 nm/194.725000 THz 3.125/6.25/12.5GHz spacing";
               }
               enum "1539.54" {
                 description "1539.54 nm/194.728125 THz 3.125GHz spacing";
               }
               enum "1539.52" {
                 description "1539.52 nm/194.731250 THz 3.125/6.25GHz spacing";
               }
               enum "1539.49" {
                 description "1539.49 nm/194.734375 THz 3.125GHz spacing";
               }
               enum "1539.47" {
                 description "1539.47 nm/194.737500 THz 3.125/6.25/12.5GHz spacing";
               }
               enum "1539.44" {
                 description "1539.44 nm/194.740625 THz 3.125GHz spacing";
               }
               enum "1539.42" {
                 description "1539.42 nm/194.743750 THz 3.125/6.25GHz spacing";
               }
               enum "1539.40" {
                 description "1539.40 nm/194.746875 THz 3.125GHz spacing";
               }
               enum "1539.37" {
                 description "1539.37 nm/194.750000 THz 3.125/6.25/12.5/50GHz spacing";
               }
               enum "1539.35" {
                 description "1539.35 nm/194.753125 THz 3.125GHz spacing";
               }
               enum "1539.32" {
                 description "1539.32 nm/194.756250 THz 3.125/6.25GHz spacing";
               }
               enum "1539.30" {
                 description "1539.30 nm/194.759375 THz 3.125GHz spacing";
               }
               enum "1539.27" {
                 description "1539.27 nm/194.762500 THz 3.125/6.25/12.5GHz spacing";
               }
               enum "1539.25" {
                 description "1539.25 nm/194.765625 THz 3.125GHz spacing";
               }
               enum "1539.22" {
                 description "1539.22 nm/194.768750 THz 3.125/6.25GHz spacing";
               }
               enum "1539.20" {
                 description "1539.20 nm/194.771875 THz 3.125GHz spacing";
               }
               enum "1539.17" {
                 description "1539.17 nm/194.775000 THz 3.125/6.25/12.5/75GHz spacing";
               }
               enum "1539.15" {
                 description "1539.15 nm/194.778125 THz 3.125GHz spacing";
               }
               enum "1539.12" {
                 description "1539.12 nm/194.781250 THz 3.125/6.25GHz spacing";
               }
               enum "1539.10" {
                 description "1539.10 nm/194.784375 THz 3.125GHz spacing";
               }
               enum "1539.07" {
                 description "1539.07 nm/194.787500 THz 3.125/6.25/12.5GHz spacing";
               }
               enum "1539.05" {
                 description "1539.05 nm/194.790625 THz 3.125GHz spacing";
               }
               enum "1539.03" {
                 description "1539.03 nm/194.793750 THz 3.125/6.25GHz spacing";
               }
               enum "1539.00" {
                 description "1539.00 nm/194.796875 THz 3.125GHz spacing";
               }
               enum "1538.98" {
                 description "1538.98 nm/194.800000 THz 3.125/6.25/12.5/100GHz spacing";
               }
               enum "1538.95" {
                 description "1538.95 nm/194.803125 THz 3.125GHz spacing";
               }
               enum "1538.93" {
                 description "1538.93 nm/194.806250 THz 3.125/6.25GHz spacing";
               }
               enum "1538.90" {
                 description "1538.90 nm/194.809375 THz 3.125GHz spacing";
               }
               enum "1538.88" {
                 description "1538.88 nm/194.812500 THz 3.125/6.25/12.5GHz spacing";
               }
               enum "1538.85" {
                 description "1538.85 nm/194.815625 THz 3.125GHz spacing";
               }
               enum "1538.83" {
                 description "1538.83 nm/194.818750 THz 3.125/6.25GHz spacing";
               }
               enum "1538.80" {
                 description "1538.80 nm/194.821875 THz 3.125GHz spacing";
               }
               enum "1538.78" {
                 description "1538.78 nm/194.825000 THz 3.125/6.25/12.5GHz spacing";
               }
               enum "1538.75" {
                 description "1538.75 nm/194.828125 THz 3.125GHz spacing";
               }
               enum "1538.73" {
                 description "1538.73 nm/194.831250 THz 3.125/6.25GHz spacing";
               }
               enum "1538.70" {
                 description "1538.70 nm/194.834375 THz 3.125GHz spacing";
               }
               enum "1538.68" {
                 description "1538.68 nm/194.837500 THz 3.125/6.25/12.5GHz spacing";
               }
               enum "1538.65" {
                 description "1538.65 nm/194.840625 THz 3.125GHz spacing";
               }
               enum "1538.63" {
                 description "1538.63 nm/194.843750 THz 3.125/6.25GHz spacing";
               }
               enum "1538.61" {
                 description "1538.61 nm/194.846875 THz 3.125GHz spacing";
               }
               enum "1538.58" {
                 description "1538.58 nm/194.850000 THz 3.125/6.25/12.5/50/75GHz spacing";
               }
               enum "1538.56" {
                 description "1538.56 nm/194.853125 THz 3.125GHz spacing";
               }
               enum "1538.53" {
                 description "1538.53 nm/194.856250 THz 3.125/6.25GHz spacing";
               }
               enum "1538.51" {
                 description "1538.51 nm/194.859375 THz 3.125GHz spacing";
               }
               enum "1538.48" {
                 description "1538.48 nm/194.862500 THz 3.125/6.25/12.5GHz spacing";
               }
               enum "1538.46" {
                 description "1538.46 nm/194.865625 THz 3.125GHz spacing";
               }
               enum "1538.43" {
                 description "1538.43 nm/194.868750 THz 3.125/6.25GHz spacing";
               }
               enum "1538.41" {
                 description "1538.41 nm/194.871875 THz 3.125GHz spacing";
               }
               enum "1538.38" {
                 description "1538.38 nm/194.875000 THz 3.125/6.25/12.5GHz spacing";
               }
               enum "1538.36" {
                 description "1538.36 nm/194.878125 THz 3.125GHz spacing";
               }
               enum "1538.33" {
                 description "1538.33 nm/194.881250 THz 3.125/6.25GHz spacing";
               }
               enum "1538.31" {
                 description "1538.31 nm/194.884375 THz 3.125GHz spacing";
               }
               enum "1538.28" {
                 description "1538.28 nm/194.887500 THz 3.125/6.25/12.5GHz spacing";
               }
               enum "1538.26" {
                 description "1538.26 nm/194.890625 THz 3.125GHz spacing";
               }
               enum "1538.24" {
                 description "1538.24 nm/194.893750 THz 3.125/6.25GHz spacing";
               }
               enum "1538.21" {
                 description "1538.21 nm/194.896875 THz 3.125GHz spacing";
               }
               enum "1538.19" {
                 description "1538.19 nm/194.900000 THz 3.125/6.25/12.5/100GHz spacing";
               }
               enum "1538.16" {
                 description "1538.16 nm/194.903125 THz 3.125GHz spacing";
               }
               enum "1538.14" {
                 description "1538.14 nm/194.906250 THz 3.125/6.25GHz spacing";
               }
               enum "1538.11" {
                 description "1538.11 nm/194.909375 THz 3.125GHz spacing";
               }
               enum "1538.09" {
                 description "1538.09 nm/194.912500 THz 3.125/6.25/12.5GHz spacing";
               }
               enum "1538.06" {
                 description "1538.06 nm/194.915625 THz 3.125GHz spacing";
               }
               enum "1538.04" {
                 description "1538.04 nm/194.918750 THz 3.125/6.25GHz spacing";
               }
               enum "1538.01" {
                 description "1538.01 nm/194.921875 THz 3.125GHz spacing";
               }
               enum "1537.99" {
                 description "1537.99 nm/194.925000 THz 3.125/6.25/12.5/75GHz spacing";
               }
               enum "1537.96" {
                 description "1537.96 nm/194.928125 THz 3.125GHz spacing";
               }
               enum "1537.94" {
                 description "1537.94 nm/194.931250 THz 3.125/6.25GHz spacing";
               }
               enum "1537.91" {
                 description "1537.91 nm/194.934375 THz 3.125GHz spacing";
               }
               enum "1537.89" {
                 description "1537.89 nm/194.937500 THz 3.125/6.25/12.5GHz spacing";
               }
               enum "1537.87" {
                 description "1537.87 nm/194.940625 THz 3.125GHz spacing";
               }
               enum "1537.84" {
                 description "1537.84 nm/194.943750 THz 3.125/6.25GHz spacing";
               }
               enum "1537.82" {
                 description "1537.82 nm/194.946875 THz 3.125GHz spacing";
               }
               enum "1537.79" {
                 description "1537.79 nm/194.950000 THz 3.125/6.25/12.5/50GHz spacing";
               }
               enum "1537.77" {
                 description "1537.77 nm/194.953125 THz 3.125GHz spacing";
               }
               enum "1537.74" {
                 description "1537.74 nm/194.956250 THz 3.125/6.25GHz spacing";
               }
               enum "1537.72" {
                 description "1537.72 nm/194.959375 THz 3.125GHz spacing";
               }
               enum "1537.69" {
                 description "1537.69 nm/194.962500 THz 3.125/6.25/12.5GHz spacing";
               }
               enum "1537.67" {
                 description "1537.67 nm/194.965625 THz 3.125GHz spacing";
               }
               enum "1537.64" {
                 description "1537.64 nm/194.968750 THz 3.125/6.25GHz spacing";
               }
               enum "1537.62" {
                 description "1537.62 nm/194.971875 THz 3.125GHz spacing";
               }
               enum "1537.59" {
                 description "1537.59 nm/194.975000 THz 3.125/6.25/12.5GHz spacing";
               }
               enum "1537.57" {
                 description "1537.57 nm/194.978125 THz 3.125GHz spacing";
               }
               enum "1537.55" {
                 description "1537.55 nm/194.981250 THz 3.125/6.25GHz spacing";
               }
               enum "1537.52" {
                 description "1537.52 nm/194.984375 THz 3.125GHz spacing";
               }
               enum "1537.50" {
                 description "1537.50 nm/194.987500 THz 3.125/6.25/12.5GHz spacing";
               }
               enum "1537.47" {
                 description "1537.47 nm/194.990625 THz 3.125GHz spacing";
               }
               enum "1537.45" {
                 description "1537.45 nm/194.993750 THz 3.125/6.25GHz spacing";
               }
               enum "1537.42" {
                 description "1537.42 nm/194.996875 THz 3.125GHz spacing";
               }
               enum "1537.40" {
                 description "1537.40 nm/195.000000 THz 3.125/6.25/12.5/50/75/100GHz spacing";
               }
               enum "1537.37" {
                 description "1537.37 nm/195.003125 THz 3.125GHz spacing";
               }
               enum "1537.35" {
                 description "1537.35 nm/195.006250 THz 3.125/6.25GHz spacing";
               }
               enum "1537.32" {
                 description "1537.32 nm/195.009375 THz 3.125GHz spacing";
               }
               enum "1537.30" {
                 description "1537.30 nm/195.012500 THz 3.125/6.25/12.5GHz spacing";
               }
               enum "1537.27" {
                 description "1537.27 nm/195.015625 THz 3.125GHz spacing";
               }
               enum "1537.25" {
                 description "1537.25 nm/195.018750 THz 3.125/6.25GHz spacing";
               }
               enum "1537.22" {
                 description "1537.22 nm/195.021875 THz 3.125GHz spacing";
               }
               enum "1537.20" {
                 description "1537.20 nm/195.025000 THz 3.125/6.25/12.5GHz spacing";
               }
               enum "1537.18" {
                 description "1537.18 nm/195.028125 THz 3.125GHz spacing";
               }
               enum "1537.15" {
                 description "1537.15 nm/195.031250 THz 3.125/6.25GHz spacing";
               }
               enum "1537.13" {
                 description "1537.13 nm/195.034375 THz 3.125GHz spacing";
               }
               enum "1537.10" {
                 description "1537.10 nm/195.037500 THz 3.125/6.25/12.5GHz spacing";
               }
               enum "1537.08" {
                 description "1537.08 nm/195.040625 THz 3.125GHz spacing";
               }
               enum "1537.05" {
                 description "1537.05 nm/195.043750 THz 3.125/6.25GHz spacing";
               }
               enum "1537.03" {
                 description "1537.03 nm/195.046875 THz 3.125GHz spacing";
               }
               enum "1537.00" {
                 description "1537.00 nm/195.050000 THz 3.125/6.25/12.5/50GHz spacing";
               }
               enum "1536.98" {
                 description "1536.98 nm/195.053125 THz 3.125GHz spacing";
               }
               enum "1536.95" {
                 description "1536.95 nm/195.056250 THz 3.125/6.25GHz spacing";
               }
               enum "1536.93" {
                 description "1536.93 nm/195.059375 THz 3.125GHz spacing";
               }
               enum "1536.90" {
                 description "1536.90 nm/195.062500 THz 3.125/6.25/12.5GHz spacing";
               }
               enum "1536.88" {
                 description "1536.88 nm/195.065625 THz 3.125GHz spacing";
               }
               enum "1536.86" {
                 description "1536.86 nm/195.068750 THz 3.125/6.25GHz spacing";
               }
               enum "1536.83" {
                 description "1536.83 nm/195.071875 THz 3.125GHz spacing";
               }
               enum "1536.81" {
                 description "1536.81 nm/195.075000 THz 3.125/6.25/12.5/75GHz spacing";
               }
               enum "1536.78" {
                 description "1536.78 nm/195.078125 THz 3.125GHz spacing";
               }
               enum "1536.76" {
                 description "1536.76 nm/195.081250 THz 3.125/6.25GHz spacing";
               }
               enum "1536.73" {
                 description "1536.73 nm/195.084375 THz 3.125GHz spacing";
               }
               enum "1536.71" {
                 description "1536.71 nm/195.087500 THz 3.125/6.25/12.5GHz spacing";
               }
               enum "1536.68" {
                 description "1536.68 nm/195.090625 THz 3.125GHz spacing";
               }
               enum "1536.66" {
                 description "1536.66 nm/195.093750 THz 3.125/6.25GHz spacing";
               }
               enum "1536.63" {
                 description "1536.63 nm/195.096875 THz 3.125GHz spacing";
               }
               enum "1536.61" {
                 description "1536.61 nm/195.100000 THz 3.125/6.25/12.5/100GHz spacing";
               }
               enum "1536.58" {
                 description "1536.58 nm/195.103125 THz 3.125GHz spacing";
               }
               enum "1536.56" {
                 description "1536.56 nm/195.106250 THz 3.125/6.25GHz spacing";
               }
               enum "1536.54" {
                 description "1536.54 nm/195.109375 THz 3.125GHz spacing";
               }
               enum "1536.51" {
                 description "1536.51 nm/195.112500 THz 3.125/6.25/12.5GHz spacing";
               }
               enum "1536.49" {
                 description "1536.49 nm/195.115625 THz 3.125GHz spacing";
               }
               enum "1536.46" {
                 description "1536.46 nm/195.118750 THz 3.125/6.25GHz spacing";
               }
               enum "1536.44" {
                 description "1536.44 nm/195.121875 THz 3.125GHz spacing";
               }
               enum "1536.41" {
                 description "1536.41 nm/195.125000 THz 3.125/6.25/12.5GHz spacing";
               }
               enum "1536.39" {
                 description "1536.39 nm/195.128125 THz 3.125GHz spacing";
               }
               enum "1536.36" {
                 description "1536.36 nm/195.131250 THz 3.125/6.25GHz spacing";
               }
               enum "1536.34" {
                 description "1536.34 nm/195.134375 THz 3.125GHz spacing";
               }
               enum "1536.31" {
                 description "1536.31 nm/195.137500 THz 3.125/6.25/12.5GHz spacing";
               }
               enum "1536.29" {
                 description "1536.29 nm/195.140625 THz 3.125GHz spacing";
               }
               enum "1536.26" {
                 description "1536.26 nm/195.143750 THz 3.125/6.25GHz spacing";
               }
               enum "1536.24" {
                 description "1536.24 nm/195.146875 THz 3.125GHz spacing";
               }
               enum "1536.22" {
                 description "1536.22 nm/195.150000 THz 3.125/6.25/12.5/50/75GHz spacing";
               }
               enum "1536.19" {
                 description "1536.19 nm/195.153125 THz 3.125GHz spacing";
               }
               enum "1536.17" {
                 description "1536.17 nm/195.156250 THz 3.125/6.25GHz spacing";
               }
               enum "1536.14" {
                 description "1536.14 nm/195.159375 THz 3.125GHz spacing";
               }
               enum "1536.12" {
                 description "1536.12 nm/195.162500 THz 3.125/6.25/12.5GHz spacing";
               }
               enum "1536.09" {
                 description "1536.09 nm/195.165625 THz 3.125GHz spacing";
               }
               enum "1536.07" {
                 description "1536.07 nm/195.168750 THz 3.125/6.25GHz spacing";
               }
               enum "1536.04" {
                 description "1536.04 nm/195.171875 THz 3.125GHz spacing";
               }
               enum "1536.02" {
                 description "1536.02 nm/195.175000 THz 3.125/6.25/12.5GHz spacing";
               }
               enum "1535.99" {
                 description "1535.99 nm/195.178125 THz 3.125GHz spacing";
               }
               enum "1535.97" {
                 description "1535.97 nm/195.181250 THz 3.125/6.25GHz spacing";
               }
               enum "1535.94" {
                 description "1535.94 nm/195.184375 THz 3.125GHz spacing";
               }
               enum "1535.92" {
                 description "1535.92 nm/195.187500 THz 3.125/6.25/12.5GHz spacing";
               }
               enum "1535.90" {
                 description "1535.90 nm/195.190625 THz 3.125GHz spacing";
               }
               enum "1535.87" {
                 description "1535.87 nm/195.193750 THz 3.125/6.25GHz spacing";
               }
               enum "1535.85" {
                 description "1535.85 nm/195.196875 THz 3.125GHz spacing";
               }
               enum "1535.82" {
                 description "1535.82 nm/195.200000 THz 3.125/6.25/12.5/100GHz spacing";
               }
               enum "1535.80" {
                 description "1535.80 nm/195.203125 THz 3.125GHz spacing";
               }
               enum "1535.77" {
                 description "1535.77 nm/195.206250 THz 3.125/6.25GHz spacing";
               }
               enum "1535.75" {
                 description "1535.75 nm/195.209375 THz 3.125GHz spacing";
               }
               enum "1535.72" {
                 description "1535.72 nm/195.212500 THz 3.125/6.25/12.5GHz spacing";
               }
               enum "1535.70" {
                 description "1535.70 nm/195.215625 THz 3.125GHz spacing";
               }
               enum "1535.67" {
                 description "1535.67 nm/195.218750 THz 3.125/6.25GHz spacing";
               }
               enum "1535.65" {
                 description "1535.65 nm/195.221875 THz 3.125GHz spacing";
               }
               enum "1535.63" {
                 description "1535.63 nm/195.225000 THz 3.125/6.25/12.5/75GHz spacing";
               }
               enum "1535.60" {
                 description "1535.60 nm/195.228125 THz 3.125GHz spacing";
               }
               enum "1535.58" {
                 description "1535.58 nm/195.231250 THz 3.125/6.25GHz spacing";
               }
               enum "1535.55" {
                 description "1535.55 nm/195.234375 THz 3.125GHz spacing";
               }
               enum "1535.53" {
                 description "1535.53 nm/195.237500 THz 3.125/6.25/12.5GHz spacing";
               }
               enum "1535.50" {
                 description "1535.50 nm/195.240625 THz 3.125GHz spacing";
               }
               enum "1535.48" {
                 description "1535.48 nm/195.243750 THz 3.125/6.25GHz spacing";
               }
               enum "1535.45" {
                 description "1535.45 nm/195.246875 THz 3.125GHz spacing";
               }
               enum "1535.43" {
                 description "1535.43 nm/195.250000 THz 3.125/6.25/12.5/50GHz spacing";
               }
               enum "1535.40" {
                 description "1535.40 nm/195.253125 THz 3.125GHz spacing";
               }
               enum "1535.38" {
                 description "1535.38 nm/195.256250 THz 3.125/6.25GHz spacing";
               }
               enum "1535.36" {
                 description "1535.36 nm/195.259375 THz 3.125GHz spacing";
               }
               enum "1535.33" {
                 description "1535.33 nm/195.262500 THz 3.125/6.25/12.5GHz spacing";
               }
               enum "1535.31" {
                 description "1535.31 nm/195.265625 THz 3.125GHz spacing";
               }
               enum "1535.28" {
                 description "1535.28 nm/195.268750 THz 3.125/6.25GHz spacing";
               }
               enum "1535.26" {
                 description "1535.26 nm/195.271875 THz 3.125GHz spacing";
               }
               enum "1535.23" {
                 description "1535.23 nm/195.275000 THz 3.125/6.25/12.5GHz spacing";
               }
               enum "1535.21" {
                 description "1535.21 nm/195.278125 THz 3.125GHz spacing";
               }
               enum "1535.18" {
                 description "1535.18 nm/195.281250 THz 3.125/6.25GHz spacing";
               }
               enum "1535.16" {
                 description "1535.16 nm/195.284375 THz 3.125GHz spacing";
               }
               enum "1535.13" {
                 description "1535.13 nm/195.287500 THz 3.125/6.25/12.5GHz spacing";
               }
               enum "1535.11" {
                 description "1535.11 nm/195.290625 THz 3.125GHz spacing";
               }
               enum "1535.08" {
                 description "1535.08 nm/195.293750 THz 3.125/6.25GHz spacing";
               }
               enum "1535.06" {
                 description "1535.06 nm/195.296875 THz 3.125GHz spacing";
               }
               enum "1535.04" {
                 description "1535.04 nm/195.300000 THz 3.125/6.25/12.5/50/75/100GHz spacing";
               }
               enum "1535.01" {
                 description "1535.01 nm/195.303125 THz 3.125GHz spacing";
               }
               enum "1534.99" {
                 description "1534.99 nm/195.306250 THz 3.125/6.25GHz spacing";
               }
               enum "1534.96" {
                 description "1534.96 nm/195.309375 THz 3.125GHz spacing";
               }
               enum "1534.94" {
                 description "1534.94 nm/195.312500 THz 3.125/6.25/12.5GHz spacing";
               }
               enum "1534.91" {
                 description "1534.91 nm/195.315625 THz 3.125GHz spacing";
               }
               enum "1534.89" {
                 description "1534.89 nm/195.318750 THz 3.125/6.25GHz spacing";
               }
               enum "1534.86" {
                 description "1534.86 nm/195.321875 THz 3.125GHz spacing";
               }
               enum "1534.84" {
                 description "1534.84 nm/195.325000 THz 3.125/6.25/12.5GHz spacing";
               }
               enum "1534.81" {
                 description "1534.81 nm/195.328125 THz 3.125GHz spacing";
               }
               enum "1534.79" {
                 description "1534.79 nm/195.331250 THz 3.125/6.25GHz spacing";
               }
               enum "1534.77" {
                 description "1534.77 nm/195.334375 THz 3.125GHz spacing";
               }
               enum "1534.74" {
                 description "1534.74 nm/195.337500 THz 3.125/6.25/12.5GHz spacing";
               }
               enum "1534.72" {
                 description "1534.72 nm/195.340625 THz 3.125GHz spacing";
               }
               enum "1534.69" {
                 description "1534.69 nm/195.343750 THz 3.125/6.25GHz spacing";
               }
               enum "1534.67" {
                 description "1534.67 nm/195.346875 THz 3.125GHz spacing";
               }
               enum "1534.64" {
                 description "1534.64 nm/195.350000 THz 3.125/6.25/12.5/50GHz spacing";
               }
               enum "1534.62" {
                 description "1534.62 nm/195.353125 THz 3.125GHz spacing";
               }
               enum "1534.59" {
                 description "1534.59 nm/195.356250 THz 3.125/6.25GHz spacing";
               }
               enum "1534.57" {
                 description "1534.57 nm/195.359375 THz 3.125GHz spacing";
               }
               enum "1534.54" {
                 description "1534.54 nm/195.362500 THz 3.125/6.25/12.5GHz spacing";
               }
               enum "1534.52" {
                 description "1534.52 nm/195.365625 THz 3.125GHz spacing";
               }
               enum "1534.50" {
                 description "1534.50 nm/195.368750 THz 3.125/6.25GHz spacing";
               }
               enum "1534.47" {
                 description "1534.47 nm/195.371875 THz 3.125GHz spacing";
               }
               enum "1534.45" {
                 description "1534.45 nm/195.375000 THz 3.125/6.25/12.5/75GHz spacing";
               }
               enum "1534.42" {
                 description "1534.42 nm/195.378125 THz 3.125GHz spacing";
               }
               enum "1534.40" {
                 description "1534.40 nm/195.381250 THz 3.125/6.25GHz spacing";
               }
               enum "1534.37" {
                 description "1534.37 nm/195.384375 THz 3.125GHz spacing";
               }
               enum "1534.35" {
                 description "1534.35 nm/195.387500 THz 3.125/6.25/12.5GHz spacing";
               }
               enum "1534.32" {
                 description "1534.32 nm/195.390625 THz 3.125GHz spacing";
               }
               enum "1534.30" {
                 description "1534.30 nm/195.393750 THz 3.125/6.25GHz spacing";
               }
               enum "1534.27" {
                 description "1534.27 nm/195.396875 THz 3.125GHz spacing";
               }
               enum "1534.25" {
                 description "1534.25 nm/195.400000 THz 3.125/6.25/12.5/100GHz spacing";
               }
               enum "1534.23" {
                 description "1534.23 nm/195.403125 THz 3.125GHz spacing";
               }
               enum "1534.20" {
                 description "1534.20 nm/195.406250 THz 3.125/6.25GHz spacing";
               }
               enum "1534.18" {
                 description "1534.18 nm/195.409375 THz 3.125GHz spacing";
               }
               enum "1534.15" {
                 description "1534.15 nm/195.412500 THz 3.125/6.25/12.5GHz spacing";
               }
               enum "1534.13" {
                 description "1534.13 nm/195.415625 THz 3.125GHz spacing";
               }
               enum "1534.10" {
                 description "1534.10 nm/195.418750 THz 3.125/6.25GHz spacing";
               }
               enum "1534.08" {
                 description "1534.08 nm/195.421875 THz 3.125GHz spacing";
               }
               enum "1534.05" {
                 description "1534.05 nm/195.425000 THz 3.125/6.25/12.5GHz spacing";
               }
               enum "1534.03" {
                 description "1534.03 nm/195.428125 THz 3.125GHz spacing";
               }
               enum "1534.00" {
                 description "1534.00 nm/195.431250 THz 3.125/6.25GHz spacing";
               }
               enum "1533.98" {
                 description "1533.98 nm/195.434375 THz 3.125GHz spacing";
               }
               enum "1533.96" {
                 description "1533.96 nm/195.437500 THz 3.125/6.25/12.5GHz spacing";
               }
               enum "1533.93" {
                 description "1533.93 nm/195.440625 THz 3.125GHz spacing";
               }
               enum "1533.91" {
                 description "1533.91 nm/195.443750 THz 3.125/6.25GHz spacing";
               }
               enum "1533.88" {
                 description "1533.88 nm/195.446875 THz 3.125GHz spacing";
               }
               enum "1533.86" {
                 description "1533.86 nm/195.450000 THz 3.125/6.25/12.5/50/75GHz spacing";
               }
               enum "1533.83" {
                 description "1533.83 nm/195.453125 THz 3.125GHz spacing";
               }
               enum "1533.81" {
                 description "1533.81 nm/195.456250 THz 3.125/6.25GHz spacing";
               }
               enum "1533.78" {
                 description "1533.78 nm/195.459375 THz 3.125GHz spacing";
               }
               enum "1533.76" {
                 description "1533.76 nm/195.462500 THz 3.125/6.25/12.5GHz spacing";
               }
               enum "1533.73" {
                 description "1533.73 nm/195.465625 THz 3.125GHz spacing";
               }
               enum "1533.71" {
                 description "1533.71 nm/195.468750 THz 3.125/6.25GHz spacing";
               }
               enum "1533.69" {
                 description "1533.69 nm/195.471875 THz 3.125GHz spacing";
               }
               enum "1533.66" {
                 description "1533.66 nm/195.475000 THz 3.125/6.25/12.5GHz spacing";
               }
               enum "1533.64" {
                 description "1533.64 nm/195.478125 THz 3.125GHz spacing";
               }
               enum "1533.61" {
                 description "1533.61 nm/195.481250 THz 3.125/6.25GHz spacing";
               }
               enum "1533.59" {
                 description "1533.59 nm/195.484375 THz 3.125GHz spacing";
               }
               enum "1533.56" {
                 description "1533.56 nm/195.487500 THz 3.125/6.25/12.5GHz spacing";
               }
               enum "1533.54" {
                 description "1533.54 nm/195.490625 THz 3.125GHz spacing";
               }
               enum "1533.51" {
                 description "1533.51 nm/195.493750 THz 3.125/6.25GHz spacing";
               }
               enum "1533.49" {
                 description "1533.49 nm/195.496875 THz 3.125GHz spacing";
               }
               enum "1533.47" {
                 description "1533.47 nm/195.500000 THz 3.125/6.25/12.5/100GHz spacing";
               }
               enum "1533.44" {
                 description "1533.44 nm/195.503125 THz 3.125GHz spacing";
               }
               enum "1533.42" {
                 description "1533.42 nm/195.506250 THz 3.125/6.25GHz spacing";
               }
               enum "1533.39" {
                 description "1533.39 nm/195.509375 THz 3.125GHz spacing";
               }
               enum "1533.37" {
                 description "1533.37 nm/195.512500 THz 3.125/6.25/12.5GHz spacing";
               }
               enum "1533.34" {
                 description "1533.34 nm/195.515625 THz 3.125GHz spacing";
               }
               enum "1533.32" {
                 description "1533.32 nm/195.518750 THz 3.125/6.25GHz spacing";
               }
               enum "1533.29" {
                 description "1533.29 nm/195.521875 THz 3.125GHz spacing";
               }
               enum "1533.27" {
                 description "1533.27 nm/195.525000 THz 3.125/6.25/12.5/75GHz spacing";
               }
               enum "1533.24" {
                 description "1533.24 nm/195.528125 THz 3.125GHz spacing";
               }
               enum "1533.22" {
                 description "1533.22 nm/195.531250 THz 3.125/6.25GHz spacing";
               }
               enum "1533.20" {
                 description "1533.20 nm/195.534375 THz 3.125GHz spacing";
               }
               enum "1533.17" {
                 description "1533.17 nm/195.537500 THz 3.125/6.25/12.5GHz spacing";
               }
               enum "1533.15" {
                 description "1533.15 nm/195.540625 THz 3.125GHz spacing";
               }
               enum "1533.12" {
                 description "1533.12 nm/195.543750 THz 3.125/6.25GHz spacing";
               }
               enum "1533.10" {
                 description "1533.10 nm/195.546875 THz 3.125GHz spacing";
               }
               enum "1533.07" {
                 description "1533.07 nm/195.550000 THz 3.125/6.25/12.5/50GHz spacing";
               }
               enum "1533.05" {
                 description "1533.05 nm/195.553125 THz 3.125GHz spacing";
               }
               enum "1533.02" {
                 description "1533.02 nm/195.556250 THz 3.125/6.25GHz spacing";
               }
               enum "1533.00" {
                 description "1533.00 nm/195.559375 THz 3.125GHz spacing";
               }
               enum "1532.98" {
                 description "1532.98 nm/195.562500 THz 3.125/6.25/12.5GHz spacing";
               }
               enum "1532.95" {
                 description "1532.95 nm/195.565625 THz 3.125GHz spacing";
               }
               enum "1532.93" {
                 description "1532.93 nm/195.568750 THz 3.125/6.25GHz spacing";
               }
               enum "1532.90" {
                 description "1532.90 nm/195.571875 THz 3.125GHz spacing";
               }
               enum "1532.88" {
                 description "1532.88 nm/195.575000 THz 3.125/6.25/12.5GHz spacing";
               }
               enum "1532.85" {
                 description "1532.85 nm/195.578125 THz 3.125GHz spacing";
               }
               enum "1532.83" {
                 description "1532.83 nm/195.581250 THz 3.125/6.25GHz spacing";
               }
               enum "1532.80" {
                 description "1532.80 nm/195.584375 THz 3.125GHz spacing";
               }
               enum "1532.78" {
                 description "1532.78 nm/195.587500 THz 3.125/6.25/12.5GHz spacing";
               }
               enum "1532.75" {
                 description "1532.75 nm/195.590625 THz 3.125GHz spacing";
               }
               enum "1532.73" {
                 description "1532.73 nm/195.593750 THz 3.125/6.25GHz spacing";
               }
               enum "1532.71" {
                 description "1532.71 nm/195.596875 THz 3.125GHz spacing";
               }
               enum "1532.68" {
                 description "1532.68 nm/195.600000 THz 3.125/6.25/12.5/50/75/100GHz spacing";
               }
               enum "1532.66" {
                 description "1532.66 nm/195.603125 THz 3.125GHz spacing";
               }
               enum "1532.63" {
                 description "1532.63 nm/195.606250 THz 3.125/6.25GHz spacing";
               }
               enum "1532.61" {
                 description "1532.61 nm/195.609375 THz 3.125GHz spacing";
               }
               enum "1532.58" {
                 description "1532.58 nm/195.612500 THz 3.125/6.25/12.5GHz spacing";
               }
               enum "1532.56" {
                 description "1532.56 nm/195.615625 THz 3.125GHz spacing";
               }
               enum "1532.53" {
                 description "1532.53 nm/195.618750 THz 3.125/6.25GHz spacing";
               }
               enum "1532.51" {
                 description "1532.51 nm/195.621875 THz 3.125GHz spacing";
               }
               enum "1532.49" {
                 description "1532.49 nm/195.625000 THz 3.125/6.25/12.5GHz spacing";
               }
               enum "1532.46" {
                 description "1532.46 nm/195.628125 THz 3.125GHz spacing";
               }
               enum "1532.44" {
                 description "1532.44 nm/195.631250 THz 3.125/6.25GHz spacing";
               }
               enum "1532.41" {
                 description "1532.41 nm/195.634375 THz 3.125GHz spacing";
               }
               enum "1532.39" {
                 description "1532.39 nm/195.637500 THz 3.125/6.25/12.5GHz spacing";
               }
               enum "1532.36" {
                 description "1532.36 nm/195.640625 THz 3.125GHz spacing";
               }
               enum "1532.34" {
                 description "1532.34 nm/195.643750 THz 3.125/6.25GHz spacing";
               }
               enum "1532.31" {
                 description "1532.31 nm/195.646875 THz 3.125GHz spacing";
               }
               enum "1532.29" {
                 description "1532.29 nm/195.650000 THz 3.125/6.25/12.5/50GHz spacing";
               }
               enum "1532.27" {
                 description "1532.27 nm/195.653125 THz 3.125GHz spacing";
               }
               enum "1532.24" {
                 description "1532.24 nm/195.656250 THz 3.125/6.25GHz spacing";
               }
               enum "1532.22" {
                 description "1532.22 nm/195.659375 THz 3.125GHz spacing";
               }
               enum "1532.19" {
                 description "1532.19 nm/195.662500 THz 3.125/6.25/12.5GHz spacing";
               }
               enum "1532.17" {
                 description "1532.17 nm/195.665625 THz 3.125GHz spacing";
               }
               enum "1532.14" {
                 description "1532.14 nm/195.668750 THz 3.125/6.25GHz spacing";
               }
               enum "1532.12" {
                 description "1532.12 nm/195.671875 THz 3.125GHz spacing";
               }
               enum "1532.09" {
                 description "1532.09 nm/195.675000 THz 3.125/6.25/12.5/75GHz spacing";
               }
               enum "1532.07" {
                 description "1532.07 nm/195.678125 THz 3.125GHz spacing";
               }
               enum "1532.04" {
                 description "1532.04 nm/195.681250 THz 3.125/6.25GHz spacing";
               }
               enum "1532.02" {
                 description "1532.02 nm/195.684375 THz 3.125GHz spacing";
               }
               enum "1532.00" {
                 description "1532.00 nm/195.687500 THz 3.125/6.25/12.5GHz spacing";
               }
               enum "1531.97" {
                 description "1531.97 nm/195.690625 THz 3.125GHz spacing";
               }
               enum "1531.95" {
                 description "1531.95 nm/195.693750 THz 3.125/6.25GHz spacing";
               }
               enum "1531.92" {
                 description "1531.92 nm/195.696875 THz 3.125GHz spacing";
               }
               enum "1531.90" {
                 description "1531.90 nm/195.700000 THz 3.125/6.25/12.5/100GHz spacing";
               }
               enum "1531.87" {
                 description "1531.87 nm/195.703125 THz 3.125GHz spacing";
               }
               enum "1531.85" {
                 description "1531.85 nm/195.706250 THz 3.125/6.25GHz spacing";
               }
               enum "1531.82" {
                 description "1531.82 nm/195.709375 THz 3.125GHz spacing";
               }
               enum "1531.80" {
                 description "1531.80 nm/195.712500 THz 3.125/6.25/12.5GHz spacing";
               }
               enum "1531.78" {
                 description "1531.78 nm/195.715625 THz 3.125GHz spacing";
               }
               enum "1531.75" {
                 description "1531.75 nm/195.718750 THz 3.125/6.25GHz spacing";
               }
               enum "1531.73" {
                 description "1531.73 nm/195.721875 THz 3.125GHz spacing";
               }
               enum "1531.70" {
                 description "1531.70 nm/195.725000 THz 3.125/6.25/12.5GHz spacing";
               }
               enum "1531.68" {
                 description "1531.68 nm/195.728125 THz 3.125GHz spacing";
               }
               enum "1531.65" {
                 description "1531.65 nm/195.731250 THz 3.125/6.25GHz spacing";
               }
               enum "1531.63" {
                 description "1531.63 nm/195.734375 THz 3.125GHz spacing";
               }
               enum "1531.60" {
                 description "1531.60 nm/195.737500 THz 3.125/6.25/12.5GHz spacing";
               }
               enum "1531.58" {
                 description "1531.58 nm/195.740625 THz 3.125GHz spacing";
               }
               enum "1531.56" {
                 description "1531.56 nm/195.743750 THz 3.125/6.25GHz spacing";
               }
               enum "1531.53" {
                 description "1531.53 nm/195.746875 THz 3.125GHz spacing";
               }
               enum "1531.51" {
                 description "1531.51 nm/195.750000 THz 3.125/6.25/12.5/50/75GHz spacing";
               }
               enum "1531.48" {
                 description "1531.48 nm/195.753125 THz 3.125GHz spacing";
               }
               enum "1531.46" {
                 description "1531.46 nm/195.756250 THz 3.125/6.25GHz spacing";
               }
               enum "1531.43" {
                 description "1531.43 nm/195.759375 THz 3.125GHz spacing";
               }
               enum "1531.41" {
                 description "1531.41 nm/195.762500 THz 3.125/6.25/12.5GHz spacing";
               }
               enum "1531.38" {
                 description "1531.38 nm/195.765625 THz 3.125GHz spacing";
               }
               enum "1531.36" {
                 description "1531.36 nm/195.768750 THz 3.125/6.25GHz spacing";
               }
               enum "1531.34" {
                 description "1531.34 nm/195.771875 THz 3.125GHz spacing";
               }
               enum "1531.31" {
                 description "1531.31 nm/195.775000 THz 3.125/6.25/12.5GHz spacing";
               }
               enum "1531.29" {
                 description "1531.29 nm/195.778125 THz 3.125GHz spacing";
               }
               enum "1531.26" {
                 description "1531.26 nm/195.781250 THz 3.125/6.25GHz spacing";
               }
               enum "1531.24" {
                 description "1531.24 nm/195.784375 THz 3.125GHz spacing";
               }
               enum "1531.21" {
                 description "1531.21 nm/195.787500 THz 3.125/6.25/12.5GHz spacing";
               }
               enum "1531.19" {
                 description "1531.19 nm/195.790625 THz 3.125GHz spacing";
               }
               enum "1531.16" {
                 description "1531.16 nm/195.793750 THz 3.125/6.25GHz spacing";
               }
               enum "1531.14" {
                 description "1531.14 nm/195.796875 THz 3.125GHz spacing";
               }
               enum "1531.12" {
                 description "1531.12 nm/195.800000 THz 3.125/6.25/12.5/100GHz spacing";
               }
               enum "1531.09" {
                 description "1531.09 nm/195.803125 THz 3.125GHz spacing";
               }
               enum "1531.07" {
                 description "1531.07 nm/195.806250 THz 3.125/6.25GHz spacing";
               }
               enum "1531.04" {
                 description "1531.04 nm/195.809375 THz 3.125GHz spacing";
               }
               enum "1531.02" {
                 description "1531.02 nm/195.812500 THz 3.125/6.25/12.5GHz spacing";
               }
               enum "1530.99" {
                 description "1530.99 nm/195.815625 THz 3.125GHz spacing";
               }
               enum "1530.97" {
                 description "1530.97 nm/195.818750 THz 3.125/6.25GHz spacing";
               }
               enum "1530.94" {
                 description "1530.94 nm/195.821875 THz 3.125GHz spacing";
               }
               enum "1530.92" {
                 description "1530.92 nm/195.825000 THz 3.125/6.25/12.5/75GHz spacing";
               }
               enum "1530.90" {
                 description "1530.90 nm/195.828125 THz 3.125GHz spacing";
               }
               enum "1530.87" {
                 description "1530.87 nm/195.831250 THz 3.125/6.25GHz spacing";
               }
               enum "1530.85" {
                 description "1530.85 nm/195.834375 THz 3.125GHz spacing";
               }
               enum "1530.82" {
                 description "1530.82 nm/195.837500 THz 3.125/6.25/12.5GHz spacing";
               }
               enum "1530.80" {
                 description "1530.80 nm/195.840625 THz 3.125GHz spacing";
               }
               enum "1530.77" {
                 description "1530.77 nm/195.843750 THz 3.125/6.25GHz spacing";
               }
               enum "1530.75" {
                 description "1530.75 nm/195.846875 THz 3.125GHz spacing";
               }
               enum "1530.72" {
                 description "1530.72 nm/195.850000 THz 3.125/6.25/12.5/50GHz spacing";
               }
               enum "1530.70" {
                 description "1530.70 nm/195.853125 THz 3.125GHz spacing";
               }
               enum "1530.68" {
                 description "1530.68 nm/195.856250 THz 3.125/6.25GHz spacing";
               }
               enum "1530.65" {
                 description "1530.65 nm/195.859375 THz 3.125GHz spacing";
               }
               enum "1530.63" {
                 description "1530.63 nm/195.862500 THz 3.125/6.25/12.5GHz spacing";
               }
               enum "1530.60" {
                 description "1530.60 nm/195.865625 THz 3.125GHz spacing";
               }
               enum "1530.58" {
                 description "1530.58 nm/195.868750 THz 3.125/6.25GHz spacing";
               }
               enum "1530.55" {
                 description "1530.55 nm/195.871875 THz 3.125GHz spacing";
               }
               enum "1530.53" {
                 description "1530.53 nm/195.875000 THz 3.125/6.25/12.5GHz spacing";
               }
               enum "1530.51" {
                 description "1530.51 nm/195.878125 THz 3.125GHz spacing";
               }
               enum "1530.48" {
                 description "1530.48 nm/195.881250 THz 3.125/6.25GHz spacing";
               }
               enum "1530.46" {
                 description "1530.46 nm/195.884375 THz 3.125GHz spacing";
               }
               enum "1530.43" {
                 description "1530.43 nm/195.887500 THz 3.125/6.25/12.5GHz spacing";
               }
               enum "1530.41" {
                 description "1530.41 nm/195.890625 THz 3.125GHz spacing";
               }
               enum "1530.38" {
                 description "1530.38 nm/195.893750 THz 3.125/6.25GHz spacing";
               }
               enum "1530.36" {
                 description "1530.36 nm/195.896875 THz 3.125GHz spacing";
               }
               enum "1530.33" {
                 description "1530.33 nm/195.900000 THz 3.125/6.25/12.5/50/75/100GHz spacing";
               }
               enum "1530.31" {
                 description "1530.31 nm/195.903125 THz 3.125GHz spacing";
               }
               enum "1530.29" {
                 description "1530.29 nm/195.906250 THz 3.125/6.25GHz spacing";
               }
               enum "1530.26" {
                 description "1530.26 nm/195.909375 THz 3.125GHz spacing";
               }
               enum "1530.24" {
                 description "1530.24 nm/195.912500 THz 3.125/6.25/12.5GHz spacing";
               }
               enum "1530.21" {
                 description "1530.21 nm/195.915625 THz 3.125GHz spacing";
               }
               enum "1530.19" {
                 description "1530.19 nm/195.918750 THz 3.125/6.25GHz spacing";
               }
               enum "1530.16" {
                 description "1530.16 nm/195.921875 THz 3.125GHz spacing";
               }
               enum "1530.14" {
                 description "1530.14 nm/195.925000 THz 3.125/6.25/12.5GHz spacing";
               }
               enum "1530.11" {
                 description "1530.11 nm/195.928125 THz 3.125GHz spacing";
               }
               enum "1530.09" {
                 description "1530.09 nm/195.931250 THz 3.125/6.25GHz spacing";
               }
               enum "1530.07" {
                 description "1530.07 nm/195.934375 THz 3.125GHz spacing";
               }
               enum "1530.04" {
                 description "1530.04 nm/195.937500 THz 3.125/6.25/12.5GHz spacing";
               }
               enum "1530.02" {
                 description "1530.02 nm/195.940625 THz 3.125GHz spacing";
               }
               enum "1529.99" {
                 description "1529.99 nm/195.943750 THz 3.125/6.25GHz spacing";
               }
               enum "1529.97" {
                 description "1529.97 nm/195.946875 THz 3.125GHz spacing";
               }
               enum "1529.94" {
                 description "1529.94 nm/195.950000 THz 3.125/6.25/12.5/50GHz spacing";
               }
               enum "1529.92" {
                 description "1529.92 nm/195.953125 THz 3.125GHz spacing";
               }
               enum "1529.89" {
                 description "1529.89 nm/195.956250 THz 3.125/6.25GHz spacing";
               }
               enum "1529.87" {
                 description "1529.87 nm/195.959375 THz 3.125GHz spacing";
               }
               enum "1529.85" {
                 description "1529.85 nm/195.962500 THz 3.125/6.25/12.5GHz spacing";
               }
               enum "1529.82" {
                 description "1529.82 nm/195.965625 THz 3.125GHz spacing";
               }
               enum "1529.80" {
                 description "1529.80 nm/195.968750 THz 3.125/6.25GHz spacing";
               }
               enum "1529.77" {
                 description "1529.77 nm/195.971875 THz 3.125GHz spacing";
               }
               enum "1529.75" {
                 description "1529.75 nm/195.975000 THz 3.125/6.25/12.5/75GHz spacing";
               }
               enum "1529.72" {
                 description "1529.72 nm/195.978125 THz 3.125GHz spacing";
               }
               enum "1529.70" {
                 description "1529.70 nm/195.981250 THz 3.125/6.25GHz spacing";
               }
               enum "1529.68" {
                 description "1529.68 nm/195.984375 THz 3.125GHz spacing";
               }
               enum "1529.65" {
                 description "1529.65 nm/195.987500 THz 3.125/6.25/12.5GHz spacing";
               }
               enum "1529.63" {
                 description "1529.63 nm/195.990625 THz 3.125GHz spacing";
               }
               enum "1529.60" {
                 description "1529.60 nm/195.993750 THz 3.125/6.25GHz spacing";
               }
               enum "1529.58" {
                 description "1529.58 nm/195.996875 THz 3.125GHz spacing";
               }
               enum "1529.55" {
                 description "1529.55 nm/196.000000 THz 3.125/6.25/12.5/100GHz spacing";
               }
               enum "1529.53" {
                 description "1529.53 nm/196.003125 THz 3.125GHz spacing";
               }
               enum "1529.50" {
                 description "1529.50 nm/196.006250 THz 3.125/6.25GHz spacing";
               }
               enum "1529.48" {
                 description "1529.48 nm/196.009375 THz 3.125GHz spacing";
               }
               enum "1529.46" {
                 description "1529.46 nm/196.012500 THz 3.125/6.25/12.5GHz spacing";
               }
               enum "1529.43" {
                 description "1529.43 nm/196.015625 THz 3.125GHz spacing";
               }
               enum "1529.41" {
                 description "1529.41 nm/196.018750 THz 3.125/6.25GHz spacing";
               }
               enum "1529.38" {
                 description "1529.38 nm/196.021875 THz 3.125GHz spacing";
               }
               enum "1529.36" {
                 description "1529.36 nm/196.025000 THz 3.125/6.25/12.5GHz spacing";
               }
               enum "1529.33" {
                 description "1529.33 nm/196.028125 THz 3.125GHz spacing";
               }
               enum "1529.31" {
                 description "1529.31 nm/196.031250 THz 3.125/6.25GHz spacing";
               }
               enum "1529.29" {
                 description "1529.29 nm/196.034375 THz 3.125GHz spacing";
               }
               enum "1529.26" {
                 description "1529.26 nm/196.037500 THz 3.125/6.25/12.5GHz spacing";
               }
               enum "1529.24" {
                 description "1529.24 nm/196.040625 THz 3.125GHz spacing";
               }
               enum "1529.21" {
                 description "1529.21 nm/196.043750 THz 3.125/6.25GHz spacing";
               }
               enum "1529.19" {
                 description "1529.19 nm/196.046875 THz 3.125GHz spacing";
               }
               enum "1529.16" {
                 description "1529.16 nm/196.050000 THz 3.125/6.25/12.5/50/75GHz spacing";
               }
               enum "1529.14" {
                 description "1529.14 nm/196.053125 THz 3.125GHz spacing";
               }
               enum "1529.11" {
                 description "1529.11 nm/196.056250 THz 3.125/6.25GHz spacing";
               }
               enum "1529.09" {
                 description "1529.09 nm/196.059375 THz 3.125GHz spacing";
               }
               enum "1529.07" {
                 description "1529.07 nm/196.062500 THz 3.125/6.25/12.5GHz spacing";
               }
               enum "1529.04" {
                 description "1529.04 nm/196.065625 THz 3.125GHz spacing";
               }
               enum "1529.02" {
                 description "1529.02 nm/196.068750 THz 3.125/6.25GHz spacing";
               }
               enum "1528.99" {
                 description "1528.99 nm/196.071875 THz 3.125GHz spacing";
               }
               enum "1528.97" {
                 description "1528.97 nm/196.075000 THz 3.125/6.25/12.5GHz spacing";
               }
               enum "1528.94" {
                 description "1528.94 nm/196.078125 THz 3.125GHz spacing";
               }
               enum "1528.92" {
                 description "1528.92 nm/196.081250 THz 3.125/6.25GHz spacing";
               }
               enum "1528.90" {
                 description "1528.90 nm/196.084375 THz 3.125GHz spacing";
               }
               enum "1528.87" {
                 description "1528.87 nm/196.087500 THz 3.125/6.25/12.5GHz spacing";
               }
               enum "1528.85" {
                 description "1528.85 nm/196.090625 THz 3.125GHz spacing";
               }
               enum "1528.82" {
                 description "1528.82 nm/196.093750 THz 3.125/6.25GHz spacing";
               }
               enum "1528.80" {
                 description "1528.80 nm/196.096875 THz 3.125GHz spacing";
               }
               enum "1528.77" {
                 description "1528.77 nm/196.100000 THz 3.125/6.25/12.5/50/75/100GHz spacing";
               }
               enum "1528.75" {
                 description "1528.75 nm/196.103125 THz 3.125GHz spacing";
               }
               enum "1528.72" {
                 description "1528.72 nm/196.106250 THz 3.125/6.25GHz spacing";
               }
               enum "1528.70" {
                 description "1528.70 nm/196.109375 THz 3.125GHz spacing";
               }
               enum "1528.68" {
                 description "1528.68 nm/196.112500 THz 3.125/6.25/12.5GHz spacing";
               }
               enum "1528.65" {
                 description "1528.65 nm/196.115625 THz 3.125GHz spacing";
               }
               enum "1528.63" {
                 description "1528.63 nm/196.118750 THz 3.125/6.25GHz spacing";
               }
               enum "1528.60" {
                 description "1528.60 nm/196.121875 THz 3.125GHz spacing";
               }
               enum "1528.58" {
                 description "1528.58 nm/196.125000 THz 3.125/6.25/12.5/75GHz spacing";
               }
               enum "1528.55" {
                 description "1528.55 nm/196.128125 THz 3.125GHz spacing";
               }
               enum "1528.53" {
                 description "1528.53 nm/196.131250 THz 3.125/6.25GHz spacing";
               }
               enum "1528.51" {
                 description "1528.51 nm/196.134375 THz 3.125GHz spacing";
               }
               enum "1528.48" {
                 description "1528.48 nm/196.137500 THz 3.125/6.25/12.5GHz spacing";
               }
               enum "1528.46" {
                 description "1528.46 nm/196.140625 THz 3.125GHz spacing";
               }
               enum "1528.43" {
                 description "1528.43 nm/196.143750 THz 3.125/6.25GHz spacing";
               }
               enum "1528.41" {
                 description "1528.41 nm/196.146875 THz 3.125GHz spacing";
               }
               enum "1528.38" {
                 description "1528.38 nm/196.15040 THz 50Ghz spacing";
               }
             }
           }
           leaf tx-power {
             description "Transmit laser output power";
             units "dBm";
             type string {
             }
           }
           container loopback {
             presence "enable loopback";
             description "Put the optics in loopback mode";
             uses apply-advanced;
           }
           leaf los-warning-threshold {
             description "LOS warning threshold";
             units "dBm";
             type string;
           }
           leaf los-alarm-threshold {
             description "LOS alarm threshold";
             units "dBm";
             type string;
           }
           leaf modulation-format {
             description "Type of Modulation Format";
             type enumeration {
               enum "16qam" {
                 description "16-QAM Modulation Format";
               }
               enum "8qam" {
                 description "8-QAM MOdulation Format";
               }
               enum "qpsk" {
                 description "QPSK Modulation Format";
               }
             }
           }
           choice laser-enable-choice {
             leaf laser-enable {
               description "Enable Laser";
               type empty;
             }
             leaf no-laser-enable {
               description "Don't enable Laser";
               type empty;
             }
           }
           choice is-ma-choice {
             leaf is-ma {
               description "Link is enabled with alarms masked";
               type empty;
             }
             leaf no-is-ma {
               description "Don't link is enabled with alarms masked";
               type empty;
             }
           }
           leaf encoding {
             description "Line encoding";
             type enumeration {
               enum "differential" {
                 description "Differential phase line encoding";
               }
               enum "non-differential" {
                 description "Non-differential phase line encoding";
               }
             }
           }
           leaf fec {
             description "Forward Error Correction mode";
             type enumeration {
               enum "sdfec" {
                 description "Sky-Compatible Soft Decision Forward Error Correction";
               }
               enum "sdfec25" {
                 description "Denali-Compatible Soft Decision Forward Error Correction with 25 percent overhead";
               }
               enum "hgfec" {
                 description "High Gain Forward Error Correction";
               }
               enum "sdfec15" {
                 description "Soft Decision Forward Error Correction with 15 percent overhead";
               }
             }
           }
           leaf high-polarization {
             description "High polarization tracking mode";
             type empty;
           }
           container signal-degrade {
             description "Signal degrade thresholds";
             uses apply-advanced;
             leaf interval {
               description "Time interval";
               default "10";
               units "milliseconds";
               type union {
                 type string {
                   pattern "<.*>|$.*";
                 }
                 type uint32 {
                   range "1 .. 1000";
                 }
               }
             }
             leaf ber-threshold-clear {
               description "Ber threshold for signal degrade clear (format: xe-n, example: 4.5e-3)";
               type string {
               }
             }
             leaf ber-threshold-signal-degrade {
               description "Ber threshold for signal-degrade (format: xe-n, example: 4.5e-3)";
               type string {
               }
             }
             leaf q-threshold-signal-degrade-clear {
               description "Q threshold for signal-degrade clear (e.g. 14.26)";
               units "dB";
               type string;
             }
             leaf q-threshold-signal-degrade {
               description "Q threshold for signal-degrade (e.g. 9.26)";
               units "dB";
               type string;
             }
           }
           list alarm {
             key name;
             ordered-by user;
             description "Set optic alarms";
             leaf name {
               type enumeration {
                 enum "low-light-alarm" {
                   description "Enable low light alarm";
                 }
               }
             }
             uses apply-advanced;
             choice actiontype {
               case case_1 {
                 leaf syslog {
                   type empty;
                 }
               }
               case case_2 {
                 leaf link-down {
                   type empty;
                 }
               }
             }
           }
           container tca {
             description "Set tca for optic alarms";
             uses apply-advanced;
             container tx-power-high-tca {
               description "Tx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container tx-power-low-tca {
               description "Tx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-power-high-tca {
               description "Rx power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-power-low-tca {
               description "Rx power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-signal-power-high-tca {
               description "Rx signal power high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container rx-signal-power-low-tca {
               description "Rx signal power low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm";
                 type string {
                 }
               }
               leaf threshold-24hrs {
                 description "TCA Threshold for 24-hour interval in dBm";
                 type string {
                 }
               }
             }
             container temperature-high-tca {
               description "Temperature high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                 }
               }
               leaf threshold-24hrs {
                 description "TCA Threshold for 24-hour interval in celsius";
                 type string {
                 }
               }
             }
             container temperature-low-tca {
               description "Temperature low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in celsius";
                 type string {
                 }
               }
               leaf threshold-24hrs {
                 description "TCA Threshold for 24-hour interval in celsius";
                 type string {
                 }
               }
             }
             container carrier-frequency-offset-high-tca {
               description "Carrier frequency offset high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container carrier-frequency-offset-low-tca {
               description "Carrier frequency offset low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container fec-ber {
               description "Optics Errored Seconds Threshold crossing defect trigger";
               choice enable-tca-choice {
                 leaf enable-tca {
                   description "Enable the Optics errored seconds threshold crossing alert";
                   type empty;
                 }
                 leaf no-enable-tca {
                   description "Don't enable the Optics errored seconds threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container tec-current-high-tca {
               description "TEC Current high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                 }
               }
               leaf threshold-24hrs {
                 description "TCA Threshold for 24-hour interval in mA";
                 type string {
                 }
               }
             }
             container tec-current-low-tca {
               description "TEC Current low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in mA";
                 type string {
                 }
               }
               leaf threshold-24hrs {
                 description "TCA Threshold for 24-hour interval in mA";
                 type string {
                 }
               }
             }
             container residual-isi-high-tca {
               description "Residual ISI high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                 }
               }
               leaf threshold-24hrs {
                 description "TCA Threshold for 24-hour interval in ps/nm";
                 type string {
                 }
               }
             }
             container residual-isi-low-tca {
               description "Residual ISI low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in ps/nm";
                 type string {
                 }
               }
               leaf threshold-24hrs {
                 description "TCA Threshold for 24-hour interval in ps/nm";
                 type string {
                 }
               }
             }
             container pam-histogram-high-tca {
               description "PAM Histogram high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes)";
                 type string {
                 }
               }
               leaf threshold-24hrs {
                 description "TCA Threshold for 24-hour interval";
                 type string {
                 }
               }
             }
             container snr-low-tca {
               description "SNR low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in dBm ";
                 type string {
                 }
               }
               leaf threshold-24hrs {
                 description "TCA Threshold for 24-hour interval in dBm";
                 type string {
                 }
               }
             }
             container fec-corrected-errors-high-tca {
               description "FEC Corrected Error High Threshold crossing defect trigger";
               uses apply-advanced;
               choice enable-tca-choice {
                 leaf enable-tca {
                   description "Enable the FEC Corrected Errors threshold crossing alert";
                   type empty;
                 }
                 leaf no-enable-tca {
                   description "Don't enable the FEC Corrected Errors threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container fec-ucorrected-words-high-tca {
               description "FEC UCorrected Words High Threshold crossing defect trigger";
               uses apply-advanced;
               choice enable-tca-choice {
                 leaf enable-tca {
                   description "Enable the FEC UCorrected Words threshold crossing alert";
                   type empty;
                 }
                 leaf no-enable-tca {
                   description "Don't enable the FEC UCorrected Words threshold crossing alert";
                   type empty;
                 }
               }
               leaf threshold {
                 description "TCA Threshold for user-configurable interval (default 15-minutes) in exponential format";
                 default "10e-3";
                 type string {
                 }
               }
               leaf threshold-24hrs {
                 description "TCA Threshold for 24-hour interval in exponential format";
                 default "10e-3";
                 type string {
                 }
               }
             }
             container laser-frequency-error-high-tca {
               description "Laser frequency error high TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
             container laser-frequency-error-low-tca {
               description "Laser frequency error low TCA";
               uses apply-advanced;
               choice enable-tca-choice {
                 leaf enable-tca {
                   description "Enable tca";
                   type empty;
                 }
                 leaf no-enable-tca {
                   description "Don't enable tca";
                   type empty;
                 }
               }
               leaf threshold {
                 description "TCA Threshold for user-configurable interval (default 15-minutes) in MHz";
                 type string {
                 }
               }
               leaf threshold-24hrs {
                 description "TCA Threshold for 24-hour interval in MHz";
                 type string {
                 }
               }
             }
           }
           list warning {
             key name;
             ordered-by user;
             description "Set optic warnings";
             leaf name {
               type enumeration {
                 enum "low-light-warning" {
                   description "Enable low light warning";
                 }
               }
             }
             uses apply-advanced;
             choice actiontype {
               case case_1 {
                 leaf syslog {
                   description "Set action as syslog";
                   type empty;
                 }
               }
               case case_2 {
                 leaf link-down {
                   description "Set action as link-down";
                   type empty;
                 }
               }
             }
           }
           choice lane-info {
             case case_1 {
             }
             case case_2 {
             }
           }
         }
         container och-options {
           description "Optical channel configuration options";
           uses och-attributes;
         }
         container otu-options {
           description "Optical transmission unit configuration options";
           uses otu-attributes;
         }
         container odu-options {
           description "Optical data unit configuration options";
           uses odu-attributes;
         }
         container ett-options {
           description "Transport ethernet client configuration options";
           uses ett-attributes;
         }
         container fastether-options {
           description "Fast Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf ingress-rate-limit {
             description "Ingress rate at port";
             units "megabits per second";
             type union {
               type string {
                 pattern "<.*>|$.*";
               }
               type uint32 {
                 range "1 .. 100";
               }
             }
           }
           list source-address-filter {
             key name;
             ordered-by user;
             description "Source address filters";
             leaf name {
               description "Remote MAC address";
               type jt:mac-addr;
             }
           }
           container ieee-802.3ad {
             description "IEEE 802.3ad";
             uses apply-advanced;
             container lacp {
               description "Link Aggregation Control Protocol configuration";
               uses apply-advanced;
               leaf port-priority {
                 description "Priority of the port (0 ... 65535)";
                 type union {
                   type uint16;
                   type string {
                     pattern "<.*>|$.*";
                   }
                 }
               }
             }
             leaf bundle {
               description "Join an aggregated Ethernet interface";
               type union {
                 type jt:interface-device;
                 type string {
                   pattern "<.*>|$.*";
                 }
               }
             }
             choice type {
               case case_1 {
                 leaf primary {
                   description "Primary interface for link-protection mode";
                   type empty;
                 }
               }
               case case_2 {
                 leaf backup {
                   description "Backup interface for link-protection mode";
                   type empty;
                 }
               }
             }
           }
           container mpls {
             description "MPLS options";
             uses mpls_ifd_options;
           }
           leaf ignore-l3-incompletes {
             description "Ignore L3 incomplete errors";
             type empty;
           }
         }
         container aggregated-ether-options {
           description "Aggregated Ethernet interface-specific options";
           uses apply-advanced;
           choice loopback-choice {
             leaf loopback {
               description "Enable loopback";
               type empty;
             }
             leaf no-loopback {
               description "Don't enable loopback";
               type empty;
             }
           }
           choice flow-control-choice {
             leaf flow-control {
               description "Enable flow control";
               type empty;
             }
             leaf no-flow-control {
               description "Don't enable flow control";
               type empty;
             }
           }
           choice source-filtering-choice {
             leaf source-filtering {
               description "Enable source address filtering";
               type empty;
             }
             leaf no-source-filtering {
               description "Don't enable source address filtering";
               type empty;
             }
           }
           leaf autostate-exclude {
             description "Interface will not contribute to IRB state";
             type empty;
           }
           container link-protection {
             presence "enable link-protection";
             description "Enable link protection mode";
             uses apply-advanced;
             leaf revertive {
               description "Revert back from active backup link to primary, if primary is UP";
               type empty;
             }
             leaf non-revertive {
               description "Do not revert back (default mode) from active backup link to primary, if primary is UP";
               type empty;
             }
             leaf backup-state {
               description "Link protection backup link state";
               default "accept-data";
               type enumeration {
                 enum "accept-data" {
                   description "Accept data on receive channel of backup link";
                 }
                 enum "discard-data" {
                   description "Discard data on receive channel of backup link";
                 }
                 enum "down" {
                   description "Backup link is marked down";
                 }
               }
             }
             container rtg-config {
               presence "enable rtg-config";
               description "RTG enable on AE";
               uses apply-advanced;
               leaf preempt-cutover-timer {
                 description "RTG preempt-cutover-timer in seconds";
                 default "1";
                 type union {
                   type string {
                     pattern "<.*>|$.*";
                   }
                   type uint32 {
                     range "0 .. 255";
                   }
                 }
               }
             }
           }
           choice fcoe-lag-choice {
             leaf fcoe-lag {
               description "Enable FIP/FCoE LAG";
               type empty;
             }
             leaf no-fcoe-lag {
               description "Don't enable FIP/FCoE LAG";
               type empty;
             }
           }
           list source-address-filter {
             key name;
             ordered-by user;
             description "Source address filters";
             leaf name {
               description "Remote MAC address";
               type jt:mac-addr;
             }
           }
           container load-balance {
             uses aggregate-load-balance;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container damping {
               description "BFD flap damping parameters";
               uses apply-advanced;
               leaf suppress {
                 description "Suppress threshold for figure-of-merit value";
                 default "5000";
                 type union {
                   type string {
                     pattern "<.*>|$.*";
                   }
                   type uint32 {
                     range "1000 .. 200000";
                   }
                 }
               }
               leaf reuse {
                 description "Reuse threshold for figure-of-merit value";
                 default "1000";
                 type union {
                   type string {
                     pattern "<.*>|$.*";
                   }
                   type uint32 {
                     range "1000 .. 200000";
                   }
                 }
               }
               leaf max-suppress-time {
                 description "Maximum hold-down time";
                 default "600";
                 units "seconds";
                 type union {
                   type string {
                     pattern "<.*>|$.*";
                   }
                   type uint32 {
                     range "1 .. 20000";
                   }
                 }
               }
               leaf half-life-interval {
                 description "Decay half life interval";
                 default "30";
                 units "seconds";
                 type union {
                   type string {
                     pattern "<.*>|$.*";
                   }
                   type uint32 {
                     range "1 .. 600";
                   }
                 }
               }
               leaf increment {
                 description "Increments applied to figure-of-merit value for every flap";
                 default "1000";
                 type union {
                   type string {
                     pattern "<.*>|$.*";
                   }
                   type uint32 {
                     range "1000 .. 20000";
                   }
                 }
               }
             }
             leaf neighbor {
               description "BFD neighbor address";
               type jt:ipaddr;
               mandatory true;
             }
             leaf local-address {
               description "BFD local address";
               type jt:ipaddr;
               mandatory true;
             }
             leaf holddown-interval {
               description "Time to hold the session-UP notification to the client";
               units "milliseconds";
               type union {
                 type string {
                   pattern "<.*>|$.*";
                 }
                 type uint32 {
                   range "0 .. 255000";
                 }
               }
             }
           }
           leaf minimum-links {
             description "Minimum number of aggregated links";
             type union {
               type string {
                 pattern "<.*>|$.*";
               }
               type uint16;
             }
           }
           container minimum-bandwidth {
             presence "enable minimum-bandwidth";
             description "Minimum bandwidth configured for aggregated bundle";
             uses apply-advanced;
             leaf bw-value {
               description "Bandwidth value";
               default "1";
               type union {
                 type uint64;
                 type string {
                   pattern "<.*>|$.*";
                 }
               }
             }
             leaf bw-unit {
               description "Bandwidth unit";
               type enumeration {
                 enum "bps" {
                   description "Links are in bits per sec";
                 }
                 enum "kbps" {
                   description "Links are in kilo bits per sec";
                 }
                 enum "mbps" {
                   description "Links are in mega bits per sec";
                 }
                 enum "gbps" {
                   description "Links are in giga bits per sec ";
                 }
               }
             }
           }
           choice redundancy_choice {
             case case_1 {
             }
             case case_2 {
             }
           }
           container rebalance-periodic {
             uses apply-advanced;
           }
           leaf link-speed {
             description "Link speed of individual interface that joins the AE";
             type enumeration {
               enum "10m" {
                 description "Links are 10M";
               }
               enum "100m" {
                 description "Links are 100M";
               }
               enum "1g" {
                 description "Links are 1G";
               }
               enum "2.5g" {
                 description "Links are 2.5G";
               }
               enum "5g" {
                 description "Links are 5G";
               }
               enum "8g" {
                 description "Links are 8G";
               }
               enum "10g" {
                 description "Links are 10G";
               }
               enum "25g" {
                 description "Links are 25G";
               }
               enum "40g" {
                 description "Links are 40G";
               }
               enum "50g" {
                 description "Links are 50G";
               }
               enum "80g" {
                 description "Links are 80G";
               }
               enum "100g" {
                 description "Links are 100G";
               }
               enum "200g" {
                 description "Links are 200G";
               }
               enum "400g" {
                 description "Links are 400G";
               }
               enum "800g" {
                 description "Links are 800G";
               }
               enum "oc192" {
                 description "Links are OC-192";
               }
               enum "mixed" {
                 description "Links are various speeds";
               }
             }
           }
           container local-bias {
             presence "enable local-bias";
             description "Turn on local bias functionality";
             uses apply-advanced;
             leaf disable {
               description "Disable local-bias";
               type empty;
             }
           }
           container lacp {
             description "Link Aggregation Control Protocol configuration";
             uses apply-advanced;
             choice mode {
               case case_1 {
                 leaf active {
                   description "Initiate transmission of LACP packets";
                   type empty;
                 }
               }
               case case_2 {
                 leaf passive {
                   description "Respond to LACP packets";
                   type empty;
                 }
               }
             }
             leaf periodic {
               description "Timer interval for periodic transmission of LACP packets";
               type enumeration {
                 enum "fast" {
                   description "Receive packets every second";
                 }
                 enum "slow" {
                   description "Receive packets every 30 seconds";
                 }
               }
             }
             leaf multiplier {
               description "LACP timeout detection multiplier";
               type union {
                 type string {
                   pattern "<.*>|$.*";
                 }
                 type uint32 {
                   range "3 .. 30";
                 }
               }
             }
             container link-protection {
               presence "enable link-protection";
               uses apply-advanced;
               leaf disable {
                 description "To turn off LACP link-protection";
                 type empty;
               }
               choice mode {
                 case case_1 {
                   leaf revertive {
                     description "Switch links when better priority link comes up";
                     type empty;
                   }
                 }
                 case case_2 {
                   leaf non-revertive {
                     description "Do not switch links when better priority link comes up";
                     type empty;
                   }
                 }
               }
               container rtg-config {
                 presence "enable rtg-config";
                 description "RTG Feature enable on AE";
                 uses apply-advanced;
                 leaf preempt-cutover-timer {
                   description "RTG preempt-cutover-timer in seconds";
                   default "1";
                   type union {
                     type string {
                       pattern "<.*>|$.*";
                     }
                     type uint32 {
                       range "0 .. 255";
                     }
                   }
                 }
               }
             }
             leaf sync-reset {
               description "On minimum-link failure notify out of sync to peer";
               type enumeration {
                 enum "disable" {
                   description "To disable minimum-link failure handling at LACP level";
                 }
                 enum "enable" {
                   description "To enable minimum-link failure handling at LACP level";
                 }
               }
             }
             leaf system-priority {
               description "Priority of the system (0 ... 65535)";
               type string;
             }
             leaf system-id {
               description "Node's System ID, encoded as a MAC address";
               type jt:mac-addr;
             }
             leaf admin-key {
               description "Node's administrative key";
               type union {
                 type uint16;
                 type string {
                   pattern "<.*>|$.*";
                 }
               }
             }
           }
           list link-protection-sub-group {
             key name;
             ordered-by user;
             description "Link Protection subgroup configuration";
             leaf name {
               description "Name of the subgroup";
               type string {
                 length "2 .. 64";
               }
             }
             uses apply-advanced;
             choice type {
               case case_1 {
                 leaf primary {
                   description "Primary subgroup for N:N link-protection mode";
                   type empty;
                 }
               }
               case case_2 {
                 leaf backup {
                   description "Backup subgroup for N:N link-protection mode";
                   type empty;
                 }
               }
             }
           }
           container ethernet-switch-profile {
             description "Ethernet virtual LAN/media access control-level options";
             uses apply-advanced;
             leaf-list tag-protocol-id {
               ordered-by user;
               description "IEEE 802.1q Tag Protocol Identifier values for VLAN-tagged frames";
               type string;
             }
             leaf mac-learn-enable {
               description "Learn MAC addresses dynamically";
               type empty;
             }
           }
         }
         container es-options {
           description "ES PIC interface-specific options";
           uses apply-advanced;
           leaf backup-interface {
             description "Name of backup interface";
             type union {
               type jt:interface-device;
               type string {
                 pattern "<.*>|$.*";
               }
             }
           }
         }
         container vdsl-options {
           description "VDSL interface-specific options";
           uses apply-advanced;
           leaf vdsl-profile {
             description "VDSL profile";
             type enumeration {
               enum "auto" {
                 description "Auto";
               }
               enum "8a" {
                 description "Profile 8a";
               }
               enum "8b" {
                 description "Profile 8b";
               }
               enum "8c" {
                 description "Profile 8c";
               }
               enum "8d" {
                 description "Profile 8d";
               }
               enum "12a" {
                 description "Profile 12a";
               }
               enum "12b" {
                 description "Profile 12b";
               }
               enum "17a" {
                 description "Profile 17a";
               }
             }
           }
           leaf sra {
             description "DSL SRA";
             default "disable";
             type enumeration {
               enum "enable" {
                 description "Enable SRA";
               }
               enum "disable" {
                 description "Disable SRA";
               }
             }
           }
           leaf v43 {
             description "DSL V43 tones";
             default "enable";
             type enumeration {
               enum "enable" {
                 description "Enable V43";
               }
               enum "disable" {
                 description "Disable V43";
               }
             }
           }
           leaf sos {
             description "Enable SOS";
             type empty;
           }
         }
         container dsl-sfp-options {
           description "DSL SFP options";
           uses apply-advanced;
           container adsl-options {
             description "ADSL options";
             uses apply-advanced;
             leaf vpi {
               description "Virtual path identifier";
               type union {
                 type string {
                   pattern "<.*>|$.*";
                 }
                 type uint32 {
                   range "0 .. 255";
                 }
               }
             }
             leaf vci {
               description "Virtual circuit identifier";
               type union {
                 type string {
                   pattern "<.*>|$.*";
                 }
                 type uint32 {
                   range "32 .. 65535";
                 }
               }
             }
             leaf encap {
               description "Encapsulation";
               type enumeration {
                 enum "bypass" {
                   description "Bypass";
                 }
                 enum "llcsnap-bridged-802dot1q" {
                   description "LLCSNAP bridged 802.1q";
                 }
                 enum "llcsnap-routed-ip" {
                   description "LLCSNAP routed ip";
                 }
                 enum "vc-mux-bridged" {
                   description "VC MUX bridged";
                 }
                 enum "vc-mux-routed-ip" {
                   description "VC MUX routed ip";
                 }
                 enum "generic" {
                   description "Generic";
                 }
               }
             }
             leaf annex {
               description "Annex type";
               type enumeration {
                 enum "auto" {
                   description "Annex type auto";
                 }
                 enum "annexj-off" {
                   description "Annex type annexj turn off";
                 }
               }
             }
           }
           container vdsl-options {
             description "VDSL options";
             uses apply-advanced;
             leaf profile {
               description "VDSL profile";
               type enumeration {
                 enum "auto" {
                   description "Automatic";
                 }
                 enum "8a" {
                   description "Profile 8a";
                 }
                 enum "8b" {
                   description "Profile 8b";
                 }
                 enum "8c" {
                   description "Profile 8c";
                 }
                 enum "8d" {
                   description "Profile 8d";
                 }
                 enum "12a" {
                   description "Profile 12a";
                 }
                 enum "12b" {
                   description "Profile 12b";
                 }
                 enum "17a" {
                   description "Profile 17a";
                 }
                 enum "30a" {
                   description "Profile 30a";
                 }
               }
             }
             leaf carrier {
               description "Carrier setting";
               type enumeration {
                 enum "auto" {
                   description "Automatic";
                 }
                 enum "a43" {
                   description "Carrier A43";
                 }
                 enum "b43" {
                   description "Carrier B43";
                 }
               }
             }
           }
           container gfast-options {
             description "G.fast options";
             uses apply-advanced;
             leaf carrier {
               description "Carrier setting";
               type enumeration {
                 enum "a43" {
                   description "Carrier A43";
                 }
                 enum "a43c" {
                   description "Carrier A43C";
                 }
                 enum "b43" {
                   description "Carrier B43";
                 }
                 enum "b43c" {
                   description "Carrier B43C";
                 }
               }
             }
           }
         }
         container shdsl-options {
           description "SHDSL interface-specific options";
           uses apply-advanced;
           leaf annex {
             description "Type of SHDSL annex";
             default "annex-b";
             type enumeration {
               enum "annex-a" {
                 description "Annex-a PIC";
               }
               enum "annex-b" {
                 description "Annex-b PIC";
               }
               enum "annex-f" {
                 description "Annex-f PIC";
               }
               enum "annex-g" {
                 description "Annex-g PIC";
               }
               enum "annex-auto" {
                 description "Annex-auto PIC";
               }
             }
           }
           leaf line-rate {
             description "SHDSL line rate";
             type string;
           }
           leaf loopback {
             description "Loopback mode";
             type enumeration {
               enum "local" {
                 description "Local loopback";
               }
               enum "remote" {
                 description "Remote loopback";
               }
             }
           }
           container snr-margin {
             presence "enable snr-margin";
             description "Signal to noise ratio margin";
             uses apply-advanced;
             leaf current {
               description "Current signal to noise ratio margin";
               units "dB";
               type string;
             }
             leaf snext {
               description "SNEXT signal to noise ratio margin";
               units "dB";
               type string;
             }
           }
         }
         container container-options {
           description "Container interface specific options";
           uses apply-advanced;
           container container-type {
             presence "enable container-type";
             description "Protocol type of the container interface";
             uses apply-advanced;
             choice container-type-choice {
               case case_1 {
                 container aps {
                   description "APS options on the container";
                   presence "enable aps";
                   uses aps_type;
                 }
               }
             }
           }
           container member-interface-type {
             description "Link type of members of container";
             uses apply-advanced;
             choice member_interface_type_choice {
               case case_1 {
                 container sonet {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                       enum "oc192" {
                         description "Links are OC-192";
                       }
                       enum "oc768" {
                         description "Links are OC-768";
                       }
                       enum "mixed" {
                         description "Links are of different speeds";
                       }
                     }
                     mandatory true;
                   }
                 }
               }
               case case_2 {
                 container atm {
                   uses apply-advanced;
                   leaf member-interface-speed {
                     description "Link speed of members of container";
                     type enumeration {
                       enum "oc3" {
                         description "Links are OC-3";
                       }
                       enum "oc12" {
                         description "Links are OC-12";
                       }
                       enum "oc48" {
                         description "Links are OC-48";
                       }
                     }
                     mandatory true;
                   }
                 }
               }
               case case_3 {
                 container channelized-sonet {
                   uses apply-advanced;
                   leaf member-interface-speed {
                     description "Link speed of members of container";
                     type enumeration {
                       enum "coc3" {
                         description "Links are COC-3";
                       }
                       enum "coc12" {
                         description "Links are COC-12";
                       }
                       enum "coc48" {
                         description "Links are COC-48";
                       }
                       enum "coc192" {
                         description "Links are COC-192";
                       }
                       enum "coc768" {
                         description "Links are COC-768";
                       }
                     }
                     mandatory true;
                   }
                 }
               }
               case case_4 {
                 container channelized-sdh {
                   uses apply-advanced;
                   leaf member-interface-speed {
                     description "Link speed of members of container";
                     type enumeration {
                       enum "cstm1" {
                         description "Links are cstm-1";
                       }
                       enum "cstm4" {
                         description "Links are cstm-4";
                       }
                       enum "cstm16" {
                         description "Links are cstm-16";
                       }
                       enum "coc64" {
                         description "Links are cstm-64";
                       }
                       enum "cstm256" {
                         description "Links are cstm256";
                       }
                     }
                     mandatory true;
                   }
                 }
               }
             }
           }
           container redundancy {
             description "Container interface redundancy options";
             uses apply-advanced;
             container hold-time {
               description "Hold time for link up and link down";
               leaf up {
                 description "Link up hold time";
                 units "milliseconds";
                 type union {
                   type string {
                     pattern "<.*>|$.*";
                   }
                   type uint32 {
                     range "0 .. 65534";
                   }
                 }
                 mandatory true;
               }
               leaf down {
                 description "Link down hold time";
                 units "milliseconds";
                 type union {
                   type string {
                     pattern "<.*>|$.*";
                   }
                   type uint32 {
                     range "0 .. 65534";
                   }
                 }
                 mandatory true;
               }
             }
           }
           leaf-list container-list {
             ordered-by user;
             description "List of container interfaces this member link is associated to";
             type union {
               type jt:interface-device;
               type string {
                 pattern "<.*>|$.*";
               }
             }
           }
           choice redundancy-type {
             case case_1 {
               choice aps-redundancy {
                 case case_1 {
                   leaf primary {
                     description "This member link is primary interface of the container";
                     type empty;
                   }
                 }
                 case case_2 {
                   leaf standby {
                     description "This member link is standby interface of the container";
                     type empty;
                   }
                 }
               }
             }
           }
           leaf fast-aps {
             description "Fast APS switch";
             type empty;
           }
           leaf allow-configuration-override {
             description "Allow physical configuration of member link to override container configuration";
             type empty;
           }
         }
         list unit {
           key name;
           description "Logical interface";
           leaf name {
             type string;
           }
           uses apply-advanced;
           leaf interface-tag {
             description "Interface tag name";
             type string {
               length "1 .. 64";
             }
           }
           leaf alias {
             description "Interface alias";
             type string;
           }
           container peer-psd {
             presence "enable peer-psd";
             description "Peer psd";
             leaf psd-name {
               description "Peer psd name";
               type string;
               mandatory true;
             }
           }
           container peer-interface {
             presence "enable peer-interface";
             description "Peer interface";
             uses apply-advanced;
             leaf interface-name {
               description "Peer interface name";
               type union {
                 type jt:interface-unit;
                 type string {
                   pattern "<.*>|$.*";
                 }
               }
             }
           }
           container interface-shared-with {
             presence "enable interface-shared-with";
             description "Specify which PSD owns this logical interface";
             uses apply-advanced;
             leaf psd-name {
               description "Name of protected system domain (psd[1-31], ex. psd2)";
               type string {
               }
               mandatory true;
             }
           }
           choice enable-disable {
             case case_1 {
               leaf disable {
                 description "Disable this logical interface";
                 type empty;
               }
             }
           }
           leaf extended-telemetry {
             description "Enable extended telemetry";
             type empty;
           }
           leaf passive-monitor-mode {
             description "Use interface to tap packets from another router";
             type empty;
           }
           leaf clear-dont-fragment-bit {
             description "Clear DF bit in packet (AS PIC and J-series only as well as MIF)";
             type empty;
           }
           leaf description {
             description "Text description of interface";
             type string;
           }
           leaf encapsulation {
             description "Logical link-layer encapsulation";
             type enumeration {
               enum "atm-nlpid" {
                 description "ATM NLPID encapsulation";
               }
               enum "atm-cisco-nlpid" {
                 description "Cisco-compatible ATM NLPID encapsulation";
               }
               enum "atm-snap" {
                 description "ATM LLC/SNAP encapsulation";
               }
               enum "atm-vc-mux" {
                 description "ATM VC multiplexing";
               }
               enum "atm-ccc-vc-mux" {
                 description "ATM VC for CCC";
               }
               enum "atm-tcc-vc-mux" {
                 description "ATM VC for translational cross-connect";
               }
               enum "atm-tcc-snap" {
                 description "ATM LLC/SNAP for translational cross-connect";
               }
               enum "atm-ccc-cell-relay" {
                 description "ATM cell relay for CCC";
               }
               enum "vlan-vci-ccc" {
                 description "CCC for VLAN Q-in-Q and ATM VPI/VCI interworking";
               }
               enum "ether-over-atm-llc" {
                 description "Ethernet over ATM (LLC/SNAP) encapsulation";
               }
               enum "ether-vpls-over-atm-llc" {
                 description "Ethernet VPLS over ATM (bridging) encapsulation";
               }
               enum "ppp-over-ether-over-atm-llc" {
                 description "PPPoE over ATM (LLC/SNAP) encapsulation";
               }
               enum "ppp-over-ether" {
                 description "PPPoE encapsulation";
               }
               enum "atm-ppp-vc-mux" {
                 description "ATM PPP over raw AAL5";
               }
               enum "atm-ppp-llc" {
                 description "ATM PPP over AAL5/LLC";
               }
               enum "atm-ppp-funi" {
                 description "ATM PPP over FUNI";
               }
               enum "atm-mlppp-llc" {
                 description "ATM MLPPP over AAL5/LLC";
               }
               enum "frame-relay-ppp" {
                 description "PPP over Frame Relay";
               }
               enum "frame-relay-ccc" {
                 description "Frame Relay DLCI for CCC";
               }
               enum "frame-relay" {
                 description "Frame Relay DLCI";
               }
               enum "frame-relay-tcc" {
                 description "Frame Relay DLCI for translational cross-connect";
               }
               enum "frame-relay-ether-type" {
                 description "Cisco-compatible Frame Relay Encapsulation DLCI";
               }
               enum "frame-relay-ether-type-tcc" {
                 description "Cisco-compatible Frame Relay Encapsulation DLCI for TCC";
               }
               enum "ether-vpls-fr" {
                 description "Ethernet VPLS over Frame Relay (bridging) encapsulation";
               }
               enum "vlan-ccc" {
                 description "802.1q tagging for a cross-connect";
               }
               enum "ethernet-ccc" {
                 description "Ethernet for a cross-connect";
               }
               enum "vlan-vpls" {
                 description "VLAN virtual private LAN service";
               }
               enum "vlan-bridge" {
                 description "VLAN layer-2 bridging";
               }
               enum "ethernet-tcc" {
                 description "Ethernet translational cross-connect";
               }
               enum "dix" {
                 description "Ethernet DIXv2 (RFC 894)";
               }
               enum "ethernet" {
                 description "Ethernet II (RFC 894)";
               }
               enum "ethernet-vpls" {
                 description "Ethernet II virtual private LAN service";
               }
               enum "ethernet-bridge" {
                 description "Ethernet II bridging";
               }
               enum "vlan" {
                 description "802.1q-tagged Ethernet";
               }
               enum "vlan-tcc" {
                 description "802.1q tagging for a translational cross-connect";
               }
               enum "multilink-ppp" {
                 description "Multilink PPP";
               }
               enum "multilink-frame-relay-end-to-end" {
                 description "Multilink Frame Relay end-to-end (FRF.15)";
               }
               enum "ppp-ccc" {
                 description "Serial PPP device for a cross-connect";
               }
             }
           }
           leaf mtu {
             description "Maximum transmission unit packet size";
             type union {
               type string {
                 pattern "<.*>|$.*";
               }
               type uint32;
             }
           }
           choice pointedness {
             case case_1 {
               leaf point-to-point {
                 description "Point-to-point connection";
                 type empty;
               }
             }
             case case_2 {
               leaf multipoint {
                 description "Multipoint connection";
                 type empty;
               }
             }
           }
           leaf bandwidth {
             description "Logical unit bandwidth (informational only)";
             type string;
           }
           choice traps-choice {
             leaf traps {
               description "Enable SNMP notifications on state changes";
               type empty;
             }
             leaf no-traps {
               description "Don't enable SNMP notifications on state changes";
               type empty;
             }
           }
           choice routing-services-choice {
             leaf routing-services {
               description "Enable routing services";
               status deprecated;
               type empty;
             }
             leaf no-routing-services {
               description "Don't enable routing services";
               status deprecated;
               type empty;
             }
           }
           container routing-service {
             description "Routing Services on this interface";
             uses apply-advanced;
             choice enable-disable {
               case case_1 {
                 leaf enable {
                   description "Enable Routing Service";
                   type empty;
                 }
               }
               case case_2 {
                 leaf disable {
                   description "Disable Routing Service";
                   type empty;
                 }
               }
             }
           }
           container arp-resp {
             presence "enable arp-resp";
             description "Knob to control ARP response on the interface, default is restricted";
             choice arp-response-options {
               case case_1 {
                 leaf unrestricted {
                   description "Enable unrestricted ARP respone on the interface";
                   type empty;
                 }
               }
               case case_2 {
                 leaf restricted {
                   description "Enable restricted proxy ARP response on the interface";
                   type empty;
                 }
               }
             }
           }
           container proxy-arp {
             presence "enable proxy-arp";
             description "Enable proxy ARP on the interface, default is unrestricted";
             choice proxyarp-options {
               case case_1 {
                 leaf unrestricted {
                   description "Enable unrestricted proxy ARP on the interface";
                   type empty;
                 }
               }
               case case_2 {
                 leaf restricted {
                   description "Enable restricted proxy ARP on the interface";
                   type empty;
                 }
               }
             }
           }
           choice vlan_choice {
             case case_1 {
               leaf vlan-id {
                 description "Virtual LAN identifier value for 802.1q VLAN tags";
                 type string;
               }
             }
             case case_2 {
               leaf vlan-id-range {
                 description "Virtual LAN identifier range of form vid1-vid2";
                 type jt:vlan-range;
               }
             }
             case case_3 {
               leaf-list inner-vlan-id-swap-ranges {
                 description "Inner vlan-id swap range(s) of form vid1-vid2 for dynamic L2 VLANs";
                 type jt:vlan-range;
               }
             }
             case case_4 {
               leaf-list vlan-id-list {
                 description "List of VLAN identifiers";
                 type jt:vlan-range;
               }
             }
             case case_5 {
               leaf-list vlan-tag {
                 ordered-by user;
                 description "IEEE 802.1q tag list for VLAN tagged frames";
                 status deprecated;
                 type string;
               }
             }
             case case_6 {
               container vlan-tags {
                 presence "enable vlan-tags";
                 description "IEEE 802.1q tags";
                 leaf outer {
                   description "[tpid.]vlan-id, tpid format is 0xNNNN and is optional";
                   type string;
                   mandatory true;
                 }
                 choice inner_choice {
                   case case_1 {
                     leaf inner {
                       description "[tpid.]vlan-id, tpid format is 0xNNNN and is optional";
                       type string;
                     }
                   }
                   case case_2 {
                     leaf inner-range {
                       description "[tpid.]vid1-vid2, tpid format is 0xNNNN and is optional";
                       type string {
                       }
                     }
                   }
                   case case_3 {
                     leaf-list inner-list {
                       description "List of VLAN identifiers";
                       type jt:vlan-range;
                     }
                   }
                 }
               }
             }
           }
           leaf native-inner-vlan-id {
             description "Native virtual LAN identifier for singly tagged frames";
             type union {
               type string {
                 pattern "<.*>|$.*";
               }
               type uint32 {
                 range "0 .. 4094";
               }
             }
           }
           container accept-source-mac {
             description "Remote media access control address to/from which to accept traffic";
             uses apply-advanced;
             list mac-address {
               key name;
               description "Remote MAC address";
               uses mac_list;
             }
           }
           container input-vlan-map {
             description "VLAN map operation on input";
             uses vlan_map;
           }
           container output-vlan-map {
             description "VLAN map operation on output";
             uses vlan_map;
           }
           leaf swap-by-poppush {
             description "Pop original vlan tag and then push a new vlan tag";
             type empty;
           }
           leaf receive-lsp {
             description "Name of incoming label-switched path";
             type string;
           }
           leaf transmit-lsp {
             description "Name of outgoing label-switched path";
             type string;
           }
           leaf dlci {
             description "Frame Relay data-link control identifier";
             type union {
               type string {
                 pattern "<.*>|$.*";
               }
               type uint32 {
                 range "1 .. 1022";
               }
             }
           }
           leaf multicast-dlci {
             description "Frame Relay data-link control identifier for multicast packets";
             type union {
               type string {
                 pattern "<.*>|$.*";
               }
               type uint32 {
                 range "1 .. 1022";
               }
             }
           }
           choice vci_type {
             case case_1 {
               leaf vci {
                 description "ATM point-to-point virtual circuit identifier ([vpi.]vci)";
                 type jt:atm-vci;
               }
             }
             case case_2 {
               leaf allow-any-vci {
                 description "Allow all VCIs to open in atm-ccc-cell-relay mode";
                 type empty;
               }
             }
             case case_3 {
               leaf vpi {
                 description "ATM point-to-point virtual path identifier (vpi)";
                 type union {
                   type string {
                     pattern "<.*>|$.*";
                   }
                   type uint32 {
                     range "0 .. 255";
                   }
                 }
               }
             }
             case case_4 {
               leaf trunk-id {
                 description "ATM trunk identifier";
                 type union {
                   type string {
                     pattern "<.*>|$.*";
                   }
                   type uint32 {
                     range "0 .. 31";
                   }
                 }
               }
             }
           }
           choice psn_vci_type {
             case case_1 {
             }
             case case_2 {
             }
           }
           container atm-l2circuit-mode {
             description "Select ATM Layer 2 circuit transport mode";
             choice mode_choice {
               case case_1 {
                 leaf cell {
                   description "ATM Layer 2 circuit cell mode";
                   type empty;
                 }
               }
               case case_2 {
                 leaf aal5 {
                   description "ATM Layer 2 circuit AAL5 mode";
                   type empty;
                 }
               }
             }
           }
           container vci-range {
             description "ATM VCI range start <start-vci> end <end-vci>";
             leaf start {
               description "ATM VCI range's start value";
               type union {
                 type string {
                   pattern "<.*>|$.*";
                 }
                 type uint16 {
                   range "32 .. 4094";
                 }
               }
               mandatory true;
             }
             leaf end {
               description "ATM VCI range's end value";
               type union {
                 type string {
                   pattern "<.*>|$.*";
                 }
                 type uint16 {
                   range "32 .. 4094";
                 }
               }
               mandatory true;
             }
           }
           leaf trunk-bandwidth {
             description "ATM trunk bandwidth";
             units "bits per second";
             type string;
           }
           leaf multicast-vci {
             description "ATM virtual circuit identifier for multicast packets";
             type jt:atm-vci;
           }
           container shaping {
             description "Virtual circuit traffic-shaping options";
             uses dcd_shaping_config;
           }
           container oam-period {
             description "OAM cell period";
             choice oam_period_choices {
               case case_1 {
                 leaf oam-period {
                   description "OAM cell period";
                   units "seconds";
                   type union {
                     type string {
                       pattern "<.*>|$.*";
                     }
                     type uint32 {
                       range "1 .. 900";
                     }
                   }
                 }
               }
               case case_2 {
                 container disable {
                   presence "enable disable";
                   description "Disable F5 OAM loopback";
                 }
               }
             }
           }
           container oam-liveness {
             description "OAM virtual circuit liveness parameters";
             uses apply-advanced;
             leaf up-count {
               description "Number of OAM cells to consider VC up";
               type union {
                 type string {
                   pattern "<.*>|$.*";
                 }
                 type uint32 {
                   range "1 .. 255";
                 }
               }
             }
             leaf down-count {
               description "Number of OAM cells to consider VC down";
               type union {
                 type string {
                   pattern "<.*>|$.*";
                 }
                 type uint32 {
                   range "1 .. 255";
                 }
               }
             }
           }
           container ppp-options {
             description "Point-to-Point Protocol interface-specific options";
             uses ppp_options_type;
           }
           choice keepalive_choices {
             case case_1 {
               container keepalives {
                 description "Send or demand keepalive messages";
                 presence "enable keepalives";
                 uses keepalives_type;
               }
             }
             case case_2 {
               leaf no-keepalives {
                 description "Do not send or demand keepalive messages";
                 type empty;
               }
             }
           }
           leaf inverse-arp {
             description "Enable inverse ARP";
             type empty;
           }
           leaf transmit-weight {
             description "ATM2 transmit weight for VC under VP tunnel";
             type union {
               type string {
                 pattern "<.*>|$.*";
               }
               type uint16 {
                 range "1 .. 32767";
               }
             }
           }
           container epd-threshold {
             description "Early packet discard threshold for ATM2";
             uses epd_threshold_config;
           }
           leaf cell-bundle-size {
             description "L2 circuit cell bundle size";
             units "cells";
             type union {
               type string {
                 pattern "<.*>|$.*";
               }
               type uint32 {
                 range "1 .. 176";
               }
             }
           }
           leaf cell-bundle-timeout {
             description "L2 circuit cell bundle timeout";
             units "microseconds";
             type union {
               type string {
                 pattern "<.*>|$.*";
               }
               type uint32 {
                 range "1 .. 512";
               }
             }
           }
           leaf plp-to-clp {
             description "Enable ATM2 PLP to CLP copy";
             type empty;
           }
           leaf atm-scheduler-map {
             description "Assign ATM2 CoS scheduling map";
             type union {
               type string {
                 pattern "default";
               }
               type string;
             }
           }
           leaf mrru {
             description "Maximum received reconstructed unit";
             units "bytes";
             type union {
               type string {
                 pattern "<.*>|$.*";
               }
               type uint16 {
                 range "1500 .. 4500";
               }
             }
           }
           leaf short-sequence {
             description "Short sequence number header format (MLPPP only)";
             type empty;
           }
           leaf fragment-threshold {
             description "Fragmentation threshold";
             units "bytes";
             type union {
               type string {
                 pattern "<.*>|$.*";
               }
               type uint32 {
                 range "64 .. 4500";
               }
             }
           }
           leaf drop-timeout {
             description "Drop timeout";
             units "milliseconds";
             type union {
               type string {
                 pattern "<.*>|$.*";
               }
               type uint16 {
                 range "0 .. 2000";
               }
             }
           }
           leaf disable-mlppp-inner-ppp-pfc {
             description "Disable compression for inner PPP header in MLPPP payload";
             type empty;
           }
           leaf minimum-links {
             description "Minimum number of links to sustain the bundle";
             type union {
               type string {
                 pattern "<.*>|$.*";
               }
               type uint16;
             }
           }
           leaf multilink-max-classes {
             description "Number of multilink classes";
             type union {
               type string {
                 pattern "<.*>|$.*";
               }
               type uint16;
             }
           }
           leaf interleave-fragments {
             description "Interleave long packets with high priority ones";
             type empty;
           }
           leaf link-layer-overhead {
             description "Link layer bit stuffing overhead (0.0 .. 50.0 percent)";
             type jt:unsigned-float;
           }
           leaf accounting-profile {
             description "Accounting profile name";
             type string;
           }
           leaf peer-unit {
             description "Peer unit number";
             type union {
               type string {
                 pattern "<.*>|$.*";
               }
               type uint32 {
                 range "0 .. 16385";
               }
             }
           }
           container tunnel {
             description "Tunnel parameters";
             uses apply-advanced;
             container encapsulation {
               presence "enable encapsulation";
               description "Encapsulation over tunnel";
               container vxlan-gpe {
                 presence "enable vxlan-gpe";
                 uses apply-advanced;
                 container source {
                   uses apply-advanced;
                   leaf address {
                     description "Interface address prefix";
                     type jt:ipv4addr;
                   }
                   leaf mac-address {
                     description "Interface source mac address";
                     type jt:mac-addr;
                   }
                   leaf interface {
                     description "Name of the interface";
                     type union {
                       type jt:interface-name;
                       type string {
                         pattern "<.*>|$.*";
                       }
                     }
                   }
                 }
                 container destination {
                   uses apply-advanced;
                   leaf address {
                     description "Interface address prefix";
                     type jt:ipv4addr;
                   }
                   leaf mac-address {
                     description "Interface destination mac address";
                     type jt:mac-addr;
                   }
                 }
                 leaf tunnel-endpoint {
                   description "Tunnel end point type";
                   type enumeration {
                     enum "vxlan" {
                       description "To configure vxlan tunnel-end-point";
                     }
                   }
                   mandatory true;
                 }
                 container source-udp-port-range {
                   description "Value range for source-udp-port";
                   leaf min {
                     description "Minimum range value";
                     type union {
                       type string {
                         pattern "<.*>|$.*";
                       }
                       type uint32 {
                         range "1 .. 65535";
                       }
                     }
                     mandatory true;
                   }
                   leaf max {
                     description "Maximum range value";
                     type union {
                       type string {
                         pattern "<.*>|$.*";
                       }
                       type uint32 {
                         range "1 .. 65535";
                       }
                     }
                     mandatory true;
                   }
                 }
                 leaf destination-udp-port {
                   description "Value to write to the destination-udp-port field";
                   type union {
                     type string {
                       pattern "<.*>|$.*";
                     }
                     type uint32 {
                       range "1 .. 65535";
                     }
                   }
                   mandatory true;
                 }
                 leaf vni {
                   description "Value to write to the vni field";
                   type union {
                     type string {
                       pattern "<.*>|$.*";
                     }
                     type uint32 {
                       range "0 .. 16777214";
                     }
                   }
                   mandatory true;
                 }
               }
             }
             choice source_type {
               case case_1 {
                 leaf source {
                   description "Tunnel source address";
                   type jt:ipaddr;
                 }
               }
               case case_2 {
               }
               case case_3 {
               }
             }
             choice destination_type {
               case case_1 {
                 leaf destination {
                   description "Tunnel destination address";
                   type jt:ipaddr;
                 }
               }
               case case_2 {
               }
             }
             leaf backup-destination {
               description "Backup tunnel destination";
               type jt:ipaddr;
             }
             choice fragmentation {
               case case_1 {
                 leaf allow-fragmentation {
                   description "Do not set DF bit on packets";
                   type empty;
                 }
               }
               case case_2 {
                 leaf do-not-fragment {
                   description "Set DF bit on packets";
                   type empty;
                 }
               }
             }
             leaf ttl {
               description "Time to live";
               type union {
                 type string {
                   pattern "<.*>|$.*";
                 }
                 type uint32 {
                   range "1 .. 255";
                 }
               }
             }
             leaf traffic-class {
               description "TOS/Traffic class field of IP-header";
               type union {
                 type string {
                   pattern "<.*>|$.*";
                 }
                 type uint32 {
                   range "0 .. 255";
                 }
               }
             }
             leaf flow-label {
               description "Flow label field of IP6-header";
               type union {
                 type string {
                   pattern "<.*>|$.*";
                 }
                 type uint32 {
                   range "0 .. 1048575";
                 }
               }
             }
             choice path-mtu-discovery-choice {
               leaf path-mtu-discovery {
                 description "Enable path MTU discovery for tunnels";
                 type empty;
               }
               leaf no-path-mtu-discovery {
                 description "Don't enable path MTU discovery for tunnels";
                 type empty;
               }
             }
             container routing-instance {
               description "Routing instance to which tunnel ends belong";
               uses apply-advanced;
               leaf destination {
                 description "Routing instance of tunnel destination";
                 type string {
                 }
               }
             }
           }
           leaf compression-device {
             description "Logical interface used for compression";
             type union {
               type jt:interface-unit;
               type string {
                 pattern "<.*>|$.*";
               }
             }
           }
           container layer2-policer {
             description "Layer2 policing for logical interface";
             uses apply-advanced;
             choice layer2-input-policer-choice {
               case case_1 {
                 leaf input-policer {
                   description "Two-color policer for received packets";
                   type string;
                 }
               }
               case case_2 {
               }
               case case_3 {
                 leaf input-three-color {
                   description "Color-blind three-color policer for received packets";
                   type string;
                 }
               }
             }
             choice layer2-output-policer-choice {
               case case_1 {
                 leaf output-policer {
                   description "Two-color policer for transmitted packets";
                   type string;
                 }
               }
               case case_2 {
                 leaf output-three-color {
                   description "Three-color policer for transmitted packets";
                   type string;
                 }
               }
             }
           }
           choice virtual-gateway {
             case case_1 {
               leaf no-auto-virtual-gateway-esi {
                 description "Disable auto ESI generation for virtual gateway address";
                 type empty;
               }
             }
             case case_2 {
               container virtual-gateway-esi {
                 description "ESI configuration of virtual gateway";
                 uses apply-advanced;
                 leaf identifier {
                   description "ESI value for the interface";
                   type jt:esi;
                   mandatory true;
                 }
                 choice mode {
                   case case_1 {
                     leaf single-active {
                       description "Single-active mode";
                       type empty;
                     }
                   }
                   case case_2 {
                     leaf all-active {
                       description "All-active mode";
                       type empty;
                     }
                   }
                 }
               }
             }
           }
           container service {
             description "Service operations";
             uses apply-advanced;
             list pcef {
               key name;
               ordered-by user;
               description "PCEF configuration";
               leaf name {
                 description "PCEF Profile name";
                 type string;
                 mandatory true;
               }
               uses apply-advanced;
               leaf activate-all {
                 description "Activate all rules and rulebases in the pcef profile";
                 type empty;
               }
               list activate {
                 key name;
                 ordered-by user;
                 description "Name of pcef profile rule or rulebase to activate";
                 leaf name {
                   description "Name of pcef profile rule or rulebase to activate";
                   type string;
                 }
                 uses apply-advanced;
               }
             }
           }
           choice generate-eui64-choice {
             leaf generate-eui64 {
               description "To generate Link Local EUI-64 addresses";
               type empty;
             }
             leaf no-generate-eui64 {
               description "Don't to generate Link Local EUI-64 addresses";
               type empty;
             }
           }
           container family {
             description "Protocol family";
             container inet {
               presence "enable inet";
               description "IPv4 parameters";
               uses apply-advanced;
               container class-based-filtering {
                 description "Enable class based filter on interface";
                 uses apply-advanced;
               }
               container dhcp {
                 description "Dynamic Host Configuration Protocol client configuration";
                 presence "enable dhcp";
                 uses dhcp-client-type;
               }
               leaf destination-class-usage {
                 description "Enable destination class usage on this interface";
                 status deprecated;
                 type empty;
               }
               leaf transit-options-packets {
                 description "Transit IP options packets (don't send to Routing Engine)";
                 status deprecated;
                 type empty;
               }
               leaf transit-ttl-exceeded {
                 description "Transit IP TTL-exceeded packets (don't send to Routing Engine)";
                 status deprecated;
                 type empty;
               }
               leaf receive-options-packets {
                 description "Receive IP options packets (don't send to Routing Engine)";
                 type empty;
               }
               leaf receive-ttl-exceeded {
                 description "Receive IP TTL-exceeded packets (don't send to Routing Engine)";
                 type empty;
               }
               container accounting {
                 description "Configure interface-based accounting options";
                 uses apply-advanced;
                 container source-class-usage {
                   description "Enable source class usage on this interface";
                   uses apply-advanced;
                   leaf input {
                     description "Specify this interface for source-class-usage input";
                     type empty;
                   }
                   leaf output {
                     description "Specify this interface for source-class-usage output";
                     type empty;
                   }
                 }
                 leaf destination-class-usage {
                   description "Enable destination class usage on this interface";
                   type empty;
                 }
               }
               leaf mtu {
                 description "Protocol family maximum transmission unit";
                 type union {
                   type uint32;
                   type string {
                     pattern "<.*>|$.*";
                   }
                 }
               }
               leaf arp-max-cache {
                 description "Max interface ARP nexthop cache size";
                 type union {
                   type string {
                     pattern "<.*>|$.*";
                   }
                   type uint32 {
                     range "1 .. 2000000";
                   }
                 }
               }
               leaf arp-new-hold-limit {
                 description "Max no. of new unresolved nexthops";
                 type union {
                   type string {
                     pattern "<.*>|$.*";
                   }
                   type uint32 {
                     range "1 .. 2000000";
                   }
                 }
               }
               leaf no-redirects {
                 description "Do not redirect traffic";
                 type empty;
               }
               leaf nat-outside-interface {
                 description "Public interface used for NAT";
                 type empty;
               }
               leaf no-neighbor-learn {
                 description "Disable neighbor address learning on interface";
                 type empty;
               }
               leaf unconditional-src-learn {
                 description "Glean from arp packets even when source cannot be validated";
                 type empty;
               }
               leaf multicast-only {
                 description "Allow only multicast traffic (tunnels only)";
                 type empty;
               }
               leaf primary {
                 description "Candidate for primary interface in system";
                 type empty;
               }
               leaf ipsec-sa {
                 description "Name of security association";
                 type string {
                   length "1 .. 32";
                 }
               }
               leaf allow-filter-on-re {
                 description "Enable kernel filter on network ports";
                 type empty;
               }
               container filter {
                 description "Packet filtering";
                 uses apply-advanced;
                 choice input_choice {
                   case case_1 {
                     container input {
                       description "Filter to be applied to received packets";
                       leaf filter-name {
                         description "Name of the filter";
                         type string;
                         mandatory true;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list input-list {
                       ordered-by user;
                       description "List of filter modules applied to received packets ";
                       type string;
                     }
                   }
                 }
                 choice output_choice {
                   case case_1 {
                     container output {
                       description "Filter to be applied to transmitted packets";
                       leaf filter-name {
                         description "Name of the filter";
                         type string;
                         mandatory true;
                       }
                       leaf shared-name {
                         description "Filter shared-name of instances of interface-shared filter";
                         type string;
                       }
                       leaf precedence {
                         description "Precedence of the filter";
                         type union {
                           type string {
                             pattern "<.*>|$.*";
                           }
                           type uint32 {
                             range "0 .. 255";
                           }
                         }
                       }
                     }
                   }
                   case case_2 {
                     leaf-list output-list {
                       ordered-by user;
                       description "List of filter modules applied to transmitted packets ";
                       type string;
                     }
                   }
                 }
                 container adf {
                   description "Ascend Data Filter definition";
                   uses apply-advanced;
                   list rule {
                     key name;
                     ordered-by user;
                     description "Set of ADF rules";
                     leaf name {
                       description "Value for a single rule";
                       type string;
                     }
                     uses apply-advanced;
                   }
                   leaf counter {
                     description "Add a counter to each rule";
                     type empty;
                   }
                   leaf input-precedence {
                     description "Precedence of the input rules";
                     type union {
                       type string {
                         pattern "<.*>|$.*";
                       }
                       type uint32 {
                         range "0 .. 255";
                       }
                     }
                   }
                   leaf not-mandatory {
                     description "No errors will be reported if no rules are present";
                     type empty;
                   }
                   leaf output-precedence {
                     description "Precedence of the output rules";
                     type union {
                       type string {
                         pattern "<.*>|$.*";
                       }
                       type uint32 {
                         range "0 .. 255";
                       }
                     }
                   }
                 }
                 leaf group {
                   description "Group to which interface belongs";
                   type union {
                     type string {
                       pattern "<.*>|$.*";
                     }
                     type uint32;
                   }
                 }
               }
               container simple-filter {
                 description "Filter for doing multifield classification";
                 uses apply-advanced;
                 leaf input {
                   description "Name of simple filter applied to received packets";
                   type string;
                 }
               }
               container policer {
                 description "Interface policing";
                 uses apply-advanced;
                 leaf arp {
                   description "Name of policer applied to received ARP packets";
                   type string;
                 }
                 leaf input {
                   description "Name of policer applied to received packets";
                   type string;
                 }
                 leaf output {
                   description "Name of policer applied to transmitted packets";
                   type string;
                 }
               }
               container sampling {
                 description "Interface sampling";
                 uses apply-advanced;
                 leaf input {
                   description "Sample all packets input on this interface";
                   type empty;
                 }
                 leaf output {
                   description "Sample all packets output on this interface";
                   type empty;
                 }
               }
               container service {
                 description "Service operations";
                 uses apply-advanced;
                 container input {
                   description "Service sets to consider for received packets";
                   uses apply-advanced;
                   list service-set {
                     key name;
                     ordered-by user;
                     description "Service set to consider for received packets";
                     leaf name {
                       description "Name of service set";
                       type string {
                       }
                     }
                     uses apply-advanced;
                     leaf service-filter {
                       description "Name of service filter";
                       type string;
                     }
                   }
                   leaf post-service-filter {
                     description "Post-service filter to apply to received packets";
                     type string;
                   }
                 }
                 container output {
                   description "Service sets to consider for transmitted packets";
                   uses apply-advanced;
                   list service-set {
                     key name;
                     ordered-by user;
                     description "Service set to consider for transmitted packets";
                     leaf name {
                       description "Name of service set";
                       type string {
                       }
                     }
                     uses apply-advanced;
                     leaf service-filter {
                       description "Name of service filter";
                       type string;
                     }
                   }
                 }
               }
               list next-hop-tunnel {
                 key name;
                 ordered-by user;
                 description "One or more next-hop tunnel tables";
                 leaf name {
                   description "Next-hop tunnel gateway address";
                   type string;
                   mandatory true;
                 }
                 uses apply-advanced;
                 leaf ipsec-vpn {
                   description "Name of IPSec VPN";
                   type string;
                   mandatory true;
                 }
               }
               choice tunnel-termination-status {
                 case case_1 {
                   leaf tunnel-termination {
                     description "Tunnel termination";
                     type empty;
                   }
                 }
                 case case_2 {
                   leaf no-tunnel-termination {
                     description "No Tunnel termination";
                     type empty;
                   }
                 }
               }
               list address {
                 key name;
                 ordered-by user;
                 description "Interface address/destination prefix";
                 leaf name {
                   description "Interface address/destination prefix";
                   type jt:ipv4prefix;
                 }
                 uses apply-advanced;
                 leaf destination {
                   description "Destination address";
                   type jt:ipv4addr;
                 }
                 leaf destination-profile {
                   description "Profile to use for destination address";
                   type string;
                 }
                 leaf broadcast {
                   description "Broadcast address";
                   type jt:ipv4addr;
                 }
                 leaf primary {
                   description "Candidate for primary address in system";
                   type empty;
                 }
                 leaf preferred {
                   description "Preferred address on interface";
                   type empty;
                 }
                 leaf master-only {
                   description "Master management IP address for router";
                   type empty;
                 }
                 container tag {
                   description "Tag used for route/local";
                   uses apply-advanced;
                   leaf tag-value {
                     description "The tag value on the address";
                     type union {
                       type string {
                         pattern "<.*>|$.*";
                       }
                       type uint32 {
                         range "1 .. 4294967295";
                       }
                     }
                     mandatory true;
                   }
                   leaf type {
                     description "Tag type must be [1-16]";
                     type union {
                       type string {
                         pattern "<.*>|$.*";
                       }
                       type uint32 {
                         range "1 .. 16";
                       }
                     }
                   }
                 }
                 container tag2 {
                   description "Tag2 used for route/local";
                   uses apply-advanced;
                   leaf tag2-value {
                     description "The tag value on the address";
                     type union {
                       type string {
                         pattern "<.*>|$.*";
                       }
                       type uint32 {
                         range "1 .. 4294967295";
                       }
                     }
                     mandatory true;
                   }
                   leaf type {
                     description "Tag type must be [1-16]";
                     type union {
                       type string {
                         pattern "<.*>|$.*";
                       }
                       type uint32 {
                         range "1 .. 16";
                       }
                     }
                   }
                 }
                 list multipoint-destination {
                   key name;
                   ordered-by user;
                   description "Multipoint NBMA destination";
                   leaf name {
                     description "Destination address";
                     type jt:ipv4addr;
                   }
                   uses apply-advanced;
                   choice link-address {
                     case case_1 {
                       leaf dlci {
                         description "Frame Relay data-link control identifier";
                         type union {
                           type string {
                             pattern "<.*>|$.*";
                           }
                           type uint32 {
                             range "1 .. 1022";
                           }
                         }
                       }
                     }
                     case case_2 {
                       leaf vci {
                         description "ATM virtual circuit identifier ([vpi.]vci)";
                         type jt:atm-vci;
                       }
                     }
                   }
                   container shaping {
                     description "Virtual circuit traffic-shaping options";
                     uses dcd_shaping_config;
                   }
                   container oam-period {
                     description "OAM cell period";
                     choice oam_period_choices {
                       case case_1 {
                         leaf oam_period {
                           description "OAM cell period";
                           units "seconds";
                           type union {
                             type string {
                               pattern "<.*>|$.*";
                             }
                             type uint32 {
                               range "1 .. 900";
                             }
                           }
                         }
                       }
                       case case_2 {
                         container disable {
                           presence "enable disable";
                           description "Disable OAM loopback";
                         }
                       }
                     }
                   }
                   container oam-liveness {
                     description "OAM virtual circuit liveness parameters";
                     uses apply-advanced;
                     leaf up-count {
                       description "Number of OAM cells to consider VC up";
                       type union {
                         type string {
                           pattern "<.*>|$.*";
                         }
                         type uint32 {
                           range "1 .. 255";
                         }
                       }
                     }
                     leaf down-count {
                       description "Number of OAM cells to consider VC down";
                       type union {
                         type string {
                           pattern "<.*>|$.*";
                         }
                         type uint32 {
                           range "1 .. 255";
                         }
                       }
                     }
                   }
                   leaf inverse-arp {
                     description "Enable inverse ARP reply messages";
                     type empty;
                   }
                   leaf transmit-weight {
                     description "ATM2 transmit weight for VC under VP tunnel";
                     type union {
                       type string {
                         pattern "<.*>|$.*";
                       }
                       type uint16 {
                         range "1 .. 32767";
                       }
                     }
                   }
                   container epd-threshold {
                     description "Early packet discard threshold for ATM2";
                     uses epd_threshold_config;
                   }
                 }
                 list arp {
                   key name;
                   ordered-by user;
                   description "Static Address Resolution Protocol entries";
                   leaf name {
                     description "Destination IP address";
                     type jt:ipv4addr;
                     mandatory true;
                   }
                   leaf l2-interface {
                     description "Layer 2 interface name for ARP entry";
                     type union {
                       type jt:interface-name;
                       type string {
                         pattern "<.*>|$.*";
                       }
                     }
                   }
                   choice mac_address_type {
                     case case_1 {
                       leaf mac {
                         description "MAC address";
                         type jt:mac-unicast;
                       }
                     }
                     case case_2 {
                       leaf multicast-mac {
                         description "Multicast MAC address";
                         type jt:mac-multicast;
                       }
                     }
                   }
                   leaf publish {
                     description "Reply to ARP requests for this entry";
                     type empty;
                   }
                   leaf flood-as-unknown-unicast {
                     description "Broadcast the packet with unicast MAC";
                     type empty;
                   }
                 }
                 list vrrp-group {
                   key name;
                   ordered-by user;
                   description "VRRP group";
                   uses vrrp-group;
                 }
                 leaf virtual-gateway-address {
                   description "Virtual Gateway IP address";
                   type jt:ipv4addr;
                 }
               }
               container unnumbered-address {
                 description "Unnumbered interface address/destination prefix";
                 leaf source {
                   description "Interface from which to take local address";
                   type union {
                     type jt:interface-unit;
                     type string {
                       pattern "<.*>|$.*";
                     }
                   }
                   mandatory true;
                 }
                 leaf preferred-source-address {
                   description "Preferred address on the donor interface";
                   type string;
                 }
                 leaf destination {
                   description "Destination address";
                   type jt:ipv4addr;
                 }
                 leaf destination-profile {
                   description "Profile to use for destination address";
                   type string;
                 }
               }
               leaf negotiate-address {
                 description "Negotiate address with remote";
                 type empty;
               }
               leaf destination-udp-port {
                 description "Choose destination UDP port number";
                 type union {
                   type string {
                     pattern "<.*>|$.*";
                   }
                   type uint32 {
                     range "10000 .. 10009";
                   }
                 }
               }
               container auto-configure {
                 description "Auto configuration";
                 uses dynamic_ipv4_type;
               }
             }
             container mlppp {
               description "Multilink PPP protocol parameters";
               uses apply-advanced;
               leaf bundle {
                 description "Logical interface name this link will join";
                 type string;
                 mandatory true;
               }
               choice anchor-points {
                 case case_1 {
                 }
                 case case_2 {
                 }
               }
               leaf dynamic-profile {
                 description " dynamic profile for interface to use";
                 type string {
                   length "1 .. 80";
                 }
               }
             }
             container mlfr-end-to-end {
               presence "enable mlfr-end-to-end";
               description "Multilink Frame Relay end-to-end protocol parameters";
               uses apply-advanced;
               leaf bundle {
                 description "Logical interface name this link will join";
                 type union {
                   type jt:interface-unit;
                   type string {
                     pattern "<.*>|$.*";
                   }
                 }
                 mandatory true;
               }
             }
             container mlfr-uni-nni {
               presence "enable mlfr-uni-nni";
               description "Multilink Frame Relay UNI NNI protocol parameters";
               uses apply-advanced;
               leaf bundle {
                 description "Logical interface name this link will join";
                 type union {
                   type jt:interface-unit;
                   type string {
                     pattern "<.*>|$.*";
                   }
                 }
                 mandatory true;
               }
             }
             container ccc {
               presence "enable ccc";
               description "Circuit cross-connect parameters";
               uses apply-advanced;
               container filter {
                 description "Packet filtering";
                 uses apply-advanced;
                 choice input_choice {
                   case case_1 {
                     leaf input {
                       description "Name of filter applied to received packets";
                       type string;
                     }
                   }
                   case case_2 {
                     leaf-list input-list {
                       ordered-by user;
                       description "List of filter modules applied to received packets ";
                       type string;
                     }
                   }
                 }
                 leaf-list input-chain {
                   ordered-by user;
                   description "List of filter modules applied to received packets ";
                   type string;
                 }
                 choice output_choice {
                   case case_1 {
                     leaf output {
                       description "Name of filter applied to transmitted packets";
                       type string;
                     }
                   }
                   case case_2 {
                     leaf-list output-list {
                       ordered-by user;
                       description "List of filter modules applied to transmitted packets ";
                       type string;
                     }
                   }
                 }
                 leaf-list output-chain {
                   ordered-by user;
                   description "List of filter modules applied to transmitted packets ";
                   type string;
                 }
                 leaf group {
                   description "Interface group to which interface belongs";
                   type union {
                     type string {
                       pattern "<.*>|$.*";
                     }
                     type uint32 {
                       range "1 .. 255";
                     }
                   }
                 }
               }
               container policer {
                 description "Interface policing";
                 uses apply-advanced;
                 leaf input {
                   description "Name of policer applied to received packets";
                   type string;
                 }
                 leaf output {
                   description "Name of policer applied to transmitted packets";
                   type string;
                 }
               }
               leaf translate-fecn-and-becn {
                 description "Translate FECN and BECN bits";
                 type empty;
               }
               choice de-or-plp {
                 case case_1 {
                   leaf translate-discard-eligible {
                     description "Translate DE bit";
                     type empty;
                   }
                 }
                 case case_2 {
                 }
               }
               leaf keep-address-and-control {
                 description "Don't strip PPP address and control bytes";
                 type empty;
               }
             }
             container tcc {
               presence "enable tcc";
               description "Translational cross-connect parameters";
               uses apply-advanced;
               container policer {
                 description "Interface policing";
                 uses apply-advanced;
                 leaf input {
                   description "Name of policer applied to received packets";
                   type string;
                 }
                 leaf output {
                   description "Name of policer applied to transmitted packets";
                   type string;
                 }
               }
               container proxy {
                 presence "enable proxy";
                 uses apply-advanced;
                 leaf inet-address {
                   description "Remote host address on non-Ethernet side of Ethernet TCC";
                   type jt:ipv4addr;
                 }
               }
               container remote {
                 presence "enable remote";
                 uses apply-advanced;
                 leaf inet-address {
                   description "Remote host address on Ethernet side of Ethernet TCC";
                   type jt:ipv4addr;
                 }
                 leaf mac-address {
                   description "Remote host MAC address on Ethernet side of Ethernet TCC";
                   type jt:mac-addr;
                 }
               }
             }
             container vpls {
               presence "enable vpls";
               description "Virtual private LAN service parameters";
               uses apply-advanced;
               leaf core-facing {
                 description "Interface is core facing";
                 type empty;
               }
             }
             container ethernet-switching {
               description "Ethernet switching parameters";
               presence "enable ethernet-switching";
               uses ethernet-switching-type;
             }
             container any {
               presence "enable any";
               description "Parameters for 'any' family";
               uses apply-advanced;
               container filter {
                 description "Layer 2 packet filtering";
                 uses apply-advanced;
                 leaf input {
                   description "Name of filter applied to received packets";
                   type string {
                   }
                 }
                 leaf group {
                   description "Group to which interface belongs";
                   type union {
                     type string {
                       pattern "<.*>|$.*";
                     }
                     type uint32 {
                       range "1 .. 255";
                     }
                   }
                 }
               }
             }
           }
           leaf service-domain {
             description "Service domain to which interface belongs";
             type enumeration {
               enum "inside" {
                 description "Inside network";
               }
               enum "outside" {
                 description "Outside network";
               }
             }
           }
           leaf copy-tos-to-outer-ip-header {
             description "Copy IP payload header's ToS field to GRE delivery header";
             type empty;
           }
           container load-balancing-options {
             description "AMS subunit load balancing options";
             uses apply-advanced;
             leaf preferred-active {
               description "Preferred active Interface name";
               type union {
                 type jt:interface-device;
                 type string {
                   pattern "<.*>|$.*";
                 }
               }
             }
             leaf disable-hash {
               description "Hash based distribution is not needed for this subunit";
               type empty;
             }
             leaf modulo-key {
               description "Modulo based distribution";
               type enumeration {
                 enum "source-ip" {
                   description "Source Ip Address";
                 }
                 enum "destination-ip" {
                   description "Destination Ip Address";
                 }
               }
             }
             container hash-keys {
               uses apply-advanced;
               leaf-list ingress-key {
                 ordered-by user;
                 description "Hash Key for the ingress direction";
                 type enumeration {
                   enum "source-ip" {
                     description "Source Ip Address";
                   }
                   enum "destination-ip" {
                     description "Destination Ip Address";
                   }
                   enum "protocol" {
                     description "Protocol";
                   }
                   enum "iif" {
                     description "Incoming Interface";
                   }
                 }
               }
               leaf-list egress-key {
                 ordered-by user;
                 description "Hash Key for the egress direction";
                 status deprecated;
                 type enumeration {
                   enum "source-ip" {
                     description "Source Ip Address";
                     status deprecated;
                   }
                   enum "destination-ip" {
                     description "Destination Ip Address";
                     status deprecated;
                   }
                   enum "protocol" {
                     description "Protocol";
                     status deprecated;
                   }
                   enum "oif" {
                     description "Outgoing Interface";
                     status deprecated;
                   }
                 }
               }
               leaf ipv6-source-prefix-length {
                 description "IPv6 source prefix length for hash computation";
                 type enumeration {
                   enum "56" {
                     description "56 bit IPv6 address prefix";
                   }
                   enum "64" {
                     description "64 bit IPv6 address prefix";
                   }
                   enum "96" {
                     description "96 bit IPv6 address prefix";
                   }
                   enum "128" {
                     description "Complete 128 bit IPv6 address";
                   }
                 }
               }
             }
           }
           container interface-state {
             description "IRB interface state computation";
             uses apply-advanced;
             choice state {
               case case_1 {
                 leaf local {
                   description "IRB State computation based on local interface state";
                   type empty;
                 }
               }
               case case_2 {
                 leaf remote {
                   description "IRB State computation based on remote reachability";
                   type empty;
                 }
               }
               case case_3 {
                 leaf local-remote {
                   description "IRB State computation based on local or remote reachability";
                   type empty;
                 }
               }
               case case_4 {
                 leaf local-interface {
                   description "IRB State computation based on loopback AE port state";
                   type union {
                     type jt:interface-name;
                     type string {
                       pattern "<.*>|$.*";
                     }
                   }
                 }
               }
             }
             leaf local-count {
               description "Minimum number of local layer2 link in up state to consider IRB up";
               type union {
                 type uint16;
                 type string {
                   pattern "<.*>|$.*";
                 }
               }
             }
             leaf vtep-count {
               description "Minimum number of VTEP link in up state to consider IRB up";
               type union {
                 type uint16;
                 type string {
                   pattern "<.*>|$.*";
                 }
               }
             }
             container hold-time {
               description "Delay before marking interface up or down for defect";
               uses apply-advanced;
               leaf up {
                 description "Delay in seconds before marking IRB interface up";
                 units "seconds";
                 type union {
                   type uint32;
                   type string {
                     pattern "<.*>|$.*";
                   }
                 }
               }
               leaf down {
                 description "Delay in seconds before marking IRB interface down";
                 units "seconds";
                 type union {
                   type uint32;
                   type string {
                     pattern "<.*>|$.*";
                   }
                 }
               }
             }
           }
           leaf virtual-gateway-v4-mac {
             description "Configure virtual gateway IPV4 virtual MAC address";
             type jt:mac-unicast;
           }
           leaf virtual-gateway-v6-mac {
             description "Configure virtual gateway IPV6 virtual MAC address";
             type jt:mac-unicast;
           }
           leaf no-dhcp-flood {
             description "Disable dhcp flooding";
             type empty;
           }
           leaf etree-ac-role {
             description "ETREE attachment circuit role";
             type enumeration {
               enum "root" {
                 description "ETREE root interface";
               }
               enum "leaf" {
                 description "ETREE leaf interface";
               }
             }
           }
         }
         container no-partition {
           description "Use channelizable interface as clear channel";
           leaf interface-type {
             description "Interface type";
             type enumeration {
               enum "e1" {
                 description "E1 interface";
               }
               enum "t1" {
                 description "T1 interface";
               }
               enum "at" {
                 description "ATM interface";
               }
               enum "t3" {
                 description "T3 interface";
               }
               enum "e3" {
                 description "E3 interface";
               }
               enum "ct3" {
                 description "Channelized T3 interface";
               }
               enum "so" {
                 description "SONET interface";
               }
               enum "cau4" {
                 description "CAU4 interface";
               }
             }
           }
         }
         list partition {
           key name;
           ordered-by user;
           description "Channelized interface partition";
           leaf name {
             description "Sublevel interface partition index (for example, 1, 3-4)";
             type string;
           }
           leaf oc-slice {
             description "Range of SONET/SDH slices (for example, 1, 7-9)";
             type string;
           }
           leaf timeslots {
             description "Timeslots [(1..24) for T1, (1..31) for E1]; for example, 1-3,4,9,22-24 (no spaces)";
             type string;
           }
           leaf interface-type {
             description "Sublevel interface type";
             type enumeration {
               enum "ds" {
                 description "DS0 interface";
               }
               enum "e1" {
                 description "E1 interface";
               }
               enum "t1" {
                 description "T1 interface";
               }
               enum "at" {
                 description "ATM interface";
               }
               enum "ct1" {
                 description "Channelized T1 interface";
               }
               enum "ce1" {
                 description "Channelized E1 interface";
               }
               enum "t3" {
                 description "T3 interface";
               }
               enum "ct3" {
                 description "Channelized T3 interface";
               }
               enum "e3" {
                 description "E3 interface";
               }
               enum "so" {
                 description "SONET interface";
               }
               enum "coc1" {
                 description "Channelized OC1 interface";
               }
               enum "cau4" {
                 description "Channelized AU4 interface";
               }
               enum "dc" {
                 description "D channel interface";
               }
               enum "bc" {
                 description "B channel interface";
               }
             }
             mandatory true;
           }
         }
       }
       list interface {
         key name;
         uses interfaces_type;
       }
     }
     container protocols {
       description "Routing protocol configuration";
       uses apply-advanced;
       container igmp {
         presence "enable igmp";
         description "IGMP options";
         uses apply-advanced;
         leaf protocol-instance-name {
           description "Name of protocol instance under routing instance";
           type string;
         }
         container traceoptions {
           description "Trace options for IGMP";
           uses apply-advanced;
           container file {
             description "Trace file options";
             leaf filename {
               description "Name of file in which to write trace information";
               type string {
                 length "1 .. 1024";
               }
               mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all IGMP packets";
                 }
                 enum "query" {
                   description "Trace IGMP membership query messages";
                 }
                 enum "report" {
                   description "Trace membership report messages";
                 }
                 enum "leave" {
                   description "Trace leave group messages (IGMPv2 only)";
                 }
                 enum "mtrace" {
                   description "Trace mtrace packets";
                 }
                 enum "group" {
                   description "Trace group operations";
                 }
                 enum "client-notification" {
                   description "Trace notifications";
                 }
                 enum "host-notification" {
                   description "Trace host notifications";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf maximum-transmit-rate {
           description "Maximum transmission rate (packets per second)";
           type union {
             type string {
               pattern "<.*>|$.*";
             }
             type uint32 {
               range "1 .. 10000";
             }
           }
         }
         leaf accounting {
           description "Enable join and leave event notification";
           type empty;
         }
         list interface {
           key name;
           ordered-by user;
           description "Interface options for IGMP";
           leaf name {
             type string;
           }
           uses apply-advanced;
           choice enable-disable {
             case case_1 {
               leaf disable {
                 description "Disable IGMP on this interface";
                 type empty;
               }
             }
           }
           leaf version {
             description "Set IGMP version number on this interface";
             type union {
               type string {
                 pattern "<.*>|$.*";
               }
               type uint8 {
                 range "1 .. 3";
               }
             }
           }
           container static {
             description "Static group or source membership";
             uses apply-advanced;
             list group {
               key name;
               ordered-by user;
               description "IP multicast group address";
               leaf name {
                 description "IP multicast group address";
                 type jt:ipv4addr;
               }
               uses apply-advanced;
               leaf group-increment {
                 description "Mask for the incrementing group IP address";
                 type jt:ipv4addr;
               }
               leaf group-count {
                 description "Number of groups";
                 type union {
                   type string {
                     pattern "<.*>|$.*";
                   }
                   type uint32 {
                     range "1 .. 512";
                   }
                 }
               }
               leaf exclude {
                 description "Exclude sources";
                 type empty;
               }
               list source {
                 key name;
                 ordered-by user;
                 description "IP multicast source address";
                 leaf name {
                   description "Source address of IP multicast data";
                   type jt:ipv4addr;
                 }
                 uses apply-advanced;
                 leaf source-increment {
                   description "Mask for the incrementing source IP address";
                   type jt:ipv4addr;
                 }
                 leaf source-count {
                   description "Number of sources";
                   type union {
                     type string {
                       pattern "<.*>|$.*";
                     }
                     type uint32 {
                       range "1 .. 1024";
                     }
                   }
                 }
               }
             }
           }
           leaf ssm-map {
             description "Map for SSM translation of IGMPv1 or IGMPv2 messages";
             type string;
           }
           leaf-list ssm-map-policy {
             ordered-by user;
             description "SSM map policy name";
             type jt:policy-algebra;
           }
           leaf immediate-leave {
             description "Group removed immediately, last membership query not sent";
             type empty;
           }
           leaf promiscuous-mode {
             description "Accept igmp messages coming from different subnet";
             type empty;
           }
           choice accounting-choice {
             leaf accounting {
               description "Enable join and leave event notification";
               type empty;
             }
             leaf no-accounting {
               description "Don't enable join and leave event notification";
               type empty;
             }
           }
           leaf-list group-policy {
             ordered-by user;
             description "Group filter applied to incoming IGMP report messages";
             type jt:policy-algebra;
           }
           leaf group-limit {
             description "Maximum number of (source,group) per interface";
             type union {
               type string {
                 pattern "<.*>|$.*";
               }
               type uint16 {
                 range "1 .. 32767";
               }
             }
           }
           leaf group-threshold {
             description "Percentage of limit at which to generate warnings";
             type union {
               type string {
                 pattern "<.*>|$.*";
               }
               type uint32 {
                 range "1 .. 100";
               }
             }
           }
           leaf log-interval {
             description "Time between consecutive log messages";
             type union {
               type string {
                 pattern "<.*>|$.*";
               }
               type uint32 {
                 range "6 .. 32767";
               }
             }
           }
           container passive {
             presence "enable passive";
             description "Suppress sending and receiving IGMP messages";
             leaf allow-receive {
               description "Allow receiving IGMP messages";
               type empty;
             }
             leaf send-general-query {
               description "Send IGMP general query messages";
               type empty;
             }
             leaf send-group-query {
               description "Send IGMP group query messages";
               type empty;
             }
           }
           leaf-list oif-map {
             ordered-by user;
             description "Output interface map";
             type jt:policy-algebra;
           }
           leaf distributed {
             description "Distributed IGMP interface";
             type empty;
           }
         }
         container amt {
           description "Automatic Multicast Tunnel options for IGMP";
           uses apply-advanced;
           container relay {
             description "AMT relay options for IGMP";
             uses apply-advanced;
             container defaults {
               presence "enable defaults";
               description "Default AMT relay options for IGMP";
               uses apply-advanced;
               leaf version {
                 description "Set IGMP version number on AMT interfaces";
                 type union {
                   type string {
                     pattern "<.*>|$.*";
                   }
                   type uint8 {
                     range "1 .. 3";
                   }
                 }
               }
               leaf ssm-map {
                 description "Map for SSM translation of IGMPv1 or IGMPv2 messages";
                 type string;
               }
               leaf-list ssm-map-policy {
                 ordered-by user;
                 description "SSM map policy name";
                 type jt:policy-algebra;
               }
               choice accounting-choice {
                 leaf accounting {
                   description "Enable join and leave event notification";
                   type empty;
                 }
                 leaf no-accounting {
                   description "Don't enable join and leave event notification";
                   type empty;
                 }
               }
               leaf-list group-policy {
                 ordered-by user;
                 description "Group filter applied to incoming IGMP report messages";
                 type jt:policy-algebra;
               }
               leaf group-limit {
                 description "Maximum number of (source,group) per interface";
                 type union {
                   type string {
                     pattern "<.*>|$.*";
                   }
                   type uint16 {
                     range "1 .. 32767";
                   }
                 }
               }
               leaf group-threshold {
                 description "Percentage of limit at which to generate warnings";
                 type union {
                   type string {
                     pattern "<.*>|$.*";
                   }
                   type uint32 {
                     range "1 .. 100";
                   }
                 }
               }
               leaf log-interval {
                 description "Time between consecutive log messages";
                 type union {
                   type string {
                     pattern "<.*>|$.*";
                   }
                   type uint32 {
                     range "6 .. 32767";
                   }
                 }
               }
               leaf robust-count {
                 description "Expected packet loss on a subnet";
                 type union {
                   type string {
                     pattern "<.*>|$.*";
                   }
                   type uint32 {
                     range "2 .. 10";
                   }
                 }
               }
               leaf query-interval {
                 description "When to send host query messages";
                 units "seconds";
                 type union {
                   type string {
                     pattern "<.*>|$.*";
                   }
                   type uint32 {
                     range "1 .. 1024";
                   }
                 }
               }
               leaf query-response-interval {
                 description "How long to wait for a host query response";
                 units "seconds";
                 type string {
                 }
               }
             }
           }
         }
       }
       container oam {
         description "Operation, Administration, and Management configuration";
         uses apply-advanced;
         container ethernet {
           description "OAM configuration for Ethernet";
           uses apply-advanced;
           container link-fault-management {
             description "802.3ah Ethernet OAM configuration";
             uses apply-advanced;
             container traceoptions {
               description "Trace options for link-fault management";
               uses apply-advanced;
               leaf no-remote-trace {
                 description "Disable remote tracing";
                 type empty;
               }
               container file {
                 description "Trace file information";
                 leaf filename {
                   description "Name of file in which to write trace information";
                   type string {
                     length "1 .. 1024";
                   }
                 }
                 leaf size {
                   description "Maximum trace file size";
                   units "bytes";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 description "Tracing parameters";
                 leaf name {
                   type enumeration {
                     enum "configuration" {
                       description "Trace configuration events";
                     }
                     enum "routing-socket" {
                       description "Trace routing socket events";
                     }
                     enum "protocol" {
                       description "Trace protocol processing events";
                     }
                     enum "action-profile" {
                       description "Trace action profile invocation events";
                     }
                     enum "all" {
                       description "Trace everything";
                     }
                   }
                 }
               }
             }
             list action-profile {
               key name;
               ordered-by user;
               description "Define an action profile";
               leaf name {
                 description "Name of action profile";
                 type string {
                   length "1 .. 32";
                 }
               }
               uses apply-advanced;
               container event {
                 description "Events this action profile will check";
                 uses apply-advanced;
                 leaf link-adjacency-loss {
                   description "Loss of adjacency with OAM peer";
                   type empty;
                 }
                 leaf protocol-down {
                   description "Upper layer indication on protocol down";
                   type empty;
                 }
                 container link-event-rate {
                   uses apply-advanced;
                   leaf symbol-period {
                     description "Rate of receiving symbol period events";
                     units "error(s) per 100 symbol";
                     type union {
                       type string {
                         pattern "<.*>|$.*";
                       }
                       type int32 {
                         range "1 .. 100";
                       }
                     }
                   }
                   leaf frame-error {
                     description "Rate of receiving frame error events";
                     units "error(s) per 100 milli-second";
                     type union {
                       type string {
                         pattern "<.*>|$.*";
                       }
                       type int32 {
                         range "1 .. 1000";
                       }
                     }
                   }
                   leaf frame-period {
                     description "Rate of receiving frame period events";
                     units "error(s) per 100 frames";
                     type union {
                       type string {
                         pattern "<.*>|$.*";
                       }
                       type int32 {
                         range "1 .. 100";
                       }
                     }
                   }
                   leaf frame-period-summary {
                     description "Rate of receiving frame period summary events";
                     units "error(s) per second";
                     type union {
                       type string {
                         pattern "<.*>|$.*";
                       }
                       type int32 {
                         range "1 .. 1000";
                       }
                     }
                   }
                 }
               }
               container action {
                 description "Action to take on specified events";
                 uses apply-advanced;
                 leaf syslog {
                   description "Generate syslog message";
                   type empty;
                 }
                 leaf link-down {
                   description "Mark the interface down for transit traffic";
                   type empty;
                 }
                 leaf send-critical-event {
                   description "Start sending OAM PDUs with critical event bit set";
                   type empty;
                 }
               }
             }
             list interface {
               key name;
               ordered-by user;
               description "Interface on which to set Ethernet OAM parameters";
               leaf name {
                 description "Interface name";
                 type union {
                   type jt:interface-device;
                   type string {
                     pattern "<.*>|$.*";
                   }
                 }
               }
               uses apply-advanced;
               leaf-list apply-action-profile {
                 ordered-by user;
                 description "Apply the specified action profile on the interface";
                 type string;
               }
               leaf pdu-interval {
                 description "Periodic OAM protocol data unit interval";
                 default "1000";
                 units "milliseconds";
                 type union {
                   type string {
                     pattern "<.*>|$.*";
                   }
                   type int32 {
                     range "100 .. 1000";
                   }
                 }
               }
               leaf loopback-tracking {
                 description "Enable link down on loopback detection";
                 type empty;
               }
               leaf detect-loc {
                 description "Detects initial lack of adjacency formation";
                 type empty;
               }
               leaf link-discovery {
                 description "Mode of discovery";
                 default "active";
                 type enumeration {
                   enum "active" {
                   }
                   enum "passive" {
                   }
                 }
               }
               leaf pdu-threshold {
                 description "Number of PDUs missed before declaring peer lost";
                 default "3";
                 type union {
                   type string {
                     pattern "<.*>|$.*";
                   }
                   type int32;
                 }
               }
               leaf remote-loopback {
                 description "Put remote DTE into remote-loopback mode";
                 type empty;
               }
               container negotiation-options {
                 description "802.3ah features supported on the interface";
                 uses apply-advanced;
                 leaf no-allow-link-events {
                   description "Do not emit periodic PDUs detailing framing and symbol errors";
                   type empty;
                 }
                 leaf allow-remote-loopback {
                   description "Allow local port to be put into loopback mode";
                   type empty;
                 }
               }
               container event-thresholds {
                 description "Thresholds for sending 802.3ah events";
                 uses apply-advanced;
                 leaf symbol-period {
                   description "Threshold for sending symbol period events";
                   default "1";
                   type union {
                     type string {
                       pattern "<.*>|$.*";
                     }
                     type int32 {
                       range "0 .. 100";
                     }
                   }
                 }
                 leaf frame-error {
                   description "Threshold for sending frame error events";
                   default "1";
                   type union {
                     type string {
                       pattern "<.*>|$.*";
                     }
                     type int32 {
                       range "0 .. 100";
                     }
                   }
                 }
                 leaf frame-period {
                   description "Threshold for sending frame period error events";
                   default "1";
                   type union {
                     type string {
                       pattern "<.*>|$.*";
                     }
                     type int32 {
                       range "0 .. 100";
                     }
                   }
                 }
                 leaf frame-period-summary {
                   description "Threshold for sending frame period summary error events";
                   default "1";
                   type union {
                     type string {
                       pattern "<.*>|$.*";
                     }
                     type int32 {
                       range "0 .. 100";
                     }
                   }
                 }
               }
             }
           }
           container connectivity-fault-management {
             description "Configurations related to 802.1ag ethernet oam";
             uses apply-advanced;
             container performance-monitoring {
               description "Configurations related to ethernet performance monitoring";
               uses apply-advanced;
               leaf hardware-assisted-timestamping {
                 description "Enable timestamping feature in hardware";
                 type empty;
               }
               leaf delegate-server-processing {
                 description "Delegate performance measurement request handling to PFE";
                 type empty;
               }
               leaf hardware-assisted-keepalives {
                 description "Enable/Disable delegating keepalives to hardware";
                 type enumeration {
                   enum "enable" {
                     description "Enable delegate keepalives handling to Hardware";
                   }
                   enum "disable" {
                     description "Disable delegate keepalives handling to Hardware (default)";
                   }
                 }
               }
               leaf hardware-assisted-pm {
                 description "Enable inline support for performance monitoring";
                 type empty;
               }
               leaf enhanced-sla-iterator {
                 description "Enable Enhanced SLA Iterator Cycle-time";
                 type empty;
               }
               leaf measurement-interval {
                 description "Enables measurement-interval based PM (MEF 36 mode). Default 15 min in enhanced-cfm-mode";
                 units "minutes";
                 type enumeration {
                   enum "2" {
                     description "2 minutes measurement interval";
                   }
                   enum "5" {
                     description "5 minutes measurement interval";
                   }
                   enum "15" {
                     description "15 minutes measurement interval";
                   }
                   enum "30" {
                     description "30 minutes measurement interval";
                   }
                   enum "60" {
                     description "1 hour measurement interval";
                   }
                 }
               }
               leaf legacy-pm-display {
                 description "Display Legacy PM output (for DM) in MEF mode.";
                 type empty;
               }
               list sla-iterator-profiles {
                 key name;
                 ordered-by user;
                 description "Configuration related to an sla monitoring iterator";
                 leaf name {
                   type string;
                 }
                 uses apply-advanced;
                 leaf disable {
                   description "Disable the iterator profile";
                   type empty;
                 }
                 leaf measurement-type {
                   description "Choice of the type of Y.1731(SLA measurement) frame to be sent";
                   type enumeration {
                     enum "two-way-delay" {
                       description "Y.1731 2-way DM frames are sent for this profile";
                     }
                     enum "loss" {
                       description "Y.1731 LM frames are sent for this profile";
                     }
                     enum "slm" {
                       description "Y.1731 SLM frames are sent for this profile";
                     }
                     enum "statistical-frame-loss" {
                       description "Y.1731 2-way DM frames for statistical frame loss are sent for this profile";
                     }
                   }
                   mandatory true;
                 }
                 leaf flap-trap-monitor {
                   description "Configurable timer value 1-360";
                   units "seconds";
                   type union {
                     type string {
                       pattern "<.*>|$.*";
                     }
                     type uint32 {
                       range "1 .. 360";
                     }
                   }
                 }
                 leaf cycle-time {
                   description "Time period of an iterator profile";
                   default "1000";
                   units "milliseconds";
                   type union {
                     type string {
                       pattern "<.*>|$.*";
                     }
                     type uint32;
                   }
                 }
                 leaf iteration-period {
                   description "Maximum services under this iterator profile";
                   default "2000";
                   units "connections";
                   type union {
                     type string {
                       pattern "<.*>|$.*";
                     }
                     type uint32 {
                       range "1 .. 2000";
                     }
                   }
                 }
                 container calculation-weight {
                   presence "enable calculation-weight";
                   description "Configure delay and delay variation calculation weight";
                   uses apply-advanced;
                   leaf delay {
                     description "Weight used in delay calculation";
                     default "1";
                     type union {
                       type string {
                         pattern "<.*>|$.*";
                       }
                       type uint32 {
                         range "1 .. 65535";
                       }
                     }
                   }
                   leaf delay-variation {
                     description "Weight used in delay-variation calculation";
                     default "1";
                     type union {
                       type string {
                         pattern "<.*>|$.*";
                       }
                       type uint32 {
                         range "1 .. 65535";
                       }
                     }
                   }
                 }
                 container avg-flr-forward-threshold {
                   presence "enable avg-flr-forward-threshold";
                   description "Avg forward flr threshold";
                   uses apply-advanced;
                   leaf avg-flr-forward {
                     description "Avg forward flr threshold value in mili-percent";
                     type union {
                       type string {
                         pattern "<.*>|$.*";
                       }
                       type uint32 {
                         range "1 .. 100000";
                       }
                     }
                     mandatory true;
                   }
                   leaf flap-trap-monitor {
                     description "Configurable timer value 1-360";
                     units "seconds";
                     type union {
                       type string {
                         pattern "<.*>|$.*";
                       }
                       type uint32 {
                         range "1 .. 360";
                       }
                     }
                   }
                 }
                 container avg-flr-backward-threshold {
                   presence "enable avg-flr-backward-threshold";
                   description "Avg backward flr threshold";
                   uses apply-advanced;
                   leaf avg-flr-backward {
                     description "Avg backward flr threshold value in mili-percent";
                     type union {
                       type string {
                         pattern "<.*>|$.*";
                       }
                       type uint32 {
                         range "1 .. 100000";
                       }
                     }
                     mandatory true;
                   }
                   leaf flap-trap-monitor {
                     description "Configurable timer value 1-360";
                     units "seconds";
                     type union {
                       type string {
                         pattern "<.*>|$.*";
                       }
                       type uint32 {
                         range "1 .. 360";
                       }
                     }
                   }
                 }
                 container avg-fd-twoway-threshold {
                   presence "enable avg-fd-twoway-threshold";
                   description "Avg frame delay threshold value";
                   uses apply-advanced;
                   leaf avg-fd-twoway {
                     description "Avg frame delay threshold value in mili-percent";
                     units "microseconds";
                     type union {
                       type string {
                         pattern "<.*>|$.*";
                       }
                       type uint32 {
                         range "1 .. 4294967295";
                       }
                     }
                     mandatory true;
                   }
                   leaf flap-trap-monitor {
                     description "Configurable timer value 1-360";
                     units "seconds";
                     type union {
                       type string {
                         pattern "<.*>|$.*";
                       }
                       type uint32 {
                         range "1 .. 360";
                       }
                     }
                   }
                 }
                 container avg-fdv-twoway-threshold {
                   presence "enable avg-fdv-twoway-threshold";
                   description "Avg frame delay variance threshold";
                   uses apply-advanced;
                   leaf avg-fdv-twoway {
                     description "Avg frame delay variance threshold value in mili-percent";
                     units "microseconds";
                     type union {
                       type string {
                         pattern "<.*>|$.*";
                       }
                       type uint32 {
                         range "1 .. 4294967295";
                       }
                     }
                     mandatory true;
                   }
                   leaf flap-trap-monitor {
                     description "Configurable timer value 1-360";
                     units "seconds";
                     type union {
                       type string {
                         pattern "<.*>|$.*";
                       }
                       type uint32 {
                         range "1 .. 360";
                       }
                     }
                   }
                 }
                 container frame-delay {
                   description "Bin configuration for frame delay";
                   uses apply-advanced;
                   leaf num-bins {
                     description "Max number of bins";
                     type union {
                       type string {
                         pattern "<.*>|$.*";
                       }
                       type uint32 {
                         range "2 .. 5";
                       }
                     }
                     mandatory true;
                   }
                   container two-way {
                     presence "enable two-way";
                     description "Bin configuration for 2way frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container frame-delay-range {
                   description "Bin configuration for frame delay range";
                   uses apply-advanced;
                   leaf num-bins {
                     description "Max number of bins";
                     type union {
                       type string {
                         pattern "<.*>|$.*";
                       }
                       type uint32 {
                         range "2 .. 5";
                       }
                     }
                     mandatory true;
                   }
                   container two-way {
                     presence "enable two-way";
                     description "Bin configuration for 2way frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward frame delay range";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
                 container ifdv {
                   description "Bin configuration for IFDV";
                   uses apply-advanced;
                   leaf num-bins {
                     description "Max number of bins";
                     type union {
                       type string {
                         pattern "<.*>|$.*";
                       }
                       type uint32 {
                         range "2 .. 5";
                       }
                     }
                     mandatory true;
                   }
                   container two-way {
                     presence "enable two-way";
                     description "Bin configuration for 2way IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container forward {
                     presence "enable forward";
                     description "Bin configuration for forward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                   container backward {
                     presence "enable backward";
                     description "Bin configuration for backward IFDV";
                     uses apply-advanced;
                     leaf-list lower-threshold-bin {
                       description "Lower threshold bin configuration in ascending order";
                       type union {
                         type string {
                           pattern "<.*>|$.*";
                         }
                         type uint32 {
                           range "1 .. 4294967294";
                         }
                       }
                     }
                   }
                 }
               }
               list interface {
                 key name;
                 ordered-by user;
                 description "Name of interface for the performance monitoring";
                 leaf name {
                   description "Interface name";
                   type union {
                     type jt:interface-unit;
                     type string {
                       pattern "<.*>|$.*";
                     }
                   }
                 }
                 leaf enable-multiclass-loss-measurement {
                   description "Disable multiclass loss measurement in hardware";
                   type empty;
                 }
                 leaf code-point-based-lm-accounting {
                   description "Enable code point based loss measurement in hardware";
                   type empty;
                 }
                 leaf priority-based-lm-accounting {
                   description "Enable priority based loss measurement in hardware";
                   type empty;
                 }
               }
               leaf enable-multiclass-loss-measurement {
                 description "Disable multiclass loss measurement in hardware";
                 type empty;
               }
               leaf code-point-based-lm-accounting {
                 description "Enable code point based loss measurement in hardware";
                 type empty;
               }
               leaf priority-based-lm-accounting {
                 description "Enable priority based loss measurement in hardware";
                 type empty;
               }
               leaf colorless-loss-measurement {
                 description "Enable colorless loss measurement in hardware";
                 type empty;
               }
             }
             leaf no-aggregate-delegate-processing {
               description "Do not distribute aggregate session to pfe";
               type empty;
             }
             leaf enhanced-cfm-mode {
               description "Enables Enhanced CFM Mode";
               type empty;
             }
             container traceoptions {
               description "Trace options for connectivity fault management";
               presence "enable traceoptions";
               uses cfm-traceoptions;
             }
             list action-profile {
               key name;
               ordered-by user;
               description "Action profiles to use when one or more remote maintenance association endpoints are down";
               leaf name {
                 description "Name of action profile";
                 type string;
               }
               uses apply-advanced;
               container event {
                 description "Events that need to be monitored";
                 uses apply-advanced;
                 leaf-list interface-status-tlv {
                   ordered-by user;
                   description "Values that need to be monitored in interface status TLV";
                   type enumeration {
                     enum "down" {
                       description "Interface is administratively down";
                     }
                     enum "lower-layer-down" {
                       description "Interface is physically down";
                     }
                   }
                 }
                 leaf-list port-status-tlv {
                   ordered-by user;
                   description "Values that need to be monitored in port status TLV";
                   type enumeration {
                     enum "blocked" {
                       description "Port is blocked";
                     }
                   }
                 }
                 leaf adjacency-loss {
                   description "Connectivity is lost";
                   type empty;
                 }
                 leaf rdi {
                   description "RDI received from some MEP";
                   type empty;
                 }
                 leaf connection-protection-tlv {
                   description "Values that need to be monitored in connection protection TLV";
                   type enumeration {
                     enum "using-working-path" {
                       description "Service traffic is using working path";
                     }
                     enum "using-protection-path" {
                       description "Service traffic is using protection path";
                     }
                   }
                 }
               }
               container action {
                 uses apply-advanced;
                 leaf interface-down {
                   description "Mark the interface as down";
                   type empty;
                 }
                 leaf revertive-interface-down {
                   description "Wait for CC loss-threshold to bring back the interface up";
                   type empty;
                 }
                 leaf non-revertive-interface-down {
                   description "Interface will not be brought up when CC is received";
                   type empty;
                 }
                 leaf propagate-remote-mac-flush {
                   description "Remote mac-flush";
                   type empty;
                 }
                 leaf interface-group-down {
                   description "Mark the interface group as down";
                   type empty;
                 }
                 leaf asynchronous-notification {
                   description "Generate asynchronous notification (Laser-off for optical phys)";
                   type empty;
                 }
                 container log-and-generate-ais {
                   uses apply-advanced;
                   leaf-list level {
                     description "Server maintenance domain levels range";
                     type union {
                       type string {
                         pattern "<.*>|$.*";
                       }
                       type uint32 {
                         range "1 .. 7";
                       }
                     }
                   }
                   leaf interval {
                     description "Interval between AIS messages";
                     default "1s";
                     type enumeration {
                       enum "1s" {
                       }
                       enum "1m" {
                       }
                     }
                   }
                   leaf priority {
                     description "802.1p priority of AIS packet";
                     default "0";
                     type union {
                       type string {
                         pattern "<.*>|$.*";
                       }
                       type uint32 {
                         range "0 .. 7";
                       }
                     }
                   }
                 }
               }
               container clear-action {
                 uses apply-advanced;
                 container interface-down {
                   description "Mark the interface as down";
                   leaf peer-interface {
                     description "Mark the interface as down";
                     type empty;
                   }
                 }
                 leaf propagate-remote-mac-flush {
                   description "Remote  mac flush";
                   type empty;
                 }
               }
               container default-actions {
                 description "Action that needs to be taken";
                 uses apply-advanced;
                 leaf interface-down {
                   description "Bring the interface down";
                   type empty;
                 }
               }
             }
             container policer {
               description "Rate limit Ethernet OAM packets for all sessions";
               uses apply-advanced;
               leaf continuity-check {
                 description "Policer to rate limit Continuity Check Ethernet OAM messages";
                 type string;
               }
               leaf other {
                 description "Policer to rate limit non Continuity Check Ethernet OAM messages";
                 type string;
               }
               leaf all {
                 description "Policer to rate limit all Ethernet OAM messages";
                 type string;
               }
             }
             container linktrace {
               presence "enable linktrace";
               description "Linktrace protocol global options";
               uses apply-advanced;
               leaf path-database-size {
                 description "Number of linktrace reply entries to be stored per linktrace request";
                 default "100";
                 type union {
                   type string {
                     pattern "<.*>|$.*";
                   }
                   type uint32 {
                     range "1 .. 255";
                   }
                 }
               }
               leaf age {
                 description "Time after which a stale request-response entry is deleted";
                 default "10m";
                 type enumeration {
                   enum "10s" {
                   }
                   enum "30s" {
                   }
                   enum "1m" {
                   }
                   enum "10m" {
                   }
                   enum "30m" {
                   }
                 }
               }
             }
             container context-history {
               presence "enable context-history";
               description "Context history limit (0..5000000)";
               uses apply-advanced;
               leaf ctxt-limit {
                 description "Context history limit [...] ";
                 type union {
                   type string {
                     pattern "<.*>|$.*";
                   }
                   type uint32 {
                     range "0 .. 5000000";
                   }
                 }
               }
             }
             list maintenance-domain {
               key name;
               description "Maintenance domain configuration";
               leaf name {
                 type string;
               }
               uses apply-advanced;
               list bridge-domain {
                 key name;
                 ordered-by user;
                 description "Bridge-domain information for the default maintenance domain";
                 leaf name {
                   description "Bridge domain name";
                   type string;
                 }
                 leaf-list vlan-id {
                   ordered-by user;
                   description "VLAN id";
                   type string;
                 }
               }
               list virtual-switch {
                 key name;
                 ordered-by user;
                 description "Virtual switch Bridge-domain information for the default maintenance domain";
                 leaf name {
                   description "Routing instance of type virtual switch";
                   type string;
                 }
                 uses apply-advanced;
                 list bridge-domain {
                   key name;
                   ordered-by user;
                   leaf name {
                     description "Bridge domain name";
                     type string;
                   }
                   leaf-list vlan-id {
                     ordered-by user;
                     description "VLAN id";
                     type string;
                   }
                 }
               }
               list instance {
                 key name;
                 ordered-by user;
                 description "VPLS instance name for the default maintenance domain";
                 leaf name {
                   description "VPLS routing instance name";
                   type string;
                 }
               }
               list interface {
                 key name;
                 ordered-by user;
                 description "Name of interface for the default maintenance domain";
                 leaf name {
                   description "Interface name";
                   type union {
                     type jt:interface-unit;
                     type string {
                       pattern "<.*>|$.*";
                     }
                   }
                 }
               }
               leaf level {
                 description "Level value for maintenance domain";
                 type union {
                   type string {
                     pattern "<.*>|$.*";
                   }
                   type uint8 {
                     range "0 .. 7";
                   }
                 }
               }
               leaf name-format {
                 description "Format of maintenance domain name";
                 type enumeration {
                   enum "none" {
                     description "No format specified";
                   }
                   enum "dns" {
                     description "Character string similar to Domain Name System name";
                   }
                   enum "mac+2oct" {
                     description "MAC address with 2 octet integer (xx:xx:xx:xx:xx:xx.Y format)";
                   }
                   enum "character-string" {
                     description "Character string";
                   }
                 }
               }
               leaf mip-half-function {
                 description "Half function to be implemented by MIP";
                 default "none";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                 }
               }
               list maintenance-association {
                 key name;
                 description "Maintenance association configuration";
                 leaf name {
                   description "Name of maintenance association in IEEE compliant format";
                   type string {
                     length "1 .. 45";
                   }
                 }
                 uses apply-advanced;
                 leaf debug-session {
                   description "Debug the CFM session";
                   type empty;
                 }
                 leaf short-name-format {
                   description "Format of Maintenance Association Name";
                   type enumeration {
                     enum "2octet" {
                       description "An integer in the range 0..65535";
                     }
                     enum "rfc-2685-vpn-id" {
                       description "VPN identifier that complies with RFC 2685";
                     }
                     enum "vlan" {
                       description "Primary VLAN identifier";
                     }
                     enum "character-string" {
                       description "Character string";
                     }
                     enum "icc" {
                       description "ITU Carrier Code";
                     }
                   }
                 }
                 leaf primary-vid {
                   description "VLAN id";
                   type string;
                 }
                 container continuity-check {
                   presence "enable continuity-check";
                   description "Continuity check configuration";
                   uses apply-advanced;
                   leaf interval {
                     description "Interval between continuity-check messages";
                     default "1m";
                     type enumeration {
                       enum "10ms" {
                       }
                       enum "100ms" {
                       }
                       enum "1s" {
                       }
                       enum "10s" {
                       }
                       enum "1m" {
                       }
                       enum "10m" {
                       }
                       enum "3.3ms" {
                       }
                     }
                   }
                   leaf loss-threshold {
                     description "Number of continuity-check messages lost before marking endpoint as down";
                     default "3";
                     type union {
                       type string {
                         pattern "<.*>|$.*";
                       }
                       type uint32 {
                         range "3 .. 256";
                       }
                     }
                   }
                   leaf hold-interval {
                     description "Time before flushing MEP database if no updates occur";
                     default "10";
                     units "minutes";
                     type union {
                       type string {
                         pattern "<.*>|$.*";
                       }
                       type uint32 {
                         range "1 .. 30240";
                       }
                     }
                   }
                   leaf port-status-tlv {
                     description "Include port status TLV in CCM";
                     type empty;
                   }
                   leaf interface-status-tlv {
                     description "Include interface status TLV in CCM";
                     type empty;
                   }
                   leaf connection-protection-tlv {
                     description "Include connection protection OUI TLV in CCM";
                     type empty;
                   }
                   leaf convey-loss-threshold {
                     description "Include Loss Threshold OUI TLV in CCM";
                     type empty;
                   }
                   leaf interface-status-send-rdi {
                     description "Send RDI on interface operation status down in CCM";
                     type empty;
                   }
                   leaf ignore-cfm-interface-status-ap {
                     description "Ignore AP cfm interface status";
                     type empty;
                   }
                   container sendid-tlv {
                     description "Include sendid-tlv in CCM/LBM/LTM";
                     uses apply-advanced;
                     leaf send-chassis-tlv {
                       description "Attach Chassis ID & Mgmt Addr to CCM/LBM/LTM";
                       type empty;
                     }
                   }
                 }
                 leaf mip-half-function {
                   description "Half function to be implemented by MIP";
                   default "defer";
                   type enumeration {
                     enum "none" {
                       description "No MHFs should be created";
                     }
                     enum "default" {
                       description "Create MHF as per IEEE 802.1ag specifications for defMHFDefault";
                     }
                     enum "explicit" {
                       description "Create MHF as per IEEE 802.1ag specifications for defMHFExplicit";
                     }
                     enum "defer" {
                       description "Create MHF as per IEEE 802.1ag specifications for defMHFDefer";
                     }
                   }
                 }
                 list mep {
                   key name;
                   ordered-by user;
                   description "Maintenance association endpoint configuration";
                   leaf name {
                     description "Identifier for maintenance association endpoint";
                     type union {
                       type string {
                         pattern "<.*>|$.*";
                       }
                       type uint16 {
                         range "1 .. 8191";
                       }
                     }
                   }
                   uses apply-advanced;
                   container interface {
                     presence "enable interface";
                     description "Name of interface";
                     leaf interface-name {
                       type union {
                         type jt:interface-unit;
                         type string {
                           pattern "<.*>|$.*";
                         }
                       }
                       mandatory true;
                     }
                     leaf vlan {
                       description "Trunk port interface VLAN identifier";
                       type union {
                         type string {
                           pattern "<.*>|$.*";
                         }
                         type uint32 {
                           range "1 .. 4094";
                         }
                       }
                     }
                     choice connection-type {
                       case case_1 {
                         leaf working {
                           description "Monitory the primary path";
                           type empty;
                         }
                       }
                       case case_2 {
                         leaf protect {
                           description "Monitory the protect path";
                           type empty;
                         }
                       }
                     }
                   }
                   leaf direction {
                     description "Direction of maintenance endpoint";
                     default "down";
                     type enumeration {
                       enum "up" {
                       }
                       enum "down" {
                       }
                     }
                   }
                   leaf priority {
                     description "802.1p priority of continuity-check and link-trace packet";
                     default "0";
                     type union {
                       type string {
                         pattern "<.*>|$.*";
                       }
                       type uint32 {
                         range "0 .. 7";
                       }
                     }
                   }
                   leaf auto-discovery {
                     description "Accept continuity-check messages from all remote MEPs";
                     type empty;
                   }
                   leaf action-profile {
                     description "Name of the action profile";
                     type string;
                   }
                   list remote-mep {
                     key name;
                     ordered-by user;
                     description "Remote maintenance association endpoint configuration";
                     leaf name {
                       description "Identifier for remote maintenance association endpoint";
                       type union {
                         type string {
                           pattern "<.*>|$.*";
                         }
                         type uint16 {
                           range "1 .. 8191";
                         }
                       }
                     }
                     uses apply-advanced;
                     leaf action-profile {
                       description "Name of the action profile";
                       type string;
                     }
                     container interface-group {
                       presence "enable interface-group";
                       description "Mark this interface group down Profile configured with action interface-group-down";
                       uses apply-advanced;
                       leaf interface-device-name {
                         description "Interface device name";
                         type union {
                           type jt:interface-device;
                           type string {
                             pattern "<.*>|$.*";
                           }
                         }
                       }
                       leaf-list unit-list {
                         description "One or more logical interface unit numbers";
                         type jt:range;
                       }
                     }
                     list sla-iterator-profile {
                       key name;
                       ordered-by user;
                       description "Name of the iterator profile";
                       leaf name {
                         type string;
                       }
                       uses apply-advanced;
                       leaf iteration-count {
                         description "Iterations to partake for acquiring SLA measurements";
                         units "frames";
                         type union {
                           type string {
                             pattern "<.*>|$.*";
                           }
                           type uint32 {
                             range "1 .. 65535";
                           }
                         }
                       }
                       leaf priority {
                         description "The vlan pcp value to be sent in the Y.1731 frame";
                         type union {
                           type string {
                             pattern "<.*>|$.*";
                           }
                           type uint32 {
                             range "0 .. 7";
                           }
                         }
                       }
                       leaf data-tlv-size {
                         description "Size of the data-tlv portion of Y.1731 frame";
                         units "bytes";
                         type union {
                           type string {
                             pattern "<.*>|$.*";
                           }
                           type uint32 {
                             range "1 .. 1400";
                           }
                         }
                       }
                     }
                     leaf detect-loc {
                       description "Detects initial loss of connectivity with remote mep";
                       type empty;
                     }
                   }
                   leaf lowest-priority-defect {
                     description "Lowest priority defect that is allowed to generate a fault alarm";
                     type enumeration {
                       enum "all-defects" {
                         description "Allows all defects";
                       }
                       enum "mac-rem-err-xcon" {
                         description "Allows only MAC, not receiving CCM, erroneous CCM and cross connect defects";
                       }
                       enum "rem-err-xcon" {
                         description "Allows only not receiving CCM, erroneous CCM and cross connect CCM defects";
                       }
                       enum "err-xcon" {
                         description "Allows only erroneous CCM and cross connect CCM defects";
                       }
                       enum "xcon" {
                         description "Allows only cross connect CCM defect";
                       }
                       enum "no-defect" {
                         description "Allows no defect";
                       }
                     }
                   }
                 }
                 container policer {
                   description "Rate limit Ethernet OAM packets for this session";
                   uses apply-advanced;
                   leaf continuity-check {
                     description "Policer to rate limit Continuity Check Ethernet OAM messages";
                     type string;
                   }
                   leaf other {
                     description "Policer to rate limit non Continuity Check Ethernet OAM messages";
                     type string;
                   }
                   leaf all {
                     description "Policer to rate limit all Ethernet OAM messages";
                     type string;
                   }
                 }
               }
             }
             container sendid-tlv {
               description "Include sendid-tlv in CCM/LBM/LTM";
               uses apply-advanced;
               leaf send-chassis-tlv {
                 description "Attach Chassis ID & Mgmt Addr to CCM/LBM/LTM";
                 type empty;
               }
             }
           }
           list evcs {
             key name;
             description "Ethernet virtual circuits configuration";
             leaf name {
               description "EVC id";
               type string {
                 length "1 .. 100";
               }
             }
             uses apply-advanced;
             container evc-protocol {
               description "Signaling protocol to monitor EVC status";
               choice protocol {
                 case case_1 {
                   container cfm {
                     presence "enable cfm";
                     description "Connectivity fault management";
                     leaf maintenance-domain {
                       description "Maintenance domain name";
                       type string;
                       mandatory true;
                     }
                     leaf maintenance-association {
                       description "Maintenance association name";
                       type string;
                       mandatory true;
                     }
                     leaf mep {
                       description "Identifier for maintenance association endpoint";
                       type union {
                         type string {
                           pattern "<.*>|$.*";
                         }
                         type uint16 {
                           range "1 .. 8191";
                         }
                       }
                       mandatory true;
                     }
                   }
                 }
                 case case_2 {
                   container vpls {
                     presence "enable vpls";
                     description "Virtual private LAN service (BGP/LDP)";
                     leaf routing-instance {
                       description "Routing instance name";
                       type string;
                       mandatory true;
                     }
                   }
                 }
                 case case_3 {
                 }
                 case case_4 {
                 }
               }
             }
             leaf remote-uni-count {
               description "Number of remote UNIs in the EVC";
               default "1";
               type union {
                 type string {
                   pattern "<.*>|$.*";
                 }
                 type uint8 {
                   range "1 .. 255";
                 }
               }
             }
             leaf multipoint-to-multipoint {
               description "Multipoint to Multipoint EVC";
               type empty;
             }
           }
           container lmi {
             presence "enable lmi";
             description "Ethernet local management interface configuration";
             uses apply-advanced;
             container traceoptions {
               description "Trace options for ethernet local management interface";
               uses apply-advanced;
               leaf no-remote-trace {
                 description "Disable remote tracing";
                 type empty;
               }
               container file {
                 description "Trace file information";
                 leaf filename {
                   description "Name of file in which to write trace information";
                   type string {
                     length "1 .. 1024";
                   }
                 }
                 leaf size {
                   description "Maximum trace file size";
                   units "bytes";
                   type string;
                 }
                 leaf files {
                   description "Maximum number of trace files";
                   default "3";
                   type union {
                     type string {
                       pattern "<.*>|$.*";
                     }
                     type uint32 {
                       range "2 .. 1000";
                     }
                   }
                 }
                 choice world-readable-choice {
                   leaf world-readable {
                     description "Allow any user to read the log file";
                     type empty;
                   }
                   leaf no-world-readable {
                     description "Don't allow any user to read the log file";
                     type empty;
                   }
                 }
                 leaf match {
                   description "Regular expression for lines to be logged";
                   type jt:regular-expression;
                 }
               }
               list flag {
                 key name;
                 ordered-by user;
                 description "Tracing parameters";
                 leaf name {
                   type enumeration {
                     enum "configuration" {
                       description "Trace configuration events";
                     }
                     enum "routing-socket" {
                       description "Trace routing socket events";
                     }
                     enum "protocol" {
                       description "Trace protocol processing events";
                     }
                     enum "init" {
                       description "Trace events related to protocol daemon start-up";
                     }
                     enum "error" {
                       description "Trace events related to catestrophic errors in daemon";
                     }
                     enum "packet" {
                       description "Trace events related to packet flow";
                     }
                     enum "all" {
                       description "Trace everything";
                     }
                   }
                 }
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             list interface {
               key name;
               description "Interface options";
               leaf name {
                 type union {
                   type jt:interface-device;
                   type string {
                     pattern "<.*>|$.*";
                   }
                 }
               }
               uses apply-advanced;
               leaf uni-id {
                 description "UNI identifier";
                 type string {
                   length "1 .. 64";
                 }
               }
               leaf status-counter {
                 description "E-LMI status counter (N393)";
                 default "4";
                 type union {
                   type string {
                     pattern "<.*>|$.*";
                   }
                   type uint8 {
                     range "2 .. 10";
                   }
                 }
               }
               leaf polling-verification-timer {
                 description "Polling verification timer (T392)";
                 default "15";
                 units "seconds";
                 type union {
                   type string {
                     pattern "<.*>|$.*";
                   }
                   type uint8 {
                     range "5 .. 30";
                   }
                 }
               }
               leaf evc-map-type {
                 description "CE-VLAN ID/EVC map type";
                 default "bundling";
                 type enumeration {
                   enum "all-to-one-bundling" {
                     description "All to one bundling";
                   }
                   enum "service-multiplexing" {
                     description "Service multiplexing with no bundling";
                   }
                   enum "bundling" {
                     description "Bundling with service multiplexing";
                   }
                 }
               }
               list evc {
                 key name;
                 description "EVC configuration";
                 leaf name {
                   description "EVC identifier";
                   type string {
                     length "1 .. 100";
                   }
                 }
                 uses apply-advanced;
                 leaf default-evc {
                   description "Default EVC";
                   type empty;
                 }
                 leaf-list vlan-list {
                   description "Vlans mapped to this EVC";
                   type jt:vlan-range;
                 }
               }
             }
           }
           container fnp {
             presence "enable fnp";
             description "Failure notification protocol configuration";
             uses apply-advanced;
             container traceoptions {
               description "Tracing options for FNP";
               uses apply-advanced;
               container file {
                 description "Trace file options";
                 leaf filename {
                   description "Name of file in which to write trace information";
                   type string {
                     length "1 .. 1024";
                   }
                   mandatory true;
                 }
                 leaf replace {
                   description "Replace trace file rather than appending to it";
                   status deprecated;
                   type empty;
                 }
                 leaf size {
                   description "Maximum trace file size";
                   type string;
                 }
                 leaf files {
                   description "Maximum number of trace files";
                   default "10";
                   type union {
                     type string {
                       pattern "<.*>|$.*";
                     }
                     type uint32 {
                       range "2 .. 1000";
                     }
                   }
                 }
                 leaf no-stamp {
                   description "Do not timestamp trace file";
                   status deprecated;
                   type empty;
                 }
                 choice world-readable-choice {
                   leaf world-readable {
                     description "Allow any user to read the log file";
                     type empty;
                   }
                   leaf no-world-readable {
                     description "Don't allow any user to read the log file";
                     type empty;
                   }
                 }
               }
               list flag {
                 key name;
                 ordered-by user;
                 description "Tracing parameters";
                 leaf name {
                   type enumeration {
                     enum "events" {
                       description "Trace protocol events";
                     }
                     enum "pdu" {
                       description "Trace PDU reception and transmission";
                     }
                     enum "timers" {
                       description "Trace protocol timers";
                     }
                     enum "error" {
                       description "Trace all failure conditions";
                     }
                     enum "all" {
                       description "Trace all";
                     }
                   }
                 }
               }
             }
             leaf interval {
               description "Interval between FNP messages";
               default "1s";
               type enumeration {
                 enum "100ms" {
                 }
                 enum "1s" {
                 }
                 enum "10s" {
                 }
                 enum "1m" {
                 }
                 enum "10m" {
                 }
               }
             }
             leaf loss-threshold {
               description "Number of FNP messages lost before clearing FNP state";
               default "4";
               type union {
                 type string {
                   pattern "<.*>|$.*";
                 }
                 type uint8 {
                   range "3 .. 255";
                 }
               }
             }
             list interface {
               key name;
               ordered-by user;
               description "Interface configuration";
               leaf name {
                 type union {
                   type jt:interface-name;
                   type string {
                     pattern "<.*>|$.*";
                   }
                 }
               }
               uses apply-advanced;
               leaf domain-id {
                 description "Ethernet domain identifier";
                 default "0";
                 type union {
                   type uint32;
                   type string {
                     pattern "<.*>|$.*";
                   }
                 }
               }
             }
           }
         }
       }
       container pim {
         description "PIM configuration";
         uses juniper-protocols-pim;
       }
     }
     container class-of-service {
       description "Class-of-service configuration";
       uses juniper-class-of-service-options;
     }
     container routing-options {
       description "Protocol-independent routing option configuration";
       uses apply-advanced;
       list rib {
         key name;
         description "Routing table options";
         leaf name {
           description "Routing table name";
           type string;
         }
         uses apply-advanced;
         container static {
           description "Static routes";
           uses apply-advanced;
           leaf rib-group {
             description "Routing table group";
             type string;
           }
           container defaults {
             description "Global route options";
             uses apply-advanced;
             choice retain-choice {
               leaf retain {
                 description "Always keep route in forwarding table";
                 type empty;
               }
               leaf no-retain {
                 description "Don't always keep route in forwarding table";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               type empty;
             }
             choice longest-match-choice {
               leaf longest-match {
                 description "Always use longest prefix match to resolve next hops";
                 type empty;
               }
               leaf no-longest-match {
                 description "Don't always use longest prefix match to resolve next hops";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
           }
           list route {
             key name;
             description "Static route";
             leaf name {
               type jt:ipprefix;
             }
             uses apply-advanced;
             leaf priority {
               description "Static route priority high/medium/low";
               type enumeration {
                 enum "medium" {
                   description "Static route medium priority";
                 }
                 enum "low" {
                   description "Static route low priority";
                 }
                 enum "high" {
                   description "Static route high priority";
                 }
               }
             }
             choice next_hop {
               case case_1 {
                 leaf-list next-hop {
                   ordered-by user;
                   description "Next hop to destination";
                   type union {
                     type jt:ipaddr-or-interface;
                     type string {
                       pattern "<.*>|$.*";
                     }
                   }
                 }
               }
               case case_2 {
                 leaf reject {
                   description "Drop packets to destination; send ICMP unreachables";
                   type empty;
                 }
               }
               case case_3 {
                 leaf discard {
                   description "Drop packets to destination; send no ICMP unreachables";
                   type empty;
                 }
               }
               case case_4 {
                 leaf receive {
                   description "Install a receive route for the destination";
                   type empty;
                 }
               }
               case case_5 {
                 leaf next-table {
                   description "Next hop to another table";
                   type string {
                   }
                 }
               }
             }
             leaf description {
               description "Static route description";
               type string {
               }
             }
             list qualified-next-hop {
               key name;
               ordered-by user;
               description "Next hop with qualifiers";
               uses qualified_nh_obj;
             }
             leaf backup-pe-group {
               description "Multicast source redundancy group";
               type string;
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               leaf inline-disable {
                 description "Disable inline mode for this BFD session";
                 type empty;
               }
               leaf pdu-size {
                 description "BFD transport protocol payload size";
                 default "24";
                 type union {
                   type string {
                     pattern "<.*>|$.*";
                   }
                   type uint32 {
                     range "24 .. 16000";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               container echo {
                 description "Echo mode parameters";
                 uses apply-advanced;
                 leaf minimum-interval {
                   description "Minimum transmit and receive interval";
                   units "milliseconds";
                   type union {
                     type string {
                       pattern "<.*>|$.*";
                     }
                     type uint32 {
                       range "100 .. 255000";
                     }
                   }
                   mandatory true;
                 }
               }
               container echo-lite {
                 description "Echo-lite more parameters";
                 uses apply-advanced;
                 leaf minimum-interval {
                   description "Minimum transmit and receive interval";
                   units "milliseconds";
                   type union {
                     type string {
                       pattern "<.*>|$.*";
                     }
                     type uint32 {
                       range "1 .. 255000";
                     }
                   }
                   mandatory true;
                 }
               }
               leaf neighbor {
                 description "BFD neighbor address";
                 type jt:ipaddr;
               }
               leaf local-address {
                 description "BFD local address (for multihop only)";
                 type jt:ipaddr;
               }
               leaf holddown-interval {
                 description "Time to hold the session-UP notification to the client";
                 units "milliseconds";
                 type union {
                   type string {
                     pattern "<.*>|$.*";
                   }
                   type uint32 {
                     range "0 .. 255000";
                   }
                 }
               }
               leaf minimum-receive-ttl {
                 description "Minimum receive TTL below which to drop";
                 type union {
                   type string {
                     pattern "<.*>|$.*";
                   }
                   type uint8 {
                     range "1 .. 255";
                   }
                 }
               }
             }
             choice retain-choice {
               leaf retain {
                 description "Always keep route in forwarding table";
                 type empty;
               }
               leaf no-retain {
                 description "Don't always keep route in forwarding table";
                 type empty;
               }
             }
             choice install-choice {
               leaf install {
                 description "Install route into forwarding table";
                 type empty;
               }
               leaf no-install {
                 description "Don't install route into forwarding table";
                 type empty;
               }
             }
             choice readvertise-choice {
               leaf readvertise {
                 description "Mark route as eligible to be readvertised";
                 type empty;
               }
               leaf no-readvertise {
                 description "Don't mark route as eligible to be readvertised";
                 type empty;
               }
             }
             choice resolve-choice {
               leaf resolve {
                 description "Allow resolution of indirectly connected next hops";
                 type empty;
               }
               leaf no-resolve {
                 description "Don't allow resolution of indirectly connected next hops";
                 type empty;
               }
             }
             leaf explicit-null {
               description "Allows service label to be popped and will lookup nexthop-table inet6.0";
               type empty;
             }
             choice longest-match-choice {
               leaf longest-match {
                 description "Always use longest prefix match to resolve next hops";
                 type empty;
               }
               leaf no-longest-match {
                 description "Don't always use longest prefix match to resolve next hops";
                 type empty;
               }
             }
             choice passive_flag {
               case case_1 {
                 leaf active {
                   description "Remove inactive route from forwarding table";
                   type empty;
                 }
               }
               case case_2 {
                 leaf passive {
                   description "Retain inactive route in forwarding table";
                   type empty;
                 }
               }
             }
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
             list lsp-next-hop {
               key name;
               ordered-by user;
               description "LSP next hop";
               uses lsp_nh_obj;
             }
             container spring-te-lsp-next-hop {
               description "SPRING-TE LSP next hop";
               uses springte_lsp_nh_obj;
             }
             container p2mp-ldp-next-hop {
               description "Point-to-multipoint LDP LSP next hop";
               uses p2mp_ldp_lsp_nh_obj;
             }
           }
           leaf protocol-instance-name {
             description "Name of protocol instance under routing instance";
             type string;
           }
           container static-route {
             description "Static route Status";
             leaf bfd-admin-down {
               description "Static route State on BFD ADMIN DOWN";
               type enumeration {
                 enum "active" {
                   description "Static route will be inactive on bfd-admin-down";
                 }
                 enum "passive" {
                   description "Static route will remain active on bfd-admin-down";
                 }
               }
             }
           }
           list route-target-filter {
             key name;
             description "Route-target-filter route";
             leaf name {
               type string {
                 length "1 .. 47";
               }
             }
             uses apply-advanced;
             leaf autonomous-system {
               description "BGP AS for filter, overriding global configuration";
               type string {
               }
             }
             leaf-list community {
               ordered-by user;
               description "BGP community identifier";
               type jt:community;
             }
             leaf-list neighbor {
               ordered-by user;
               description "BGP peers for filter";
               type jt:ipaddr-scoped;
             }
             leaf-list group {
               ordered-by user;
               description "BGP groups for filter";
               type string;
             }
             leaf local {
               description "Locally originated filter";
               type empty;
             }
           }
           list route-target-community-filter {
             key name;
             description "Route-target-filter communites";
             leaf name {
               type string;
             }
             uses apply-advanced;
             leaf autonomous-system {
               description "BGP AS for filter, overriding global configuration";
               type string {
               }
             }
             leaf-list community {
               ordered-by user;
               description "BGP community identifier";
               type jt:community;
             }
             leaf-list neighbor {
               ordered-by user;
               description "BGP peers for filter";
               type jt:ipaddr-scoped;
             }
             leaf-list group {
               ordered-by user;
               description "BGP groups for filter";
               type string;
             }
             leaf local {
               description "Locally originated filter";
               type empty;
             }
           }
         }
         list martians {
           key "address choice-ident choice-value";
           ordered-by user;
           description "Invalid routes";
           uses martian_type;
         }
         container aggregate {
           description "Coalesced routes";
           uses rib_aggregate_type;
         }
         container generate {
           description "Route of last resort";
           uses rib_aggregate_type;
         }
         choice maximum-paths-type {
           case case_1 {
             container maximum-routes {
               description "Maximum number of routes";
               status deprecated;
               leaf limit {
                 description "Maximum number of routes";
                 type union {
                   type string {
                     pattern "<.*>|$.*";
                   }
                   type uint32 {
                     range "1 .. 4294967295";
                   }
                 }
                 mandatory true;
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
           case case_2 {
             container maximum-paths {
               description "Maximum number of paths";
               leaf limit {
                 description "Maximum number of paths";
                 type union {
                   type string {
                     pattern "<.*>|$.*";
                   }
                   type uint32 {
                     range "1 .. 4294967295";
                   }
                 }
                 mandatory true;
               }
               choice log_type {
                 case case_1 {
                   leaf threshold {
                     description "Percentage of limit at which to start generating warnings";
                     type union {
                       type string {
                         pattern "<.*>|$.*";
                       }
                       type uint32 {
                         range "1 .. 100";
                       }
                     }
                   }
                 }
                 case case_2 {
                   leaf log-only {
                     description "Generate warning messages only";
                     type empty;
                   }
                 }
               }
               leaf log-interval {
                 description "Minimum interval between log messages";
                 units "seconds";
                 type union {
                   type string {
                     pattern "<.*>|$.*";
                   }
                   type uint32 {
                     range "5 .. 86400";
                   }
                 }
               }
             }
           }
         }
         container maximum-prefixes {
           description "Maximum number of prefixes";
           leaf limit {
             description "Maximum number of prefixes";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container multipath {
           presence "enable multipath";
           description "Protocol-independent load balancing";
           uses apply-advanced;
           container vpn-unequal-cost {
             presence "enable vpn-unequal-cost";
             description "Include VPN routes with unequal IGP metrics";
             leaf equal-external-internal {
               description "Include external and internal VPN routes";
               type empty;
             }
           }
           leaf as-path-compare {
             description "Compare AS path sequences in addition to AS path length";
             type empty;
           }
           leaf preserve-nexthop-hierarchy {
             description "Force multipath to create List nexthop";
             type empty;
           }
         }
         container policy-multipath {
           description "Policy based multipath";
           uses apply-advanced;
           leaf-list policy {
             ordered-by user;
             description "Import policy to create policy based multipath";
             type jt:policy-algebra;
           }
           container traceoptions {
             description "Trace options";
             uses apply-advanced;
             container file {
               description "Trace file options";
               leaf filename {
                 description "Name of file in which to write trace information";
                 type string {
                   length "1 .. 1024";
                 }
                 mandatory true;
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "route" {
                     description "Policy-multipath route tracing.";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf preserve-nexthop-hierarchy {
             description "Enable preserved nexthop hierarchy";
             type empty;
           }
         }
         container protect {
           description "Protocol-independent protection";
           leaf core {
             description "Protect against unreachability to service-edge router";
             type empty;
           }
         }
         container access {
           description "Access routes";
           uses apply-advanced;
           list route {
             key name;
             ordered-by user;
             description "Access route";
             leaf name {
               description "IP address of destination";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
             leaf metric {
               description "Metric value";
               type union {
                 type string {
                   pattern "<.*>|$.*";
                 }
                 type uint32 {
                   range "1 .. 255";
                 }
               }
             }
             leaf preference {
               description "Preference value";
               type union {
                 type uint32;
                 type string {
                   pattern "<.*>|$.*";
                 }
               }
             }
             leaf tag {
               description "Tag string";
               type union {
                 type uint32;
                 type string {
                   pattern "<.*>|$.*";
                 }
               }
             }
             leaf tag2 {
               description "Tag2 string";
               type union {
                 type uint32;
                 type string {
                   pattern "<.*>|$.*";
                 }
               }
             }
           }
         }
         container access-internal {
           description "Access-internal routes";
           uses apply-advanced;
           list route {
             key name;
             ordered-by user;
             description "Access-internal route";
             leaf name {
               description "IP address and optional prefix length of destination";
               type jt:ipprefix;
             }
             uses apply-advanced;
             leaf-list next-hop {
               ordered-by user;
               description "Next hop to destination";
               type union {
                 type jt:ipaddr-or-interface;
                 type string {
                   pattern "<.*>|$.*";
                 }
               }
             }
             list qualified-next-hop {
               key name;
               ordered-by user;
               description "Next hop with qualifiers";
               uses qualified_nh_obj;
             }
           }
         }
         container bgp-static {
           description "Routes for BGP static advertisements";
           uses apply-advanced;
           list route {
             key name;
             ordered-by user;
             description "BGP-static route";
             leaf name {
               description "IP address and optional prefix length of destination";
               type jt:ipprefix;
             }
             uses apply-advanced;
             container metric {
               description "Metric value";
               presence "enable metric";
               uses rib_static_metric_type;
             }
             container metric2 {
               description "Metric value 2";
               presence "enable metric2";
               uses rib_static_metric_type;
             }
             container metric3 {
               description "Metric value 3";
               presence "enable metric3";
               uses rib_static_metric_type;
             }
             container metric4 {
               description "Metric value 4";
               presence "enable metric4";
               uses rib_static_metric_type;
             }
             container tag {
               description "Tag string";
               presence "enable tag";
               uses rib_static_metric_type;
             }
             container tag2 {
               description "Tag string 2";
               presence "enable tag2";
               uses rib_static_metric_type;
             }
             container preference {
               description "Preference value";
               presence "enable preference";
               uses rib_static_metric_type;
             }
             container preference2 {
               description "Preference value 2";
               presence "enable preference2";
               uses rib_static_metric_type;
             }
             container color {
               description "Color (preference) value";
               presence "enable color";
               uses rib_static_metric_type;
             }
             container color2 {
               description "Color (preference) value 2";
               presence "enable color2";
               uses rib_static_metric_type;
             }
             leaf-list community {
               ordered-by user;
               description "BGP community identifier";
               type jt:community;
             }
             container as-path {
               description "Autonomous system path";
               uses apply-advanced;
               leaf path {
                 description "Autonomous system path";
                 type string;
               }
               leaf origin {
                 type enumeration {
                   enum "igp" {
                     description "Path originated in the local IGP";
                   }
                   enum "egp" {
                     description "Path originated in another AS";
                   }
                   enum "incomplete" {
                     description "Path was learned by some other means";
                   }
                 }
               }
               leaf atomic-aggregate {
                 description "Add ATOMIC_AGGREGATE path attribute to route";
                 type empty;
               }
               container aggregator {
                 presence "enable aggregator";
                 description "Add AGGREGATOR path attribute to route";
               }
               leaf as-number {
                 description " Autonomous system number in plain number or 'higher 16bits'.'Lower 16 bits' (asdot notation) format";
                 type string {
                 }
               }
               leaf address {
                 description "Address of BGP system that formed the route";
                 type jt:ipv4addr;
               }
             }
           }
         }
         container flow {
           description "Locally defined flow routing information";
           uses apply-advanced;
           container validation {
             description "Flow route validation options";
             presence "enable validation";
             uses flow-validation;
           }
           list route {
             key name;
             ordered-by user;
             description "Flow route";
             uses flow-route-inet6;
           }
           container interface-group {
             description "Interface-group for applying flow-spec filter";
             uses flow-interface-group;
           }
           leaf discard-action-for-unresolved-redir-addr {
             description "For action redirect IP if redirect address is unresolved install discard action filter";
             type empty;
           }
           choice per-route-accounting-choice {
             leaf per-route-accounting {
               description "Enable traffic accounting per flowspec route";
               type empty;
             }
             leaf no-per-route-accounting {
               description "Don't enable traffic accounting per flowspec route";
               type empty;
             }
           }
         }
         container rib-export {
           presence "enable rib-export";
           description "Group of routing tables to import the routes";
           uses apply-advanced;
           leaf ribexport-name {
             description "RIB export group name";
             type string;
           }
         }
         container label {
           presence "enable label";
           description "Label processing";
           uses apply-advanced;
           leaf-list allocation {
             ordered-by user;
             description "Label allocation policy";
             type jt:policy-algebra;
           }
           leaf-list substitution {
             ordered-by user;
             description "Label substitution policy";
             type jt:policy-algebra;
           }
         }
         leaf-list vpn-global-import {
           ordered-by user;
           description "Import policy for L3VPN routes to global RIB";
           type jt:policy-algebra;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container multicast {
         description "Global multicast options";
         uses apply-advanced;
         container traceoptions {
           description "Global multicast trace options";
           uses apply-advanced;
           container file {
             description "Trace file options";
             leaf filename {
               description "Name of file in which to write trace information";
               type string {
                 length "1 .. 1024";
               }
               mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "parse" {
                   description "Trace configuration parsing";
                 }
                 enum "config-internal" {
                   description "Trace configuration internals";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf disable {
               description "Disable this trace flag";
               type empty;
             }
           }
         }
         leaf rpf {
           status deprecated;
           type string;
         }
         list scope {
           key name;
           ordered-by user;
           description "Multicast address scope";
           leaf name {
             description "Name to identify multicast address scope";
             type string;
           }
           uses apply-advanced;
           leaf prefix {
             description "Administratively scoped address";
             type jt:ipprefix;
             mandatory true;
           }
           leaf-list interface {
             ordered-by user;
             description "Interface on which to configure scoping";
             type union {
               type jt:interface-name;
               type string {
                 pattern "<.*>|$.*";
               }
             }
           }
         }
         leaf-list scope-policy {
           ordered-by user;
           description "Scoping policy";
           type jt:policy-algebra;
         }
         list flow-map {
           key name;
           ordered-by user;
           description "Multicast flow map configuration";
           leaf name {
             description "Name of the flow map";
             type string;
           }
           uses apply-advanced;
           leaf-list policy {
             ordered-by user;
             description "Policy for matched flows";
             type jt:policy-algebra;
           }
           container bandwidth {
             presence "enable bandwidth";
             description "Bandwidth properties for matched flows";
             leaf bandwidth-value {
               description "Static or default bandwidth for the matched flows";
               units "bps";
               type string;
             }
             leaf adaptive {
               description "Auto-sense bandwidth for matched flows";
               type empty;
             }
           }
           leaf-list redundant-sources {
             ordered-by user;
             description "Redundant source addresses";
             type jt:ipaddr;
           }
           container forwarding-cache {
             description "Forwarding cache properties for matched flows";
             uses apply-advanced;
             container timeout {
               description "Timeout properties for matched flows";
               choice timeout_choice {
                 case case_1 {
                   leaf timeout-value {
                     description "Timeout for forwarding cache entry";
                     units "minutes";
                     type union {
                       type string {
                         pattern "<.*>|$.*";
                       }
                       type uint32 {
                         range "1 .. 720";
                       }
                     }
                   }
                 }
                 case case_2 {
                   container never {
                     presence "enable never";
                     description "Forwarding cache entries never time out";
                     uses apply-advanced;
                     leaf non-discard-entry-only {
                       description "Apply only to non-discard entries";
                       type empty;
                     }
                   }
                 }
               }
             }
           }
         }
         leaf-list resolve-filter {
           ordered-by user;
           description "Multicast resolve policy filter";
           status deprecated;
           type jt:policy-algebra;
         }
         leaf-list ssm-groups {
           ordered-by user;
           description "Source-specific multicast group ranges";
           type jt:ipprefix;
         }
         leaf cont-stats-collection-interval {
           description "IGMP/MLD continuous statistics collection interval";
           default "300";
           type union {
             type string {
               pattern "<.*>|$.*";
             }
             type uint16 {
               range "60 .. 3600";
             }
           }
         }
         leaf asm-override-ssm {
           description "Allow ASM state for SSM group ranges";
           type empty;
         }
         leaf-list rpf-check-policy {
           ordered-by user;
           description "Disable RPF check for a source group pair";
           type jt:policy-algebra;
         }
         container pim-to-igmp-proxy {
           description "PIM-to-IGMP proxy";
           uses apply-advanced;
           leaf-list upstream-interface {
             ordered-by user;
             description "Upstream interface list";
             type union {
               type jt:interface-name;
               type string {
                 pattern "<.*>|$.*";
               }
             }
             max-elements 2;
           }
         }
         container pim-to-mld-proxy {
           description "PIM-to-MLD proxy";
           uses apply-advanced;
           leaf-list upstream-interface {
             ordered-by user;
             description "Upstream interface list";
             type union {
               type jt:interface-name;
               type string {
                 pattern "<.*>|$.*";
               }
             }
             max-elements 2;
           }
         }
         leaf resolve-request-holdcount {
           description "Set resolve request holdcount for multicast";
           type union {
             type string {
               pattern "<.*>|$.*";
             }
             type uint32 {
               range "0 .. 256";
             }
           }
         }
         container forwarding-cache {
           description "Multicast forwarding cache";
           uses apply-advanced;
           leaf allow-maximum {
             description "Allow maximum of global and family level threshold values for suppress and reuse";
             type empty;
           }
           list family {
             key name;
             ordered-by user;
             description "Protocol family";
             leaf name {
               description "Protocol family";
               type enumeration {
                 enum "inet" {
                   description "IPv4 family";
                 }
                 enum "inet6" {
                   description "IPv6 family";
                 }
               }
             }
             uses apply-advanced;
             container threshold {
               presence "enable threshold";
               description "Multicast forwarding cache suppress threshold";
               uses apply-advanced;
               leaf suppress {
                 description "Suppress threshold";
                 type union {
                   type string {
                     pattern "<.*>|$.*";
                   }
                   type uint32 {
                     range "1 .. 200000";
                   }
                 }
                 mandatory true;
               }
               leaf reuse {
                 description "Reuse threshold";
                 type union {
                   type string {
                     pattern "<.*>|$.*";
                   }
                   type uint32 {
                     range "1 .. 200000";
                   }
                 }
               }
               leaf mvpn-rpt-suppress {
                 description "MVPN RP tree entry suppress threshold";
                 type union {
                   type string {
                     pattern "<.*>|$.*";
                   }
                   type uint32 {
                     range "1 .. 200000";
                   }
                 }
               }
               leaf mvpn-rpt-reuse {
                 description "MVPN RP tree entry reuse threshold";
                 type union {
                   type string {
                     pattern "<.*>|$.*";
                   }
                   type uint32 {
                     range "1 .. 200000";
                   }
                 }
               }
               leaf log-warning {
                 description "Percentage at which to start generating warnings";
                 type union {
                   type string {
                     pattern "<.*>|$.*";
                   }
                   type uint32 {
                     range "1 .. 100";
                   }
                 }
               }
             }
           }
           container threshold {
             description "Threshold";
             uses apply-advanced;
             leaf suppress {
               description "Suppress threshold";
               type union {
                 type string {
                   pattern "<.*>|$.*";
                 }
                 type uint32 {
                   range "1 .. 200000";
                 }
               }
               mandatory true;
             }
             leaf reuse {
               description "Reuse threshold";
               type union {
                 type string {
                   pattern "<.*>|$.*";
                 }
                 type uint32 {
                   range "1 .. 200000";
                 }
               }
             }
             leaf mvpn-rpt-suppress {
               description "MVPN RP tree entry suppress threshold";
               type union {
                 type string {
                   pattern "<.*>|$.*";
                 }
                 type uint32 {
                   range "1 .. 200000";
                 }
               }
             }
             leaf mvpn-rpt-reuse {
               description "MVPN RP tree entry reuse threshold";
               type union {
                 type string {
                   pattern "<.*>|$.*";
                 }
                 type uint32 {
                   range "1 .. 200000";
                 }
               }
             }
             leaf log-warning {
               description "Percentage at which to start generating warnings";
               type union {
                 type string {
                   pattern "<.*>|$.*";
                 }
                 type uint32 {
                   range "1 .. 100";
                 }
               }
             }
           }
           leaf timeout {
             description "Forwarding cache entry timeout in minutes";
             type union {
               type string {
                 pattern "<.*>|$.*";
               }
               type uint32 {
                 range "1 .. 720";
               }
             }
           }
         }
         list interface {
           key name;
           ordered-by user;
           description "Multicast interface options";
           uses multicast_interface_options_type;
         }
         list ssm-map {
           key name;
           ordered-by user;
           description "SSM map definitions";
           leaf name {
             description "SSM map name";
             type string;
           }
           uses apply-advanced;
           leaf-list policy {
             ordered-by user;
             description "Policy for matching group";
             type jt:policy-algebra;
           }
           leaf-list source {
             ordered-by user;
             description "One or more source addresses";
             type jt:ipaddr;
           }
         }
         list backup-pe-group {
           key name;
           ordered-by user;
           description "Backup PE group definitions";
           leaf name {
             description "PE group name";
             type string;
           }
           uses apply-advanced;
           leaf-list backups {
             ordered-by user;
             description "One or more IP addresses";
             type jt:ipaddr;
             max-elements 8;
           }
           leaf local-address {
             description "Address to be used as local-address for this group";
             type jt:ipaddr;
             mandatory true;
           }
         }
         leaf omit-wildcard-address {
           description "Omit wildcard source/group fields in SPMSI AD NLRI";
           type empty;
         }
         leaf local-address {
           description "Local address for PIM and MVPN sessions";
           type jt:ipv4addr;
         }
       }
     }
     container firewall {
       description "Define a firewall configuration";
       uses apply-advanced;
       container family {
         description "Protocol family";
         container inet {
           description "Protocol family IPv4 for firewall filter";
           uses apply-advanced;
           list prefix-action {
             key name;
             ordered-by user;
             description "Define a prefix action";
             uses prefix_action;
           }
           list filter {
             key name;
             description "Define an IPv4 firewall filter";
             uses inet_filter;
           }
           list service-filter {
             key name;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list filter {
             key name;
             description "Define an IPv6 firewall filter";
             uses inet6_filter;
           }
           list service-filter {
             key name;
             description "One or more IPv6 service filters";
             uses inet6_service_filter;
           }
           list fast-update-filter {
             key name;
             ordered-by user;
             description "One or more fast update filters";
             uses inet6_fuf;
           }
         }
         container vpls {
           description "Protocol family VPLS for firewall filter";
           uses apply-advanced;
           list filter {
             key name;
             uses vpls_filter;
           }
         }
         container evpn {
           description "Protocol family EVPN for firewall filter";
           uses apply-advanced;
           list filter {
             key name;
             uses vpls_filter;
           }
         }
         container ccc {
           description "Protocol family CCC for firewall filter";
           uses apply-advanced;
           list filter {
             key name;
             uses ccc_filter;
           }
         }
         container any {
           description "Protocol-independent filter";
           uses apply-advanced;
           list filter {
             key name;
             description "Define a protocol independent filter";
             uses any_filter;
           }
         }
         container ethernet-switching {
           description "Protocol family Ethernet Switching for firewall filter";
           uses apply-advanced;
           list filter {
             key name;
             description "Define an Ethernet Switching firewall filter";
             uses es_filter;
           }
         }
       }
       list policer {
         key name;
         description "Policer template definition";
         uses firewall_policer;
       }
       list flexible-match {
         key name;
         description "Flexible packet match template definition";
         uses firewall_flexible_match;
       }
       list tunnel-end-point {
         key name;
         description "Tunnel end-point template definition";
         uses tunnel_end_point;
       }
       list hierarchical-policer {
         key name;
         description "Hierarchical policer template definition";
         uses firewall_hierpolicer;
       }
       leaf disable-arp-policers {
         description "Disables ARP policers";
         type empty;
       }
       list interface-set {
         key name;
         description "Interface set definition";
         uses interface_set_type;
       }
       list filter {
         key name;
         description "Define an IPv4 firewall filter";
         uses inet_filter;
       }
     }
     container services {
       description "Service PIC applications settings";
       uses apply-advanced;
       container inline-napt {
         presence "enable inline-napt";
         description "Inline-NAPT configuration";
         uses apply-advanced;
         container nat44 {
           presence "enable nat44";
           uses apply-advanced;
           choice enable-disable {
             case case_1 {
               leaf disable {
                 description "Disable NAT44 on this interface";
                 type empty;
               }
             }
           }
         }
         container nat64 {
           presence "enable nat64";
           uses apply-advanced;
           choice enable-disable {
             case case_1 {
               leaf disable {
                 description "Disable NAT64 on this interface";
                 type empty;
               }
             }
           }
         }
       }
       container external-napt {
         presence "enable external-napt";
         description "External-NAPT configuration";
         uses apply-advanced;
         choice enable-disable {
           case case_1 {
             leaf disable {
               description "Disable External-NAPT";
               type empty;
             }
           }
         }
       }
     }
     list profile-variable-set {
       key name;
       ordered-by user;
       description "Dynamic profiles variable configuration";
       uses juniper-dynamic-profile-varset-object;
     }
     container policy-options {
       description "Routing policy option configuration";
       uses apply-advanced;
       list prefix-list {
         key name;
         description "Define a named set of address prefixes";
         leaf name {
           description "Prefix list name";
           type string;
         }
         uses apply-advanced;
         list prefix-list-item {
           key name;
           uses prefix_list_items;
         }
         leaf apply-path {
           description "Apply IP prefixes from a configuration statement";
           type string;
         }
       }
     }
     container extensible-subscriber-services {
       presence "enable extensible-subscriber-services";
       description "Extensible subscriber services";
       uses apply-advanced;
       leaf-list vsas {
         ordered-by user;
         description "Service VSAs";
         type string;
       }
     }
     container access-cac {
       description "Access ucac configuration";
       uses apply-advanced;
       list interface {
         key name;
         ordered-by user;
         description "Access ucac interface options";
         uses access_cac_interface_options;
       }
     }
     container profile-type {
       presence "enable profile-type";
       description "Profile type";
       uses apply-advanced;
       leaf remote-device-service {
         description "Service profile to be programmed on a remote device";
         type empty;
       }
     }
   }
   grouping access_cac_interface_options {
     description "Access ucac interface options";
     leaf name {
       description "Interface name";
       type union {
         type jt:interface-unit;
         type string {
           pattern "<.*>|$.*";
         }
       }
     }
     uses apply-advanced;
     container multicast-video-bandwidth {
       presence "enable multicast-video-bandwidth";
       description "Maximum multicast bandwidth for the interface";
       leaf access-cac-bandwidth {
         description "Bandwidth used in access cac configuration";
         units "bps";
         type string;
       }
     }
     container video-bandwidth {
       presence "enable video-bandwidth";
       description "Maximum video bandwidth for the interface";
       leaf access-cac-bandwidth {
         description "Bandwidth used in access cac configuration";
         units "bps";
         type string;
       }
     }
     choice isqos {
       case case_1 {
         leaf no-qos-adjust {
           description "No qos adjustment";
           type empty;
         }
       }
       case case_2 {
         container qos-adjust-hierarchical {
           description "Ucac interface set configuration";
           uses apply-advanced;
           leaf interface-set {
             description "Enable hierarchical adjust on iflset";
             type empty;
           }
         }
       }
     }
     list multicast-video-policy {
       key name;
       ordered-by user;
       description "Mcast video policy";
       leaf name {
         description "Mcast video policy name";
         type string {
           length "1 .. 64";
         }
       }
       uses apply-advanced;
       container family {
         presence "enable family";
         description "Access cac multicast policy family";
         uses apply-advanced;
         choice family_type {
           case case_1 {
             container inet {
               presence "enable inet";
               description "Family inet";
               uses apply-advanced;
               leaf-list source {
                 description "One or more multicast source addresses";
                 type jt:ipv4addr;
               }
               leaf-list group {
                 ordered-by user;
                 description "One or more multicast group addresses";
                 type jt:ipv4addr;
               }
             }
           }
           case case_2 {
             container inet6 {
               presence "enable inet6";
               description "Family inet6";
               uses apply-advanced;
               leaf-list source {
                 description "One or more multicast source addresses";
                 type jt:ipv6addr;
               }
               leaf-list group {
                 ordered-by user;
                 description "One or more multicast group addresses";
                 type jt:ipv6addr;
               }
             }
           }
         }
       }
       container bandwidth {
         presence "enable bandwidth";
         description "Maximum video bandwidth for the interface";
         uses apply-advanced;
         leaf access-cac-bandwidth {
           description "Bandwidth used in access cac configuration";
           units "bps";
           type string;
         }
       }
       leaf adaptive {
         description "Use multicast real traffic rate";
         type empty;
       }
     }
   }
   grouping base-default-variable-object {
     leaf name {
       description "Name of predefined variable";
       type enumeration {
         enum "igmp-enable" {
           description "Default for junos-igmp-enable";
         }
         enum "igmp-access-group-name" {
           description "Default for junos-igmp-access-group-name";
         }
         enum "igmp-access-source-group-name" {
           description "Default for junos-igmp-access-group-name";
         }
         enum "igmp-version" {
           description "Default for junos-igmp-version";
         }
         enum "igmp-immediate-leave" {
           description "Default for junos-igmp-immediate-leave";
         }
         enum "mld-access-group-name" {
           description "Default for junos-mld-access-group-name";
         }
         enum "mld-access-source-group-name" {
           description "Default for junos-mld-access-source-group-name";
         }
         enum "mld-immediate-leave" {
           description "Default for junos-mld-immediate-leave";
         }
         enum "input-filter" {
           description "Default for junos-input-filter";
         }
         enum "output-filter" {
           description "Default for junos-output-filter";
         }
         enum "input-interface-filter" {
           description "Default for junos-input-interface-filter";
         }
         enum "output-interface-filter" {
           description "Default for junos-output-interface-filter";
         }
         enum "input-ipv6-filter" {
           description "Default for junos-input-ipv6-filter";
         }
         enum "output-ipv6-filter" {
           description "Default for junos-output-ipv6-filter";
         }
         enum "adf-rule-v4" {
           description "Default for junos-adf-rule-v4";
         }
         enum "adf-rule-v6" {
           description "Default for junos-adf-rule-v6";
         }
         enum "cos-scheduler-map" {
           description "Default for junos-cos-scheduler-map";
         }
         enum "cos-shaping-rate" {
           description "Default for junos-cos-shaping-rate";
         }
         enum "cos-guaranteed-rate" {
           description "Default for junos-cos-guaranteed-rate";
         }
         enum "cos-delay-buffer-rate" {
           description "Default for junos-cos-delay-buffer-rate";
         }
         enum "cos-traffic-control-profile" {
           description "Default for junos-cos-traffic-control-profile";
         }
         enum "cos-shaping-mode" {
           description "Default for junos-cos-shaping-mode";
         }
         enum "cos-byte-adjust" {
           description "Default for junos-cos-byte-adjust";
         }
         enum "cos-scheduler" {
           description "Default for junos-cos-scheduler";
         }
         enum "cos-scheduler-pri" {
           description "Default for junos-cos-scheduler-pri";
         }
         enum "cos-scheduler-dropfile-low" {
           description "Default for junos-cos-scheduler-dropfile-low";
         }
         enum "cos-scheduler-dropfile-medium-low" {
           description "Default for junos-cos-scheduler-dropfile-medium-low";
         }
         enum "cos-scheduler-dropfile-medium-high" {
           description "Default for junos-cos-scheduler-dropfile-medium-high";
         }
         enum "cos-scheduler-dropfile-high" {
           description "Default for junos-cos-scheduler-dropfile-high";
         }
         enum "cos-scheduler-dropfile-any" {
           description "Default for junos-cos-scheduler-dropfile-any";
         }
         enum "cos-scheduler-excess-rate" {
           description "Default for junos-cos-scheduler-excess-rate";
         }
         enum "cos-scheduler-explicit-congestion-notification" {
           description "Default for junos-cos-scheduler-explicit-congestion-notification";
         }
         enum "cos-scheduler-ecn-rtlog-rate-limit" {
           description "Default for junos-cos-scheduler-ecn-rtlog-rate-limit";
         }
         enum "cos-scheduler-excess-priority" {
           description "Default for junos-cos-scheduler-excess-priority";
         }
         enum "cos-adjust-minimum" {
           description "Default for junos-cos-adjust-minimum";
         }
         enum "cos-excess-rate-high" {
           description "Default for junos-cos-excess-rate-high";
         }
         enum "cos-excess-rate-low" {
           description "Default for junos-cos-excess-rate-low";
         }
         enum "cos-shaping-rate-burst" {
           description "Default for junos-cos-shaping-rate-burst";
         }
         enum "cos-byte-adjust-frame" {
           description "Default for junos-cos-byte-adjust-frame";
         }
         enum "cos-byte-adjust-cell" {
           description "Default for junos-cos-byte-adjust-cell";
         }
         enum "cos-shaping-rate-priority-high" {
           description "Default for junos-cos-shaping-rate-priority-high";
         }
         enum "cos-shaping-rate-priority-high-burst" {
           description "Default for junos-cos-shaping-rate-priority-high-burst";
         }
         enum "cos-shaping-rate-priority-medium" {
           description "Default for junos-cos-shaping-rate-priority-medium";
         }
         enum "cos-shaping-rate-priority-medium-burst" {
           description "Default for junos-cos-shaping-rate-priority-medium-burst";
         }
         enum "cos-shaping-rate-priority-low" {
           description "Default for junos-cos-shaping-rate-priority-low";
         }
         enum "cos-shaping-rate-priority-low-burst" {
           description "Default for junos-cos-shaping-rate-priority-low-burst";
         }
         enum "cos-shaping-rate-excess-high" {
           description "Default for junos-cos-shaping-rate-excess-high";
         }
         enum "cos-shaping-rate-excess-high-burst" {
           description "Default for junos-cos-shaping-rate-excess-high-burst";
         }
         enum "cos-shaping-rate-excess-low" {
           description "Default for junos-cos-shaping-rate-excess-low";
         }
         enum "cos-shaping-rate-excess-low-burst" {
           description "Default for junos-cos-shaping-rate-excess-low-burst";
         }
         enum "cos-guaranteed-rate-burst" {
           description "Default for junos-cos-guaranteed-rate-burst";
         }
         enum "cos-traffic-control-profile-remaining" {
           description "Default for junos-cos-traffic-control-profile-remaining";
         }
         enum "cos-shaping-rate-granularity" {
           description "Default for junos-cos-shaping-rate-granluarity";
         }
         enum "cos-number-of-queues" {
           description "Default for junos-cos-number-of-queues";
         }
         enum "cos-rewrite-rules-dscp" {
           description "Default for junos-cos-rewrite-rules-dscp";
         }
         enum "cos-rewrite-rules-dscp-ipv6" {
           description "Default for junos-cos-rewrite-rules-dscp-ipv6";
         }
         enum "cos-rewrite-rules-exp" {
           description "Default for junos-cos-rewrite-rules-exp";
         }
         enum "cos-rewrite-rules-ieee802-1" {
           description "Default for junos-cos-rewrite-rules-ieee802-1";
         }
         enum "cos-rewrite-rules-ieee802-1ad" {
           description "Default for junos-cos-rewrite-rules-ieee802-1ad";
         }
         enum "cos-rewrite-rules-inet-precedence" {
           description "Default for junos-cos-rewrite-rules-inet-precedence";
         }
         enum "routing-instances" {
           description "Default for junos-routing-instance";
         }
         enum "pim-enable" {
           description "Default for junos-pim-enable";
         }
         enum "interface-mtu" {
           description "Default for junos-interface-mtu";
         }
         enum "tag-protocol-id" {
           description "Default for junos-tag-protocol-id";
         }
         enum "inner-vlan-tag-protocol-id" {
           description "Default for junos-inner-vlan-tag-protocol-id";
         }
         enum "routing-services" {
           description "Default for junos-routing-services";
         }
         enum "aggregation-interface-set-name" {
           description "Default for junos-aggregation-interface-set-name";
         }
         enum "interface-set-name" {
           description "Default for junos-interface-set-name";
         }
         enum "default-interface-set-name" {
           description "Default for junos-default-interface-set-name";
         }
         enum "phy-ifd-interface-set-name" {
           description "Default for junos-phy-ifd-interface-set-name";
         }
         enum "phy-ifd-underlying-intf-set-name" {
           description "Default for junos-phy-ifd-underlying-intf-set-name";
         }
         enum "hpolicer-high-cir" {
           description "Default for junos-hpolicer-high-cir";
         }
         enum "hpolicer-high-max-cir" {
           description "Default for junos-hpolicer-high-max-cir";
         }
         enum "hpolicer-high-committed-burst" {
           description "Default for junos-hpolicer-high-committed-burst";
         }
         enum "hpolicer-med-high-cir" {
           description "Default for junos-hpolicer-med-high-cir";
         }
         enum "hpolicer-med-high-max-cir" {
           description "Default for junos-hpolicer-med-high-max-cir";
         }
         enum "hpolicer-med-high-committed-burst" {
           description "Default for junos-hpolicer-med-high-committed-burst";
         }
         enum "hpolicer-med-low-cir" {
           description "Default for junos-hpolicer-med-low-cir";
         }
         enum "hpolicer-med-low-max-cir" {
           description "Default for junos-hpolicer-med-low-max-cir";
         }
         enum "hpolicer-med-low-committed-burst" {
           description "Default for junos-hpolicer-med-low-committed-burst";
         }
         enum "hpolicer-low-cir" {
           description "Default for junos-hpolicer-low-cir";
         }
         enum "hpolicer-low-max-cir" {
           description "Default for junos-hpolicer-low-max-cir";
         }
         enum "hpolicer-low-committed-burst" {
           description "Default for junos-hpolicer-low-committed-burst";
         }
         enum "external-napt-control" {
           description "Default for junos-external-napt-control";
         }
       }
     }
     uses apply-advanced;
     leaf default-value {
       description "Default value for predefined variable";
       type string;
     }
   }
   grouping cfm-traceoptions {
     description "Trace options for connectivity fault management";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "configuration" {
             description "Trace configuration events";
           }
           enum "routing-socket" {
             description "Trace routing socket events";
           }
           enum "protocol" {
             description "Trace protocol processing events";
           }
           enum "init" {
             description "Trace events related to protocol daemon start-up";
           }
           enum "error" {
             description "Trace events related to catestrophic errors in daemon";
           }
           enum "issu" {
             description "Trace ISSU related events";
           }
           enum "all" {
             description "Trace everything";
           }
         }
       }
     }
   }
   grouping flow-interface-group {
     leaf group {
       description "Interface group ID to match traffic";
       type union {
         type string {
           pattern "<.*>|$.*";
         }
         type uint32;
       }
       mandatory true;
     }
     leaf exclude {
       description "Don't apply flow-spec filter to traffic on this group";
       type empty;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
       mandatory true;
     }
     leaf prefix-offset {
       description "Offset from where prefix match will start";
       type union {
         type uint32;
         type string {
           pattern "<.*>|$.*";
         }
       }
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
           mandatory true;
         }
         leaf-list policy {
           ordered-by user;
           description "Filter policy";
           type jt:policy-algebra;
         }
       }
     }
   }
   grouping juniper-dynamic-profile-varset-object {
     leaf name {
       description "Profile varset associated with the profile";
       type string {
         length "1 .. 80";
       }
     }
     uses apply-advanced;
     leaf junos-mep-id {
       description "Dynamic variable to substitute 'mep' value in the profile";
       type union {
         type string {
           pattern "<.*>|$.*";
         }
         type uint32 {
           range "1 .. 8191";
         }
       }
     }
     leaf junos-md-level {
       description "Dynamic variable to substitute 'level' value in the profile";
       type union {
         type string {
           pattern "<.*>|$.*";
         }
         type uint32 {
           range "0 .. 7";
         }
       }
     }
     leaf junos-remote-mep-id {
       description "Dynamic variable to substitute 'remote-mep' value in the profile";
       type union {
         type string {
           pattern "<.*>|$.*";
         }
         type uint32 {
           range "1 .. 8191";
         }
       }
     }
     leaf junos-md-name {
       description "Dynamic variable to substitute 'maintenance-domain' in profile";
       type string;
     }
     leaf junos-ma-name {
       description "Dynamic variable to substitute 'maintenance-association' in profile";
       type string {
         length "1 .. 32";
       }
     }
     leaf junos-loss-threshold {
       description "Dynamic variable to substitute 'loss-threshold' in profile";
       type union {
         type string {
           pattern "<.*>|$.*";
         }
         type uint32 {
           range "3 .. 256";
         }
       }
     }
     leaf junos-md-name-format {
       description "Dynamic variable to substitute 'name-format' in profile";
       type enumeration {
         enum "none" {
           description "No format specified";
         }
         enum "dns" {
           description "Character string similar to Domain Name System name";
         }
         enum "mac+2oct" {
           description "MAC address with 2 octet integer (xx:xx:xx:xx:xx:xx.Y format)";
         }
         enum "character-string" {
           description "Character string";
         }
       }
     }
     leaf junos-ma-name-format {
       description "Dynamic variable to substitute 'short-name-format' in profile";
       type enumeration {
         enum "2octet" {
           description "An integer in the range 0..65535";
         }
         enum "rfc-2685-vpn-id" {
           description "VPN identifier that complies with RFC 2685";
         }
         enum "vlan" {
           description "Primary VLAN identifier";
         }
         enum "character-string" {
           description "Character string";
         }
         enum "icc" {
           description "ITU Carrier Code";
         }
       }
     }
     leaf junos-ccm-interval {
       description "Dynamic variable to substitute 'interval' in profile";
       type enumeration {
         enum "10ms" {
         }
         enum "100ms" {
         }
         enum "1s" {
         }
         enum "10s" {
         }
         enum "1m" {
         }
         enum "10m" {
         }
       }
     }
     leaf junos-action-profile {
       description "Dynamic variable to substitute 'action-profile' in profile";
       type string;
     }
     leaf junos-layer2-output-policer {
       description "Dynamic variable to substitute 'layer2 output-policer'";
       type string;
     }
   }
   grouping juniper-dynamic-variable-object {
     leaf name {
       description "Name of variable";
       type string {
       }
     }
     uses apply-advanced;
     leaf equals {
       description "Computable expression of dynamic profile variables";
       type string;
     }
     leaf default-value {
       description "Default value for variable";
       type string;
     }
     leaf mandatory {
       description "Variable must be supplied by external server";
       type empty;
     }
     leaf uid-reference {
       description "Variable that refers to the uid variable";
       type empty;
     }
     leaf uid {
       description "Compute unique Id value for the variable";
       type empty;
     }
   }
   grouping juniper-forwarding-options {
     uses apply-advanced;
     list storm-control-profiles {
       key name;
       description "Storm control profile for this instance";
       leaf name {
         description "Storm control profile name";
         type string {
           length "1 .. 127";
         }
       }
       uses apply-advanced;
       container all {
         presence "enable all";
         description "For all BUM traffic";
         uses apply-advanced;
         choice bandwidth {
           case case_1 {
             leaf bandwidth-percentage {
               description "Percentage of link bandwidth";
               type union {
                 type string {
                   pattern "<.*>|$.*";
                 }
                 type uint32;
               }
             }
           }
           case case_2 {
             leaf bandwidth-level {
               description "Link bandwidth";
               units "kbps";
               type union {
                 type string {
                   pattern "<.*>|$.*";
                 }
                 type uint32;
               }
             }
           }
         }
         leaf burst-size {
           description "Burst size";
           units "bytes";
           type union {
             type string {
               pattern "<.*>|$.*";
             }
             type uint32;
           }
         }
         leaf no-broadcast {
           description "Disable broadcast storm control";
           type empty;
         }
         leaf no-unknown-unicast {
           description "Disable unknown unicast storm control";
           type empty;
         }
         choice no-multicast-choices {
           case case_1 {
             leaf no-multicast {
               description "Disable multicast storm control";
               type empty;
             }
           }
           case case_2 {
             leaf no-registered-multicast {
               description "Disable registered multicast storm control";
               type empty;
             }
           }
           case case_3 {
             leaf no-unregistered-multicast {
               description "Disable unregistered multicast storm control";
               type empty;
             }
           }
         }
       }
       leaf action-shutdown {
         description "Disable port for excessive storm control errors";
         type empty;
       }
     }
     leaf tunnel-termination {
       description "Enable tunnel termination for all interfaces";
       type empty;
     }
     choice sampling-or-packet-capture {
       case case_1 {
         container sampling {
           description "Statistical traffic sampling options";
           uses juniper-sampling-options;
         }
       }
       case case_2 {
       }
     }
     list accounting {
       key name;
       description "Configure accounting of traffic";
       uses juniper-packet-accounting-options;
     }
     list analyzer {
       key name;
       description "Analyzer options";
       uses smpl-analyzer-type;
     }
     container port-mirroring {
       description "Configure port mirroring of traffic";
       uses juniper-port-mirror-options;
     }
     container pfe-sensor {
       description "Enable sensor for pfe resources";
       uses apply-advanced;
       container npu-memory {
         description "Gather npu memory information";
         uses apply-advanced;
         container resource-list {
           description "List of resources monitored for pfe sensors";
           uses apply-advanced;
           leaf l3-next-hop {
             description "Fetch l3 next hop information";
             type empty;
           }
           leaf host-ipv4 {
             description "Fetch host ipv4 information";
             type empty;
           }
           leaf host-ipv6 {
             description "Fetch host ipv6 information";
             type empty;
           }
           leaf lpm-table-ipv4 {
             description "Fetch lpm table ipv4 information";
             type empty;
           }
           leaf lpm-table-ipv6-64 {
             description "Fetch lpm table ipv6 information for /64 prefix routes";
             type empty;
           }
           leaf lpm-table-ipv6-128 {
             description "Fetch lpm table ipv6 information for /128 prefix routes";
             type empty;
           }
           leaf egress-l3-interface {
             description "Fetch egress l3 interface information";
             type empty;
           }
           leaf vport {
             description "Fetch vport information";
             type empty;
           }
           leaf mpls-swap-table {
             description "Fetch mpls swap table information";
             type empty;
           }
           leaf mpls-ingress-table {
             description "Fetch mpls ingress table information";
             type empty;
           }
           leaf tunnel-table {
             description "Fetch mpls/Ip tunnel table information";
             type empty;
           }
           leaf vfp {
             description "Fetch vlan filter information";
             type empty;
           }
           leaf ifp {
             description "Fetch ingress filter information";
             type empty;
           }
           leaf efp {
             description "Fetch egress filter information";
             type empty;
           }
           leaf ecmp-group-table {
             description "Fetch ecmp group table information";
             type empty;
           }
           leaf ecmp-member-table {
             description "Fetch ecmp member table information";
             type empty;
           }
         }
       }
     }
     container evpn-vxlan {
       description "EVPN VXLAN configurations";
       uses apply-advanced;
       leaf shared-tunnels {
         description "Create VTEP tunnels to EVPN PE";
         type empty;
       }
       leaf bridge-domain-index-ecmp {
         description "Bridge Domain Index based control plane ECMP";
         type empty;
       }
       leaf skip-install-wan-host-route {
         description "Don't install Type-2 dest routes learnt from WAN DCI peers";
         type empty;
       }
       container host-originated-packets {
         presence "enable host-originated-packets";
         description "Host Originated Packets";
         uses apply-advanced;
         leaf gbp-src-tag {
           description "GBP source tag for host originated packets";
           type union {
             type string {
               pattern "<.*>|$.*";
             }
             type uint32 {
               range "1 .. 65535";
             }
           }
         }
       }
       container reroute-address {
         description "Reroute IP address for vxlan encapsulation";
         uses apply-advanced;
         choice family {
           case case_1 {
             container inet {
               presence "enable inet";
               description "IPv4 address family";
               uses apply-advanced;
               leaf address {
                 description "Reroute address for IPV4 FRR";
                 type jt:ipv4addr;
                 mandatory true;
               }
             }
           }
           case case_2 {
             container inet6 {
               presence "enable inet6";
               description "IPv6 address family";
               uses apply-advanced;
               leaf address {
                 description "Reroute address for IPV6 FRR";
                 type jt:ipv6addr;
                 mandatory true;
               }
             }
           }
         }
       }
       container gbp {
         description "Group Based Policy options";
         uses apply-advanced;
         leaf ingress-enforcement {
           description "Enable GBP ingress policy enforcement (restarts PFE if standalone and need reboot for VC)";
           type empty;
         }
         leaf tag-only-policy {
           description "Support only src and dst GBP tag match (restarts PFE if standalone and need reboot for VC)";
           type empty;
         }
         leaf mac-ip-inter-tagging {
           description "Enable MAC/IP inter GBP tagging (restarts PFE if standalone and need reboot for VC)";
           type empty;
         }
         container ingress-src-tag {
           description "Assign source tag to filter matched pfx routes under this routing instance";
           uses apply-advanced;
           choice filter_choice {
             case case_1 {
               leaf-list filter {
                 ordered-by user;
                 description "List of filter modules having src tag";
                 type string;
               }
             }
           }
         }
       }
       leaf vxlan-trans-vni-enable {
         description "Enable VxLAN Translated VNI in DCI. This will restart PFE";
         type empty;
       }
       leaf vxlan-dci-enable {
         description "Enable VxLAN DCI Egr Xlate carvings. This will restart PFE";
         type empty;
       }
     }
     container multicast-replication {
       description "Set mode of multicast replication";
       uses apply-advanced;
       container evpn {
         description "EVPN IRB multicast related options";
         uses apply-advanced;
         leaf irb {
           type enumeration {
             enum "local-only" {
               description "Multicast forward in local-only mode";
             }
             enum "local-remote" {
               description "Multicast forward in local-remote mode";
             }
             enum "oism" {
               description "Optimized inter subnet multicast mode";
             }
             enum "enhanced-oism" {
               description "Enhanced OISM to support asymmetric bridge domains";
             }
           }
         }
         leaf smet-forwarding {
           description "Enable SMET forwarding";
           type empty;
         }
         leaf smet-nexthop-limit {
           description "Flood traffic to all egress when count goes above limit";
           type union {
             type string {
               pattern "<.*>|$.*";
             }
             type uint32 {
               range "10000 .. 40000";
             }
           }
         }
       }
     }
     container load-balance {
       description "Configure load-balancing attributes on the forwarding path";
       uses apply-advanced;
       container indexed-load-balance {
         presence "enable indexed-load-balance";
         description "Use indexed permuted next hop lists for unilist and aggregate next hops";
         uses apply-advanced;
       }
       container per-flow {
         uses apply-advanced;
       }
       container per-prefix {
         presence "enable per-prefix";
         uses apply-advanced;
         leaf hash-seed {
           description "Specifies per-router input value for per-prefix load-balancing hash function";
           default "0";
           type union {
             type string {
               pattern "<.*>|$.*";
             }
             type uint16 {
               range "0 .. 65534";
             }
           }
         }
       }
     }
     container hash-key {
       description "Select data used in the hash key";
       uses junos_hash_key;
     }
     container local-bias {
       presence "enable local-bias";
       description "Turn on local bias functionality";
       uses apply-advanced;
       leaf disable {
         description "Disable local-bias";
         type empty;
       }
     }
     container enhanced-hash-key {
       description "Select data used in the hash key for Enhanced IP Forwarding Engines";
       uses apply-advanced;
       leaf use-trunk-max-links {
         description "Use 8 links in trunk programming instead of actual links";
         type empty;
       }
       container hash-seed {
         presence "enable hash-seed";
         description "Hash seed";
         uses apply-advanced;
       }
       container mpls {
         description "Configure mpls fields";
         uses apply-advanced;
         leaf no-incoming-port {
           description "Exclude incoming port from the hash key";
           type empty;
         }
       }
       container services-loadbalancing {
         description "Select key to load balance across service PICs";
         uses apply-advanced;
         container family {
           description "Protocol family";
           container inet {
             description "IPv4 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
             }
           }
           container inet6 {
             description "IPv6 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
               leaf src-prefix-len {
                 description "Enhanced hash key inet6 source prefix length";
                 default "127";
                 units "bits";
                 type union {
                   type string {
                     pattern "<.*>|$.*";
                   }
                   type uint32 {
                     range "56 .. 127";
                   }
                 }
               }
             }
           }
         }
       }
       container family {
         description "Protocol family";
         container inet {
           description "IPv4 protocol family";
           uses apply-advanced;
           leaf incoming-interface-index {
             description "Include incoming interface index in the hash key";
             type empty;
           }
           leaf no-destination-port {
             description "Omit IP destination port in the hash key";
             type empty;
           }
           leaf no-source-port {
             description "Omit IP source port in the hash key";
             type empty;
           }
           leaf type-of-service {
             description "Include TOS byte in the hash key";
             type empty;
           }
           leaf gtp-tunnel-endpoint-identifier {
             description "Include TEID in the hash key for GTP-U packets";
             type empty;
           }
           leaf l2tp-tunnel-session-identifier {
             description "Include TID SID in the hash key for L2TP packets";
             type empty;
           }
         }
         container inet6 {
           description "IPv6 protocol family";
           uses apply-advanced;
           leaf incoming-interface-index {
             description "Include incoming interface index in the hash key";
             type empty;
           }
           leaf traffic-class {
             description "Include Traffic Class byte in the hash key";
             type empty;
           }
           leaf no-destination-port {
             description "Omit IP destination port in the hash key";
             type empty;
           }
           leaf no-source-port {
             description "Omit IP source port in the hash key";
             type empty;
           }
           leaf gtp-tunnel-endpoint-identifier {
             description "Include TEID in the hash key for GTP-U packets";
             type empty;
           }
           leaf no-flow-label {
             description "Omit Flow label in the hash key";
             type empty;
           }
           leaf type-of-service {
             description "Include TOS byte in the hash key";
             status deprecated;
             type empty;
           }
         }
         container mpls {
           description "MPLS protocol family";
           uses apply-advanced;
           leaf label-1-exp {
             description "Include EXP of first MPLS label from the hash key";
             type empty;
           }
           leaf incoming-interface-index {
             description "Include incoming interface index in the hash key";
             type empty;
           }
           choice pseudowire_option {
             case case_1 {
               leaf no-ether-pseudowire {
                 description "Omit IP payload over ethernet PW from the hash-key";
                 type empty;
               }
             }
             case case_2 {
             }
           }
           leaf no-payload {
             description "Omit MPLS payload data from the hash key";
             type empty;
           }
         }
         container multiservice {
           description "Multiservice protocol (bridged/CCC/VPLS) family";
           uses apply-advanced;
           leaf incoming-interface-index {
             description "Include incoming interface index in hash key";
             type empty;
           }
           leaf outer-priority {
             description "Include Outer 802.1 Priority bits in the hash key";
             type empty;
           }
           leaf no-payload {
             description "Omit payload data from the hash key";
             type empty;
           }
           leaf no-mac-addresses {
             description "Omit source and destination MAC addresses from the hash key";
             type empty;
           }
         }
       }
       container hash-function {
         description "Configure hash functions";
         uses apply-advanced;
         choice instance {
           case case_1 {
           }
           case case_2 {
           }
           case case_3 {
           }
           case case_4 {
           }
           case case_5 {
           }
           case case_6 {
           }
           case case_7 {
           }
           case case_8 {
           }
           case case_9 {
             container xor {
               presence "enable xor";
               description "XOR based hashing";
               uses apply-advanced;
               leaf no-L3-L4-headers {
                 description "Exclude source IP, dest IP, source L4 port, dest L4 port addresses from hashing";
                 type empty;
               }
               leaf no-L4-ports {
                 description "Exclude source L4 port and dest L4 port addresses from hashing";
                 type empty;
               }
               leaf mac-addresses {
                 description "Include source and destination MAC addresses in IPv4/IPv6 packet hashing";
                 type empty;
               }
               leaf no-mpls-hash {
                 description "Exclude MPLS information from hashing";
                 type empty;
               }
               leaf no-ipv4-source-address {
                 description "Exclude source IPv4 address from hashing";
                 type empty;
               }
               leaf no-ipv4-destination-address {
                 description "Exclude dest IPv4 address from hashing";
                 type empty;
               }
               leaf no-ipv6-source-address {
                 description "Exclude source IPv6 address from hashing";
                 type empty;
               }
               leaf no-ipv6-destination-address {
                 description "Exclude dest IPv6 address from hashing";
                 type empty;
               }
               leaf no-ip6-flow-label {
                 description "Exclude IPv6 flow label from hashing";
                 type empty;
               }
               leaf en-ip-over-mpls {
                 description "Enable parsing of IP in MPLS packets";
                 type empty;
               }
               leaf no-mpls-label0 {
                 description "Exclude MPLS Label 0 from hashing";
                 type empty;
               }
               leaf no-mpls-label1 {
                 description "Exclude MPLS Label 1 from hashing";
                 type empty;
               }
               leaf no-source-mac-address {
                 description "Exclude source MAC address from hashing";
                 type empty;
               }
               leaf no-destination-mac-address {
                 description "Exclude dest MAC address from hashing";
                 type empty;
               }
               leaf no-l4-source-port {
                 description "Exclude l4 source port from the hash key";
                 type empty;
               }
               leaf no-l4-destination-port {
                 description "Exclude l4 dest port from the hash key";
                 type empty;
               }
             }
           }
           case case_10 {
             leaf ingress-port {
               description "Ingress port based hashing";
               type empty;
             }
           }
           case case_11 {
             container crc6 {
               presence "enable crc6";
               description "CRC6 based hashing";
               uses apply-advanced;
               leaf crc6-seed {
                 description "CRC6 seed value";
                 type union {
                   type string {
                     pattern "<.*>|$.*";
                   }
                   type uint32 {
                     range "0 .. 63";
                   }
                 }
               }
               leaf en-ip-over-mpls {
                 description "Enable parsing of IP in MPLS packets";
                 type empty;
               }
               leaf no-source-mac-address {
                 description "Exclude source MAC address from hashing";
                 type empty;
               }
               leaf no-destination-mac-address {
                 description "Exclude dest MAC address from hashing";
                 type empty;
               }
               leaf no-mpls-label0 {
                 description "Exclude MPLS Label 0 from hashing";
                 type empty;
               }
               leaf no-mpls-label1 {
                 description "Exclude MPLS Label 1 from hashing";
                 type empty;
               }
               leaf no-l4-source-port {
                 description "Exclude l4 source port from the hash key";
                 type empty;
               }
               leaf no-l4-destination-port {
                 description "Exclude l4 dest port from the hash key";
                 type empty;
               }
               leaf no-ip-source-address {
                 description "Exclude source IPv4/IPv6 address from hashing";
                 type empty;
               }
               leaf no-ip-destination-address {
                 description "Exclude dest IPv4/IPv6 address from hashing";
                 type empty;
               }
               leaf no-ip6-flow-label {
                 description "Exclude IPv6 flow label from hashing";
                 type empty;
               }
             }
           }
           case case_12 {
             container crc16 {
               presence "enable crc16";
               description "CRC16 based hashing";
               uses apply-advanced;
               leaf crc16-seed {
                 description "CRC16 seed value";
                 type union {
                   type string {
                     pattern "<.*>|$.*";
                   }
                   type uint32 {
                     range "0 .. 65535";
                   }
                 }
               }
               leaf en-ip-over-mpls {
                 description "Enable parsing of IP in MPLS packets";
                 type empty;
               }
               leaf no-source-mac-address {
                 description "Exclude source MAC address from hashing";
                 type empty;
               }
               leaf no-destination-mac-address {
                 description "Exclude dest MAC address from hashing";
                 type empty;
               }
               leaf no-mpls-label0 {
                 description "Exclude MPLS Label 0 from hashing";
                 type empty;
               }
               leaf no-mpls-label1 {
                 description "Exclude MPLS Label 1 from hashing";
                 type empty;
               }
               leaf no-l4-source-port {
                 description "Exclude l4 source port from the hash key";
                 type empty;
               }
               leaf no-l4-destination-port {
                 description "Exclude l4 dest port from the hash key";
                 type empty;
               }
               leaf no-ip-source-address {
                 description "Exclude source IPv4/IPv6 address from hashing";
                 type empty;
               }
               leaf no-ip-destination-address {
                 description "Exclude dest IPv4/IPv6 address from hashing";
                 type empty;
               }
               leaf no-ip6-flow-label {
                 description "Exclude IPv6 flow label from hashing";
                 type empty;
               }
             }
           }
         }
       }
       container vxlan {
         description "Vxlan traffic";
         uses apply-advanced;
         leaf no-inner-payload {
           description "To enable load-balancing on Vxlan traffic based on outer IP/UDP header";
           type empty;
         }
       }
       list conditional-match {
         key name;
         ordered-by user;
         description "Configures a conditional match";
         leaf name {
           description "Name identifier";
           type string;
         }
         uses apply-advanced;
         container offset1 {
           presence "enable offset1";
           description "Configure offset 1";
           uses apply-advanced;
           leaf base-offset1 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
             mandatory true;
           }
           leaf offset1-value {
             description "Offset of the data to be extracted from the base offset. Only even number";
             type union {
               type string {
                 pattern "<.*>|$.*";
               }
               type uint8 {
                 range "0 .. 126";
               }
             }
             mandatory true;
           }
           leaf matchdata1 {
             description "Data to be matched";
             type string {
               length 4;
             }
             mandatory true;
           }
           leaf matchdata1-mask {
             description "Matchdata mask";
             type string {
               length 4;
             }
             mandatory true;
           }
         }
         container offset2 {
           presence "enable offset2";
           description "Configure offset 2";
           uses apply-advanced;
           leaf base-offset2 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
             mandatory true;
           }
           leaf offset2-value {
             description "Offset of the data to be extracted from the base offset. Only even number";
             type union {
               type string {
                 pattern "<.*>|$.*";
               }
               type uint8 {
                 range "0 .. 126";
               }
             }
             mandatory true;
           }
           leaf matchdata2 {
             description "Data to be matched";
             type string {
               length 4;
             }
             mandatory true;
           }
           leaf matchdata2-mask {
             description "Matchdata mask";
             type string {
               length 4;
             }
             mandatory true;
           }
         }
         container offset3 {
           presence "enable offset3";
           description "Configure offset 3";
           uses apply-advanced;
           leaf base-offset3 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
             mandatory true;
           }
           leaf offset3-value {
             description "Offset of the data to be extracted from the base offset. Only even number";
             type union {
               type string {
                 pattern "<.*>|$.*";
               }
               type uint8 {
                 range "0 .. 126";
               }
             }
             mandatory true;
           }
           leaf matchdata3 {
             description "Data to be matched";
             type string {
               length 4;
             }
             mandatory true;
           }
           leaf matchdata3-mask {
             description "Matchdata mask";
             type string {
               length 4;
             }
             mandatory true;
           }
         }
         container offset4 {
           presence "enable offset4";
           description "Configure offset 4";
           uses apply-advanced;
           leaf base-offset4 {
             description "Configure base-offset";
             type enumeration {
               enum "start-of-L2Header" {
                 description "Offset will be extracted from start of L2 header";
               }
               enum "start-of-L3-OuterHeader" {
                 description "Offset will be extracted from start of outer L3 header";
               }
               enum "start-of-L3-InnerHeader" {
                 description "Offset will be extracted from start of inner L3 header";
               }
               enum "start-of-L4-Header" {
                 description "Offset will be extracted from start of L4 header";
               }
             }
             mandatory true;
           }
           leaf offset4-value {
             description "Offset of the data to be extracted from the base offset. Only even number";
             type union {
               type string {
                 pattern "<.*>|$.*";
               }
               type uint8 {
                 range "0 .. 126";
               }
             }
             mandatory true;
           }
           leaf matchdata4 {
             description "Data to be matched";
             type string {
               length 4;
             }
             mandatory true;
           }
           leaf matchdata4-mask {
             description "Matchdata mask";
             type string {
               length 4;
             }
             mandatory true;
           }
         }
       }
       list flex-hashing {
         key name;
         ordered-by user;
         description "Set flex hashing";
         leaf name {
           description "Name identifier";
           type string;
         }
         uses apply-advanced;
         container ethtype {
           presence "enable ethtype";
           description "Configure ether-type of packet";
           uses apply-advanced;
           container inet {
             description "Enable flex-hashing on ipv4";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                   mandatory true;
                 }
                 leaf offset1-value {
                   description "Offset of the data to be extracted from the base offset. Only even number";
                   type union {
                     type string {
                       pattern "<.*>|$.*";
                     }
                     type uint8 {
                       range "0 .. 126";
                     }
                   }
                   mandatory true;
                 }
                 leaf offset1-mask {
                   description "Mask for the hash data extracted. 2 byte mask";
                   type string {
                     length 4;
                   }
                   mandatory true;
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                     mandatory true;
                   }
                   leaf offset2-value {
                     description "Offset of the data to be extracted from the base offset. Only even number";
                     type union {
                       type string {
                         pattern "<.*>|$.*";
                       }
                       type uint8 {
                         range "0 .. 126";
                       }
                     }
                     mandatory true;
                   }
                   leaf offset2-mask {
                     description "Mask for the hash data extracted. 2 byte mask";
                     type string {
                       length 4;
                     }
                     mandatory true;
                   }
                 }
               }
             }
           }
           container inet6 {
             description "Enable flex-hashing on ipv6";
             uses apply-advanced;
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                   mandatory true;
                 }
                 leaf offset1-value {
                   description "Offset of the data to be extracted from the base offset. Only even number";
                   type union {
                     type string {
                       pattern "<.*>|$.*";
                     }
                     type uint8 {
                       range "0 .. 126";
                     }
                   }
                   mandatory true;
                 }
                 leaf offset1-mask {
                   description "Mask for the hash data extracted. 2 byte mask";
                   type string {
                     length 4;
                   }
                   mandatory true;
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                     mandatory true;
                   }
                   leaf offset2-value {
                     description "Offset of the data to be extracted from the base offset. Only even number";
                     type union {
                       type string {
                         pattern "<.*>|$.*";
                       }
                       type uint8 {
                         range "0 .. 126";
                       }
                     }
                     mandatory true;
                   }
                   leaf offset2-mask {
                     description "Mask for the hash data extracted. 2 byte mask";
                     type string {
                       length 4;
                     }
                     mandatory true;
                   }
                 }
               }
             }
           }
           container mpls {
             description "Configure number of MPLS labels";
             uses apply-advanced;
             leaf num-labels {
               description "Configure number of MPLS labels";
               type union {
                 type string {
                   pattern "<.*>|$.*";
                 }
                 type uint8 {
                   range "1 .. 5";
                 }
               }
             }
             leaf interface {
               description "Incoming interface name. This is optional parameter";
               type union {
                 type jt:interface-name;
                 type string {
                   pattern "<.*>|$.*";
                 }
               }
             }
             leaf conditional-match {
               description "Conditional match to be matched in the packet";
               type string;
             }
             container hash-offset {
               description "Configure the offsets for hashing";
               uses apply-advanced;
               container offset1 {
                 presence "enable offset1";
                 description "Configure offset 1 value";
                 uses apply-advanced;
                 leaf base-offset1 {
                   description "Configure base-offset";
                   type enumeration {
                     enum "start-of-L2Header" {
                       description "Offset will be extracted from start of L2 header";
                     }
                     enum "start-of-L3-OuterHeader" {
                       description "Offset will be extracted from start of outer L3 header";
                     }
                     enum "start-of-L3-InnerHeader" {
                       description "Offset will be extracted from start of inner L3 header";
                     }
                     enum "start-of-L4-Header" {
                       description "Offset will be extracted from start of L4 header";
                     }
                   }
                   mandatory true;
                 }
                 leaf offset1-value {
                   description "Offset of the data to be extracted from the base offset. Only even number";
                   type union {
                     type string {
                       pattern "<.*>|$.*";
                     }
                     type uint8 {
                       range "0 .. 126";
                     }
                   }
                   mandatory true;
                 }
                 leaf offset1-mask {
                   description "Mask for the hash data extracted. 2 byte mask";
                   type string {
                     length 4;
                   }
                   mandatory true;
                 }
                 container offset2 {
                   presence "enable offset2";
                   description "Configure offset 2 value";
                   uses apply-advanced;
                   leaf base-offset2 {
                     description "Configure base-offset";
                     type enumeration {
                       enum "start-of-L2Header" {
                         description "Offset will be extracted from start of L2 header";
                       }
                       enum "start-of-L3-OuterHeader" {
                         description "Offset will be extracted from start of outer L3 header";
                       }
                       enum "start-of-L3-InnerHeader" {
                         description "Offset will be extracted from start of inner L3 header";
                       }
                       enum "start-of-L4-Header" {
                         description "Offset will be extracted from start of L4 header";
                       }
                     }
                     mandatory true;
                   }
                   leaf offset2-value {
                     description "Offset of the data to be extracted from the base offset. Only even number";
                     type union {
                       type string {
                         pattern "<.*>|$.*";
                       }
                       type uint8 {
                         range "0 .. 126";
                       }
                     }
                     mandatory true;
                   }
                   leaf offset2-mask {
                     description "Mask for the hash data extracted. 2 byte mask";
                     type string {
                       length 4;
                     }
                     mandatory true;
                   }
                 }
               }
             }
           }
         }
       }
     }
     container next-hop {
       description "Next hop throttle";
       uses apply-advanced;
     }
     container sflow {
       description "Sflow related";
       uses apply-advanced;
       container egress-multicast {
         description "Sflow for egress multicast";
         uses apply-advanced;
         leaf max-replication-rate {
           description "To configure max replication rate";
           type union {
             type string {
               pattern "<.*>|$.*";
             }
             type uint32;
           }
         }
       }
       container flow-sample {
         description "Flow sample input";
         uses apply-advanced;
       }
     }
     container multicast {
       description "Multicast resolve and mismatch rate";
       uses apply-advanced;
       leaf resolve-rate {
         description "Multicast resolve rate";
         units "per second";
         type union {
           type string {
             pattern "<.*>|$.*";
           }
           type uint32 {
             range "100 .. 1000";
           }
         }
       }
       leaf mismatch-rate {
         description "Multicast interface mismatch rate";
         units "per second";
         type union {
           type string {
             pattern "<.*>|$.*";
           }
           type uint32 {
             range "50 .. 1000";
           }
         }
       }
     }
     container packet-capture-telemetry {
       description "Packet capture telemetry options";
       uses apply-advanced;
       container egress {
         description "Egress options";
         uses packet-capture-egress-intf-type;
       }
     }
     container explicit-null-cos {
       presence "enable explicit-null-cos";
       description "Configure to use MPLS explicit null exp for COS classification";
       uses apply-advanced;
       leaf inet {
         description "Include family inet";
         type empty;
       }
       leaf inet6 {
         description "Include family inet6";
         type empty;
       }
     }
     container helpers {
       description "Port forwarding configuration";
       uses apply-advanced;
       container traceoptions {
         description "Trace options for helper";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of UDP forwarding helper process on which to enable debugging output";
           leaf name {
             type enumeration {
               enum "trace" {
                 description "Trace tracing code";
               }
               enum "address" {
                 description "Trace address management code";
               }
               enum "main" {
                 description "Trace main loop code";
               }
               enum "config" {
                 description "Trace configuration code";
               }
               enum "ifdb" {
                 description "Trace interface database code";
               }
               enum "io" {
                 description "Trace I/O code";
               }
               enum "rtsock" {
                 description "Trace routing socket code";
               }
               enum "ui" {
                 description "Trace user interface code";
               }
               enum "util" {
                 description "Trace miscellaneous utility code";
               }
               enum "gencfg" {
                 description "Trace fud gencfg message";
               }
               enum "domain" {
                 description "Trace DNS service-specific code";
               }
               enum "tftp" {
                 description "Trace TFTP service-specific code";
               }
               enum "bootp" {
                 description "Trace BOOTP/DHCP service-specific code";
               }
               enum "port" {
                 description "Trace arbitrary protocol code";
               }
               enum "if-rtsdb" {
                 description "Trace interface hierarchy rtsdb";
               }
               enum "all" {
                 description "Trace all areas of code";
               }
             }
           }
         }
       }
       container rtsdb-client-traceoptions {
         presence "enable rtsdb-client-traceoptions";
         description "SHM rtsock database client library trace options";
         status deprecated;
         uses apply-advanced;
         container if-rtsdb {
           presence "enable if-rtsdb";
           description "Trace interface hierarchy rtsdb";
           uses apply-advanced;
           list flag {
             key name;
             ordered-by user;
             description "Tracing parameters";
             leaf name {
               type enumeration {
                 enum "init" {
                   description "Trace initialization";
                 }
                 enum "routing-socket" {
                   description "Trace routing socket messages";
                 }
                 enum "map" {
                   description "Trace shared memory mapping";
                 }
                 enum "all" {
                   description "Trace all";
                 }
               }
             }
             leaf disable {
               description "Disable this trace flag";
               type empty;
             }
           }
         }
       }
       container domain {
         description "Incoming DNS request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                   mandatory true;
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming DNS request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                     mandatory true;
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container tftp {
         description "Incoming TFTP request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                   mandatory true;
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming TFTP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                     mandatory true;
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container bootp {
         description "Incoming BOOTP/DHCP request forwarding configuration";
         uses apply-advanced;
         leaf relay-agent-option {
           description "Use DHCP Relay Agent option in relayed BOOTP/DHCP messages";
           type empty;
         }
         container dhcp-option82 {
           description "Configure DHCP option 82";
           presence "enable dhcp-option82";
           uses dhcp-option82-type;
         }
         leaf description {
           description "Text description of servers";
           type string;
         }
         list server {
           key name;
           ordered-by user;
           description "Server information";
           leaf name {
             description "Name or address of servers to which to forward";
             type jt:ipv4addr;
           }
           uses apply-advanced;
           list logical-system {
             key name;
             ordered-by user;
             description "Logical system of server to which to forward";
             leaf name {
               description "Name of logical system";
               type string {
               }
               mandatory true;
             }
             leaf-list routing-instance {
               ordered-by user;
               description "Routing instance of server to which to forward";
               type string;
             }
           }
           leaf-list routing-instance {
             ordered-by user;
             description "Routing instance of server to which to forward";
             type string;
           }
         }
         leaf maximum-hop-count {
           description "Maximum number of hops per packet";
           default "4";
           type union {
             type string {
               pattern "<.*>|$.*";
             }
             type uint32 {
               range "1 .. 16";
             }
           }
         }
         leaf minimum-wait-time {
           description "Minimum number of seconds before requests are forwarded";
           default "0";
           type union {
             type string {
               pattern "<.*>|$.*";
             }
             type uint32 {
               range "0 .. 30000";
             }
           }
         }
         leaf client-response-ttl {
           description "IP time-to-live value to set in responses to client";
           type union {
             type string {
               pattern "<.*>|$.*";
             }
             type uint32 {
               range "1 .. 255";
             }
           }
         }
         leaf source-address-giaddr {
           description "Use GIADDR as the source IP address for relayed packets";
           type empty;
         }
         leaf apply-secondary-as-giaddr {
           description "Enable DHCP relay to use secondary gateway ip on all interfaces";
           type empty;
         }
         list interface {
           key name;
           ordered-by user;
           description "Incoming BOOTP/DHCP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of servers";
             type string;
           }
           list server {
             key name;
             ordered-by user;
             description "Server information";
             leaf name {
               description "Name or address of servers to which to forward";
               type jt:ipv4addr;
             }
             uses apply-advanced;
             list logical-system {
               key name;
               ordered-by user;
               description "Logical system of server to which to forward";
               leaf name {
                 description "Name of logical system";
                 type string {
                 }
                 mandatory true;
               }
               leaf-list routing-instance {
                 ordered-by user;
                 description "Routing instance of server to which to forward";
                 type string;
               }
             }
             leaf-list routing-instance {
               ordered-by user;
               description "Routing instance of server to which to forward";
               type string;
             }
           }
           leaf maximum-hop-count {
             description "Maximum number of hops per packet";
             default "4";
             type union {
               type string {
                 pattern "<.*>|$.*";
               }
               type uint32 {
                 range "1 .. 16";
               }
             }
           }
           leaf minimum-wait-time {
             description "Minimum number of seconds before requests are forwarded";
             default "0";
             type union {
               type string {
                 pattern "<.*>|$.*";
               }
               type uint32 {
                 range "0 .. 30000";
               }
             }
           }
           leaf client-response-ttl {
             description "IP time-to-live value to set in responses to client";
             type union {
               type string {
                 pattern "<.*>|$.*";
               }
               type uint32 {
                 range "1 .. 255";
               }
             }
           }
           leaf source-address-giaddr {
             description "Use GIADDR as the source IP address for relayed packets";
             type empty;
           }
           container dhcp-option82 {
             description "Configure DHCP option 82";
             presence "enable dhcp-option82";
             uses dhcp-option82-type;
           }
           leaf apply-secondary-as-giaddr {
             description "Enable DHCP relay to use secondary gateway ip on this interface";
             type empty;
           }
         }
       }
       list port {
         key name;
         ordered-by user;
         description "Incoming arbitrary protocol request forwarding configuration";
         leaf name {
           description "Port number of the protocol to listen";
           type union {
             type string {
               pattern "<.*>|$.*";
             }
             type uint32 {
               range "1 .. 65535";
             }
           }
         }
         uses apply-advanced;
         leaf description {
           description "Text description of server";
           type string;
         }
         list server {
           key name;
           ordered-by user;
           description "Server information";
           leaf name {
             description "Name or address of server to which to forward";
             type jt:ipv4addr;
           }
           uses apply-advanced;
           choice instance {
             case case_1 {
               container logical-system {
                 description "Logical system of server to which to forward";
                 leaf logical-system-name {
                   description "Name of logical system";
                   type string {
                   }
                   mandatory true;
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           list server {
             key name;
             ordered-by user;
             description "Server information";
             leaf name {
               description "Name or address of server to which to forward";
               type jt:ipv4addr;
             }
             uses apply-advanced;
             choice instance {
               case case_1 {
                 container logical-system {
                   description "Logical system of server to which to forward";
                   leaf logical-system-name {
                     description "Name of logical system";
                     type string {
                     }
                     mandatory true;
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
     }
     container family {
       description "Protocol family";
       container inet {
         description "IPv4 parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container inet6 {
         description "IPv6 parameters";
         uses apply-advanced;
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv6 route accounting";
           type empty;
         }
         leaf source-checking {
           description "Discard IPv6 packet when source address type is unspecified, loopback, multicast or link-local ";
           type empty;
         }
       }
       container vpls {
         description "VPLS parameters";
         uses apply-advanced;
         container filter {
           description "Filtering for VPLS DMAC forwarding table";
           uses apply-advanced;
           leaf input {
             description "Name of input filter to apply for forwarded packets";
             type string;
           }
         }
         container flood {
           description "Filtering for VPLS flood table";
           uses apply-advanced;
           leaf input {
             description "Name of input filter to apply for VPLS flood packets";
             type string;
           }
         }
       }
       container evpn {
         description "EVPN parameters";
         uses apply-advanced;
         container filter {
           description "Filtering for EVPN DMAC forwarding table";
           uses apply-advanced;
           leaf input {
             description "Name of input filter to apply for forwarded packets";
             type string;
           }
         }
         container flood {
           description "Filtering for EVPN flood table";
           uses apply-advanced;
           leaf input {
             description "Name of input filter to apply for EVPN flood packets";
             type string;
           }
         }
       }
     }
     container dhcp-relay {
       description "Dynamic Host Configuration Protocol relay configuration";
       uses jdhcp-relay-type;
     }
     choice load-balance-label-capability-choice {
       leaf load-balance-label-capability {
         description "Load balance label capability";
         type empty;
       }
       leaf no-load-balance-label-capability {
         description "Don't load balance label capability";
         type empty;
       }
     }
     list ip-options-protocol-queue {
       key name;
       ordered-by user;
       description "IP Options protocol logical queue parameters";
       leaf name {
         description "Protocol name";
         type string;
       }
       uses apply-advanced;
       leaf protocol-id {
         description "Protocol Identifier";
         type union {
           type string {
             pattern "<.*>|$.*";
           }
           type uint8 {
             range "1 .. 254";
           }
         }
         mandatory true;
       }
       leaf queue-depth {
         description "Size of the protocol logical options queue";
         type union {
           type string {
             pattern "<.*>|$.*";
           }
           type uint32 {
             range "1 .. 807";
           }
         }
         mandatory true;
       }
     }
     leaf allow-traffic-in-detached-ae {
       description "To accept the traffic on child links when ae is in detached";
       type empty;
     }
     leaf vxlan-bum-bit-disable {
       description "Disable setting BUM traffic bit in VxLAN header";
       type empty;
     }
     leaf lag-heap-optimization {
       description "Improve heap memory utilization with LAG interfaces. This will restart PFE.";
       type empty;
     }
     leaf no-host-as-lpm {
       description "Block spilling into LPM table if host table is full. This will restart PFE";
       type empty;
     }
     leaf port-mac-in-tcam {
       description "Enable Port+mac knob in my_station_tcam. This will restart PFE";
       type empty;
     }
     leaf vxlan-flexflow {
       description "Enable VxLAN flexflow. This will restart PFE";
       type empty;
     }
     leaf inline-bfd-sw-based {
       description "Enable inline BFD as SW based. This will restart PFE";
       type empty;
     }
     container access-security {
       description "Access security configuration";
       uses jdhcp-access-security-type;
     }
     container vxlan-routing {
       description "VXLAN Routing forwarding options";
       uses apply-advanced;
       leaf next-hop {
         description "Next-hop. Must be multiple of 4096. This will restart PFE";
         type union {
           type string {
             pattern "<.*>|$.*";
           }
           type uint32;
         }
       }
       leaf interface-num {
         description "Interface. Must be multiple of 2048. This will restart PFE";
         type union {
           type string {
             pattern "<.*>|$.*";
           }
           type uint32;
         }
       }
       leaf overlay-ecmp {
         description "Enable overlay ecmp for vxlan L3. This will restart PFE";
         type empty;
       }
       leaf loopback-port {
         description "AE loopback interface used for VXLAN routing. This will restart PFE";
         type string;
       }
     }
   }
   grouping dhcp-option82-type {
     uses apply-advanced;
     leaf disable {
       description "Disable DHCP option 82 on this VLAN";
       type empty;
     }
     container circuit-id {
       presence "enable circuit-id";
       description "Configure DHCP option 82 circuit id";
       uses apply-advanced;
       leaf prefix {
         description "Configure DHCP option 82 circuit id prefix";
         type enumeration {
           enum "hostname" {
             description "Set hostname as the prefix";
           }
         }
       }
       leaf use-interface-description {
         description "Use interface description instead of name";
         type empty;
       }
       leaf use-vlan-id {
         description "Use VLAN id instead of name";
         type empty;
       }
     }
     container remote-id {
       presence "enable remote-id";
       description "Configure DHCP option 82 remote id";
       uses apply-advanced;
       leaf prefix {
         description "Configure DHCP option 82 remote id prefix";
         type enumeration {
           enum "none" {
             description "Set no prefix";
           }
           enum "hostname" {
             description "Set hostname as the prefix";
           }
           enum "mac" {
             description "Set chassis MAC as the prefix";
           }
         }
       }
       leaf use-interface-description {
         description "Use interface description instead of name";
         type empty;
       }
       leaf use-string {
         description "Use raw string instead of the default remote id";
         type string;
       }
     }
     container vendor-id {
       presence "enable vendor-id";
       description "Configure DHCP option 82 vendor id";
       uses apply-advanced;
       leaf use-string {
         description "Use raw string instead of the default vendor id";
         type string;
       }
     }
   }
   grouping jdhcp-access-security-type {
     description "Access security configuration";
     uses apply-advanced;
     container router-advertisement-guard {
       presence "enable router-advertisement-guard";
       description "Router Advertisement Guard Configuration";
       uses apply-advanced;
       list policy {
         key name;
         ordered-by user;
         description "Router Advertisement Guard policy";
         leaf name {
           description "Router Advertisement Guard policy name";
           type string {
             length "1 .. 64";
           }
         }
         uses apply-advanced;
         container discard {
           description "Discard parameters";
           uses apply-advanced;
           leaf source-ip-address-list {
             description "IPv6 Source address list name";
             type string;
           }
           leaf source-mac-address-list {
             description "Source mac address list name";
             type string;
           }
           leaf prefix-list-name {
             description "Prefix-list Name";
             type string;
           }
         }
         container accept {
           description "Accept parameters";
           uses apply-advanced;
           container match-list {
             description "List of parameters to check";
             uses apply-advanced;
             leaf source-ip-address-list {
               description "IPv6 Source address list name";
               type string;
             }
             leaf source-mac-address-list {
               description "Source mac address list name";
               type string;
             }
             leaf prefix-list-name {
               description "Prefix-list Name";
               type string;
             }
             leaf match-criteria {
               description "Match Criteria";
               type enumeration {
                 enum "match-all" {
                   description "A match from every list";
                 }
                 enum "match-any" {
                   description "A match from any list";
                 }
               }
             }
           }
           container match-options {
             presence "enable match-options";
             description "List of Options to check";
             uses apply-advanced;
             container hop-limit {
               description "Hop limit";
               uses apply-advanced;
               leaf maximum {
                 description "Maximum hop limit";
                 type union {
                   type string {
                     pattern "<.*>|$.*";
                   }
                   type uint32 {
                     range "1 .. 255";
                   }
                 }
               }
               leaf minimum {
                 description "Minimum hop limit";
                 type union {
                   type string {
                     pattern "<.*>|$.*";
                   }
                   type uint32 {
                     range "1 .. 255";
                   }
                 }
               }
             }
             container route-preference {
               description "Accept route preference";
               uses apply-advanced;
               leaf maximum {
                 description "Maximum route preference";
                 type enumeration {
                   enum "low" {
                     description "Route preference low";
                   }
                   enum "medium" {
                     description "Route preference medium";
                   }
                   enum "high" {
                     description "Route preference high";
                   }
                 }
                 mandatory true;
               }
             }
             leaf managed-config-flag {
               description "Check Managed config flag";
               type empty;
             }
             leaf other-config-flag {
               description "Check Other config flag";
               type empty;
             }
           }
         }
       }
       container interface {
         description "RA Guard config on Interface";
         uses apply-advanced;
         list intf-config {
           key name;
           description "Interface Configuration";
           uses interface-policy;
         }
       }
       container vlans {
         description "RA Guard config on Vlan";
         uses apply-advanced;
         list vlan-config {
           key name;
           description "Virtual LAN Configuration";
           uses vlan-policy;
         }
       }
     }
   }
   grouping interface-policy {
     description "Interface Name";
     leaf name {
       description "Interface Name";
       type union {
         type jt:interface-name;
         type string {
           pattern "<.*>|$.*";
         }
       }
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       uses apply-advanced;
       choice mark-intf-type {
         case case_1 {
           leaf trusted {
             description "Mark interface trusted";
             type empty;
           }
         }
         case case_2 {
           leaf block {
             description "Block router-advertisement";
             type empty;
           }
         }
       }
     }
   }
   grouping jdhcp-relay-type {
     description "Dynamic Host Configuration Protocol relay configuration";
     uses apply-advanced;
     container traceoptions {
       description "DHCP relay trace options";
       status deprecated;
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses override-type;
     }
     container relay-option {
       description "DHCP option processing";
       presence "enable relay-option";
       uses dhcp-generic-v4-option;
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       uses relay-option-60-type-top;
     }
     container relay-option-82 {
       description "DHCP option-82 processing";
       presence "enable relay-option-82";
       uses relay-option-82-type;
     }
     container forward-only {
       description "Forward DHCP packets without creating binding";
       presence "enable forward-only";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       uses server-group-type;
     }
     container active-server-group {
       description "Name of DHCP server group";
       uses dhcpv4-gbl-active-sg-type;
     }
     container route-suppression {
       description "Suppress access-internal and/or destination route addition";
       uses dhcp-route-suppression-type;
     }
     list group {
       key name;
       description "Define a DHCP group";
       uses dhcp-group;
     }
     list dual-stack-group {
       key name;
       description "Define a DHCP dual stack group";
       uses dhcp-dual-stack-group;
     }
     leaf no-snoop {
       description "Do not snoop DHCP packets";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       uses relay-leasequery-type;
     }
     container bulk-leasequery {
       description "DHCP bulk leasequery configuration";
       presence "enable bulk-leasequery";
       uses relay-bulk-leasequery-v4-type;
     }
     container active-leasequery {
       description "DHCPv4 active leasequery configuration";
       presence "enable active-leasequery";
       uses active-leasequery-v4-type;
     }
     container remote-id-mismatch {
       description "DHCP client remote-id mismatch";
       presence "enable remote-id-mismatch";
       uses dhcp-remote-id-mismatch-type;
     }
   }
   grouping active-leasequery-v4-type {
     description "Configure active leasequery";
     uses apply-advanced;
     leaf topology-discover {
       description "Topology discovery";
       type empty;
     }
     list peer-address {
       key name;
       description "Server ip address";
       leaf name {
         description "Peer ip address";
         type jt:ipaddr;
       }
       uses apply-advanced;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-dual-stack-group {
     description "DHCP dual stack groups";
     leaf name {
       description "Dual stack group name";
       type string {
         length "1 .. 64";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       uses dhcp-generic-v4-option-type;
     }
     container option-77 {
       description "Add option 77 processing";
       presence "enable option-77";
       uses dhcp-generic-v4-option-type;
     }
     list option-order {
       key name;
       ordered-by user;
       description "Options precedence order";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       uses dhcp-generic-v4-option;
     }
     container relay-option-60 {
       description "DHCP option-60 processing";
       presence "enable relay-option-60";
       status deprecated;
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interfae tag configuration";
       leaf name {
         description "Interface tag name";
         type string {
           length "1 .. 64";
         }
       }
       uses apply-advanced;
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     leaf inline-disable {
       description "Disable inline mode for this BFD session";
       type empty;
     }
     leaf pdu-size {
       description "BFD transport protocol payload size";
       default "24";
       type union {
         type string {
           pattern "<.*>|$.*";
         }
         type uint32 {
           range "24 .. 16000";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
       mandatory true;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcp-v4-option-default-action {
     description "Default action";
     uses apply-advanced;
     choice server-group-choice {
       case case_1 {
         leaf relay-server-group {
           description "Name of DHCP relay server group when match is made";
           type string {
             length "1 .. 64";
           }
         }
       }
       case case_2 {
         leaf local-server-group {
           description "Name of DHCP local server group when match is made";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       type string {
         length "1 .. 64";
       }
     }
     leaf allow-server-change {
       description "Accept DHCP-ACK from any server in this group";
       type empty;
     }
   }
   grouping dhcpv4-gp-active-sg-type {
     leaf active-server-group {
       description "Name of DHCP server group";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     leaf exclude-relay-agent-identifier {
       description "Exclude relay agent identifier from packets to server";
       type empty;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       type empty;
     }
     container leasequery {
       description "DHCPv6 leasequery configuration";
       presence "enable leasequery";
       uses relay-leasequery-type;
     }
     container bulk-leasequery {
       description "DHCPv6 bulk leasequery configuration";
       presence "enable bulk-leasequery";
       uses relay-bulk-leasequery-v6-type;
     }
     container active-leasequery {
       description "DHCPv6 active leasequery configuration";
       presence "enable active-leasequery";
       uses active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping active-leasequery-v6-type {
     description "Configure active leasequery";
     uses apply-advanced;
     leaf topology-discover {
       description "Topology discovery";
       type empty;
     }
     list exclude-interface {
       key name;
       ordered-by user;
       description "Exclude interface participating in active leasequery";
       leaf name {
         description "Interface name";
         type union {
           type jt:interface-name;
           type string {
             pattern "<.*>|$.*";
           }
         }
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       description "Peer ipv6 address";
       leaf name {
         description "Peer ipv6 address";
         type jt:ipv6addr;
       }
       uses apply-advanced;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       uses dhcp-generic-v6-option-type;
     }
     container option-16 {
       description "Add option 16 processing";
       presence "enable option-16";
       uses dhcp-generic-v6-option-type;
     }
     list option-order {
       key name;
       ordered-by user;
       description "Options precedence order";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf nak-unknown-rebind {
       description "Nak unknown rebind requests";
       type empty;
     }
     leaf nak-unknown-renew {
       description "Nak unknown renew requests";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configurations";
       leaf name {
         description "Interface tag name";
         type string {
           length "1 .. 64";
         }
       }
       uses apply-advanced;
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       type string {
         length "1 .. 64";
       }
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container client-id {
         presence "enable client-id";
         description "Include client ID";
         leaf exclude-headers {
           description "Exclude all the headers";
           type empty;
         }
         leaf use-automatic-ascii-hex-encoding {
           description "Use automatic ascii hex username encoding";
           type empty;
         }
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       type string {
         length "1 .. 80";
       }
       mandatory true;
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-traceoptions-type {
     description "Trace options for DHCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
           enum "era" {
             description "DHCP ERA logging option dhcp";
           }
           enum "telemetry" {
             description "Telemetry operation";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-group {
     description "Configuration groups";
     leaf name {
       description "Group name";
       type string {
         length "1 .. 254";
       }
     }
     container when {
       description "Specify additional conditions for groups";
       uses apply-advanced;
       container time {
         description "Time at which group should be effective";
         leaf start-time {
           description "Start time([yyyy-mm-dd.]hh:mm)";
           type string;
         }
         container to {
           description "End time";
           uses apply-advanced;
           leaf end-time {
             description "End time([yyyy-mm-dd.]hh:mm)";
             type string;
           }
         }
       }
       leaf-list peers {
         ordered-by user;
         description "Hosts on which this group should be effective";
         type string {
           length "1 .. 255";
         }
       }
       leaf chassis {
         description "Chassis id";
         type enumeration {
           enum "lcc0" {
             description "Chassis lcc0";
           }
           enum "lcc1" {
             description "Chassis lcc1";
           }
           enum "lcc2" {
             description "Chassis lcc2";
           }
           enum "lcc3" {
             description "Chassis lcc3";
           }
           enum "lcc4" {
             description "Chassis lcc4";
           }
           enum "lcc5" {
             description "Chassis lcc5";
           }
           enum "lcc6" {
             description "Chassis lcc6";
           }
           enum "lcc7" {
             description "Chassis lcc7";
           }
           enum "scc" {
             description "Chassis scc";
           }
           enum "sfc0" {
             description "Chassis sfc0";
           }
         }
       }
       leaf model {
         description "Model name";
         type string;
       }
       leaf routing-engine {
         description "Routing Engine";
         type enumeration {
           enum "re0" {
             description "RE0";
           }
           enum "re1" {
             description "RE1";
           }
         }
       }
       leaf member {
         description "Member of virtual chassis";
         type string;
       }
       leaf node {
         description "Node of cluster";
         type enumeration {
           enum "node0" {
             description "Node0";
           }
           enum "node1" {
             description "Node1";
           }
         }
       }
     }
     uses juniper-config;
   }
   grouping juniper-logical-system {
     description "Logical system configuration";
     leaf name {
       description "Logical system name";
       type string {
       }
     }
     uses apply-advanced;
     container interfaces {
       description "Interface configuration";
       uses apply-advanced;
       list interface {
         key name;
         uses lr_interfaces_type;
       }
     }
     container protocols {
       description "Routing protocol configuration";
       uses juniper-protocols;
     }
     container policy-options {
       description "Policy option configuration";
       uses juniper-policy-options;
     }
     container routing-options {
       description "Protocol-independent routing option configuration";
       uses juniper-routing-options;
     }
     container forwarding-options {
       description "Configure options to control packet forwarding";
       uses apply-advanced;
       container dhcp-relay {
         description "Dynamic Host Configuration Protocol relay configuration";
         uses jdhcp-relay-type;
       }
       list storm-control-profiles {
         key name;
         description "Storm control profile for this instance";
         leaf name {
           description "Storm control profile name";
           type string {
             length "1 .. 127";
           }
         }
         uses apply-advanced;
         container all {
           presence "enable all";
           description "For all BUM traffic";
           uses apply-advanced;
           choice bandwidth {
             case case_1 {
               leaf bandwidth-percentage {
                 description "Percentage of link bandwidth";
                 type union {
                   type string {
                     pattern "<.*>|$.*";
                   }
                   type uint32;
                 }
               }
             }
             case case_2 {
               leaf bandwidth-level {
                 description "Link bandwidth";
                 units "kbps";
                 type union {
                   type string {
                     pattern "<.*>|$.*";
                   }
                   type uint32;
                 }
               }
             }
           }
           leaf burst-size {
             description "Burst size";
             units "bytes";
             type union {
               type string {
                 pattern "<.*>|$.*";
               }
               type uint32;
             }
           }
           leaf no-broadcast {
             description "Disable broadcast storm control";
             type empty;
           }
           leaf no-unknown-unicast {
             description "Disable unknown unicast storm control";
             type empty;
           }
           choice no-multicast-choices {
             case case_1 {
               leaf no-multicast {
                 description "Disable multicast storm control";
                 type empty;
               }
             }
             case case_2 {
               leaf no-registered-multicast {
                 description "Disable registered multicast storm control";
                 type empty;
               }
             }
             case case_3 {
               leaf no-unregistered-multicast {
                 description "Disable unregistered multicast storm control";
                 type empty;
               }
             }
           }
         }
         leaf action-shutdown {
           description "Disable port for excessive storm control errors";
           type empty;
         }
       }
       container sampling {
         presence "enable sampling";
         uses apply-advanced;
         container family {
           description "Address family of packets to sample";
           container inet {
             description "Sample IPv4 packets";
             uses apply-advanced;
             container output {
               description "Configure output options for packet sampling";
               uses apply-advanced;
               list flow-server {
                 key name;
                 description "Configure sending traffic aggregates in cflowd format";
                 max-elements 8;
                 uses cflowd_sampling_inet_lr_type;
               }
             }
           }
           container mpls {
             description "Sample MPLS packets";
             uses apply-advanced;
             container output {
               description "Configure output options for packet sampling";
               uses apply-advanced;
               list flow-server {
                 key name;
                 description "Configure sending traffic aggregates in cflowd format";
                 max-elements 8;
                 uses cflowd_sampling_mpls_lr_type;
               }
             }
           }
         }
       }
     }
     container system {
       description "System parameters";
       uses apply-advanced;
       container arp {
         description "ARP settings";
         uses apply-advanced;
         leaf aging-timer {
           description "Change the ARP aging time value";
           units "minutes";
           type union {
             type string {
               pattern "<.*>|$.*";
             }
             type int32 {
               range "1 .. 240";
             }
           }
         }
         container interfaces {
           description "Logical interface on which to specify ARP aging timer";
           uses apply-advanced;
           list arp-interface {
             key name;
             uses arp-interface-type;
           }
         }
         leaf passive-learning {
           description "ARP passive learning";
           type empty;
         }
         leaf purging {
           description "ARP purging when link goes down";
           type empty;
         }
         leaf gratuitous-arp-on-ifup {
           description "Gratuitous ARP announcement on interface up";
           type empty;
         }
         leaf gratuitous-arp-delay {
           description "Delay gratuitous ARP request";
           type union {
             type string {
               pattern "<.*>|$.*";
             }
             type uint32 {
               range "1 .. 4000000";
             }
           }
         }
         leaf non-subscriber-no-reply {
           description "Do not reply to ARP requests from non-subscribers";
           type empty;
         }
         leaf proxy-arp-reply-for-default {
           description "Reply to proxy ARP request when target matches default-route";
           type empty;
         }
         leaf unicast-mode-on-expire {
           description "Send unicast ARP request on expiry timer";
           type empty;
         }
         leaf respond-out-of-subnet {
           description "Respond to out of subnet arp requests";
           type empty;
         }
         leaf arp-retries {
           description "Set maximum ARP retries";
           type union {
             type uint32;
             type string {
               pattern "<.*>|$.*";
             }
           }
         }
       }
       container services {
         description "System services";
         uses apply-advanced;
         container dhcp-local-server {
           description "Dynamic Host Configuration Protocol server configuration";
           uses jdhcp-local-server-type;
         }
       }
       container processes {
         description "Process control";
         uses apply-advanced;
         container routing {
           presence "enable routing";
           description "Routing process";
           uses apply-advanced;
           choice mode {
             case case_1 {
               leaf force-32-bit {
                 description "Always use 32-bit mode";
                 type empty;
               }
             }
             case case_2 {
               leaf force-64-bit {
                 description "Always use 64-bit mode";
                 type empty;
               }
             }
             case case_3 {
               leaf auto-64-bit {
                 description "Ignored; same as force-32-bit";
                 type empty;
               }
             }
           }
         }
       }
     }
     container access {
       description "Network access configuration";
       uses apply-advanced;
       container address-assignment {
         description "Address assignment configuration";
         uses address-assignment-type;
       }
       container address-protection {
         presence "enable address-protection";
         description "Initiate Duplicate Address Protection";
         uses apply-advanced;
         leaf reassign-on-match {
           description "Disconnect owning session and reassign to this session";
           type empty;
         }
       }
     }
     container access-profile {
       description "Access profile for this instance";
       leaf access-profile-name {
         description "Profile name";
         type string;
       }
     }
     container firewall {
       description "Define a firewall configuration";
       uses apply-advanced;
       container family {
         description "Protocol family";
         container inet {
           description "Protocol family IPv4 for firewall filter";
           uses apply-advanced;
           list prefix-action {
             key name;
             ordered-by user;
             description "Define a prefix action";
             uses prefix_action;
           }
           list filter {
             key name;
             description "Define an IPv4 firewall filter";
             uses inet_filter;
           }
           list service-filter {
             key name;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list filter {
             key name;
             description "Define an IPv6 firewall filter";
             uses inet6_filter;
           }
           list service-filter {
             key name;
             description "One or more IPv6 service filters";
             uses inet6_service_filter;
           }
           list fast-update-filter {
             key name;
             ordered-by user;
             description "One or more fast update filters";
             uses inet6_fuf;
           }
         }
         container vpls {
           description "Protocol family VPLS for firewall filter";
           uses apply-advanced;
           list filter {
             key name;
             uses vpls_filter;
           }
         }
         container evpn {
           description "Protocol family EVPN for firewall filter";
           uses apply-advanced;
           list filter {
             key name;
             uses vpls_filter;
           }
         }
         container ccc {
           description "Protocol family CCC for firewall filter";
           uses apply-advanced;
           list filter {
             key name;
             uses ccc_filter;
           }
         }
         container any {
           description "Protocol-independent filter";
           uses apply-advanced;
           list filter {
             key name;
             description "Define a protocol independent filter";
             uses any_filter;
           }
         }
         container ethernet-switching {
           description "Protocol family Ethernet Switching for firewall filter";
           uses apply-advanced;
           list filter {
             key name;
             description "Define an Ethernet Switching firewall filter";
             uses es_filter;
           }
         }
       }
       list policer {
         key name;
         description "Policer template definition";
         uses firewall_policer;
       }
       list flexible-match {
         key name;
         description "Flexible packet match template definition";
         uses firewall_flexible_match;
       }
       list tunnel-end-point {
         key name;
         description "Tunnel end-point template definition";
         uses tunnel_end_point;
       }
       list hierarchical-policer {
         key name;
         description "Hierarchical policer template definition";
         uses firewall_hierpolicer;
       }
       leaf disable-arp-policers {
         description "Disables ARP policers";
         type empty;
       }
       list interface-set {
         key name;
         description "Interface set definition";
         uses interface_set_type;
       }
       list filter {
         key name;
         description "Define an IPv4 firewall filter";
         uses inet_filter;
       }
     }
     container multicast-snooping-options {
       description "Multicast snooping option configuration";
       uses juniper-multicast-snooping-options;
     }
     container services {
       description "Service PIC daemon configuration";
       uses apply-advanced;
     }
     container switch-options {
       description "Options for default routing-instance of type virtual-switch";
       uses juniper-def-rtb-switch-options;
     }
     container vlans {
       description "VLAN configuration";
       uses apply-advanced;
       list vlan {
         key name;
         description "Virtual LAN";
         uses vlan-types;
       }
       container vlan-groups {
         description "802.1x VLAN group configuration";
         uses apply-advanced;
         list vlan-group {
           key name;
           description "802.1x Vlan group";
           max-elements 4096;
           uses vlan-group-types;
         }
       }
     }
   }
   grouping address-assignment-type {
     description "Address assignment configuration";
     uses apply-advanced;
     container neighbor-discovery-router-advertisement {
       description "Designated NDRA pool for this instance";
       leaf ndra-name {
         description "Designated NDRA pool name";
         type string {
           length "1 .. 63";
         }
       }
     }
     leaf high-utilization {
       description "Generate an SNMP trap when address pool use surpasses this percentage";
       type union {
         type string {
           pattern "<.*>|$.*";
         }
         type uint16 {
           range "2 .. 99";
         }
       }
     }
     leaf abated-utilization {
       description "Generate an SNMP clear trap when address pool use falls below this percentage";
       type union {
         type string {
           pattern "<.*>|$.*";
         }
         type uint16 {
           range "1 .. 98";
         }
       }
     }
     leaf high-utilization-v6 {
       description "Generate an SNMP trap when address pool use surpasses this percentage";
       type union {
         type string {
           pattern "<.*>|$.*";
         }
         type uint16 {
           range "2 .. 99";
         }
       }
     }
     leaf abated-utilization-v6 {
       description "Generate an SNMP clear trap when address pool use falls below this percentage";
       type union {
         type string {
           pattern "<.*>|$.*";
         }
         type uint16 {
           range "1 .. 98";
         }
       }
     }
     list pool {
       key name;
       ordered-by user;
       description "Address pool";
       leaf name {
         description "Address pool name";
         type string {
           length "1 .. 63";
         }
       }
       uses apply-advanced;
       leaf active-drain {
         description "Notify client of pool active drain mode";
         type empty;
       }
       leaf hold-down {
         description "Place pool in passive drain mode";
         type empty;
       }
       leaf link {
         description "Address pool link name";
         type string {
           length "1 .. 63";
         }
       }
       container family {
         presence "enable family";
         description "Address family";
         choice family_type {
           case case_1 {
             container inet {
               presence "enable inet";
               description "IPv4";
               uses apply-advanced;
               leaf network {
                 description "Network address";
                 type jt:ipv4prefix;
                 mandatory true;
               }
               list range {
                 key name;
                 ordered-by user;
                 description "Address range";
                 leaf name {
                   description "Range name";
                   type string {
                     length "1 .. 63";
                   }
                 }
                 uses apply-advanced;
                 leaf low {
                   description "Lower limit of address range";
                   type jt:ipv4addr;
                   mandatory true;
                 }
                 leaf high {
                   description "Upper limit of address range";
                   type jt:ipv4addr;
                   mandatory true;
                 }
               }
               container dhcp-attributes {
                 description "DHCP options and match criteria";
                 uses dhcp-attribute-type;
               }
               container xauth-attributes {
                 description "Configure xauth attributes";
                 uses apply-advanced;
                 leaf primary-dns {
                   description "Specify the primary-dns IP address";
                   type jt:ipv4prefix;
                 }
                 leaf secondary-dns {
                   description "Specify the secondary-dns IP address";
                   type jt:ipv4prefix;
                 }
                 leaf primary-wins {
                   description "Specify the primary-wins IP address";
                   type jt:ipv4prefix;
                 }
                 leaf secondary-wins {
                   description "Specify the secondary-wins IP address";
                   type jt:ipv4prefix;
                 }
               }
               list host {
                 key name;
                 ordered-by user;
                 description "Hostname for static reservations";
                 leaf name {
                   description "Hostname";
                   type string {
                     length "1 .. 256";
                   }
                 }
                 uses apply-advanced;
                 leaf hardware-address {
                   description "Hardware address";
                   type jt:mac-addr;
                 }
                 leaf ip-address {
                   description "Reserved address";
                   type jt:ipv4addr;
                   mandatory true;
                 }
                 choice host-identifier-type {
                   case case_1 {
                     leaf user-name {
                       description "Set subscriber user name as host identifier";
                       type empty;
                     }
                   }
                 }
               }
               list excluded-address {
                 key name;
                 ordered-by user;
                 description "Excluded Addresses";
                 max-elements 20;
                 leaf name {
                   description "Excluded address";
                   type jt:ipv4addr;
                 }
                 uses apply-advanced;
               }
               list excluded-range {
                 key name;
                 ordered-by user;
                 description "Excluded address range";
                 max-elements 20;
                 leaf name {
                   description "Range name";
                   type string {
                     length "1 .. 63";
                   }
                 }
                 uses apply-advanced;
                 leaf low {
                   description "Lower limit of excluded address range";
                   type jt:ipv4addr;
                   mandatory true;
                 }
                 leaf high {
                   description "Upper limit of excluded address range";
                   type jt:ipv4addr;
                   mandatory true;
                 }
               }
             }
           }
           case case_2 {
           }
         }
       }
     }
     list domain-profile {
       key name;
       ordered-by user;
       description "Address domain profile";
       leaf name {
         description "Pool domain profile name";
         type string {
           length "1 .. 63";
         }
       }
       uses apply-advanced;
       container family {
         presence "enable family";
         description "Network family to which this configuration belongs";
         uses apply-advanced;
         choice family_type {
           case case_1 {
             container inet {
               description "The IPv4 internet family";
               uses apply-advanced;
               leaf preferred-prefix-length {
                 description "Preferred prefix length";
                 type union {
                   type string {
                     pattern "<.*>|$.*";
                   }
                   type uint32 {
                     range "8 .. 30";
                   }
                 }
                 mandatory true;
               }
               leaf source-partition-qualifier {
                 description "Prefix source qualifier appended to location for partition name";
                 type string {
                   length "1 .. 63";
                 }
               }
               container excluded-address {
                 description "Excluded addresses from allocation";
                 leaf-list last-octet {
                   ordered-by user;
                   description "Last octet of the excluded address";
                   type union {
                     type string {
                       pattern "<.*>|$.*";
                     }
                     type uint8 {
                       range "0 .. 255";
                     }
                   }
                 }
               }
               container install-discard-routes {
                 presence "enable install-discard-routes";
                 description "Install discard route domain pool prefix";
                 uses apply-advanced;
                 leaf tag {
                   description "Route tag";
                   type union {
                     type string {
                       pattern "<.*>|$.*";
                     }
                     type uint32 {
                       range "0 .. 4294967295";
                     }
                   }
                 }
               }
               leaf dhcp-gateway-address-last-octet {
                 description "DHCP host address component to be excluded and passed to DHCP";
                 type union {
                   type string {
                     pattern "<.*>|$.*";
                   }
                   type uint8 {
                     range "1 .. 8";
                   }
                 }
               }
               leaf protocol-attributes {
                 description "Access protocol-attributes name";
                 type string {
                   length "1 .. 63";
                 }
               }
             }
           }
           case case_2 {
             container inet6 {
               description "The IPv6 internet family";
               uses apply-advanced;
               leaf partition-type {
                 description "Partition type";
                 type enumeration {
                   enum "non-temporary-address" {
                     description "Address to advertise in DHCPv6";
                   }
                   enum "delegated-prefix" {
                     description "Prefix to advertise in DHCPv6";
                   }
                   enum "router-advertisement" {
                     description "Prefix for router advertisement";
                   }
                 }
                 mandatory true;
               }
               leaf preferred-prefix-length {
                 description "Preferred prefix length";
                 type union {
                   type string {
                     pattern "<.*>|$.*";
                   }
                   type uint32 {
                     range "8 .. 126";
                   }
                 }
                 mandatory true;
               }
               leaf allocation-length {
                 description "Per-allocation length";
                 default "128";
                 type union {
                   type string {
                     pattern "<.*>|$.*";
                   }
                   type uint32 {
                     range "8 .. 128";
                   }
                 }
               }
               leaf source-partition-qualifier {
                 description "Prefix source qualifier appended to location for partition name";
                 type string {
                   length "1 .. 63";
                 }
               }
               container install-discard-routes {
                 presence "enable install-discard-routes";
                 description "Install discard route domain pool prefix";
                 uses apply-advanced;
                 leaf tag {
                   description "Route tag";
                   type union {
                     type string {
                       pattern "<.*>|$.*";
                     }
                     type uint32 {
                       range "0 .. 4294967295";
                     }
                   }
                 }
               }
               leaf protocol-attributes {
                 description "Access protocol-attributes name";
                 type string {
                   length "1 .. 63";
                 }
               }
             }
           }
         }
       }
     }
   }
   grouping arp-interface-type {
     description "Logical interface on which to configure ARP aging timer";
     leaf name {
       description "Interface name";
       type union {
         type jt:interface-name;
         type string {
           pattern "<.*>|$.*";
         }
       }
     }
     uses apply-advanced;
     leaf aging-timer {
       description "Change the ARP aging time value";
       units "minutes";
       type union {
         type string {
           pattern "<.*>|$.*";
         }
         type uint32 {
           range "1 .. 600000";
         }
       }
       mandatory true;
     }
   }
   grouping cflowd_sampling_inet_lr_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
   }
   grouping aggregation_type {
     uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       uses apply-advanced;
       leaf caida-compliant {
         description "Compatible with Caida record format for prefix aggregation (v8)";
         type empty;
       }
     }
   }
   grouping cflowd_sampling_mpls_lr_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
   }
   grouping dhcp-attribute-type {
     uses apply-advanced;
     container option-match {
       description "Match";
       uses apply-advanced;
       container option-82 {
         uses apply-advanced;
         list circuit-id {
           key name;
           ordered-by user;
           description "Circuit ID portion of the option 82";
           leaf name {
             type string;
           }
           leaf range {
             description "Range name";
             type string;
             mandatory true;
           }
         }
         list remote-id {
           key name;
           ordered-by user;
           description "Remote ID portion of the option 82";
           leaf name {
             type string;
           }
           leaf range {
             description "Range name";
             type string;
             mandatory true;
           }
         }
       }
     }
     leaf maximum-lease-time {
       description "Maximum lease time advertised to clients";
       units "seconds";
       type string;
     }
     leaf server-identifier {
       description "Server Identifier - IP address value";
       type jt:ipv4addr;
     }
     leaf grace-period {
       description "Grace period for leases";
       units "seconds";
       type union {
         type uint32;
         type string {
           pattern "<.*>|$.*";
         }
       }
     }
     leaf domain-name {
       description "Domain name advertised to clients";
       type string {
       }
     }
     list name-server {
       key name;
       ordered-by user;
       description "Domain name servers available to the client";
       leaf name {
         description "DNS server's IPv4 address";
         type jt:ipv4addr;
       }
       uses apply-advanced;
     }
     list wins-server {
       key name;
       ordered-by user;
       description "WINS name servers";
       leaf name {
         description "WINS server's IPv4 address";
         type jt:ipv4addr;
       }
       uses apply-advanced;
     }
     list router {
       key name;
       description "Routers advertised to clients";
       leaf name {
         description "Router's IPv4 address";
         type jt:ipv4addr;
       }
       uses apply-advanced;
     }
     leaf boot-file {
       description "Boot filename advertised to clients";
       type string;
     }
     leaf boot-server {
       description "Boot server advertised to clients";
       type string {
       }
     }
     leaf tftp-server {
       description "TFTP server IP address advertised to clients";
       type jt:ipv4addr;
     }
     leaf netbios-node-type {
       description "Type of NETBIOS node advertised to clients";
       type enumeration {
         enum "b-node" {
           description "Broadcast node";
         }
         enum "p-node" {
           description "Peer-to-peer node";
         }
         enum "m-node" {
           description "Mixed Node";
         }
         enum "h-node" {
           description "Hybrid node";
         }
       }
     }
     leaf sip-server-domain-name {
       description "SIP server domain name available to clients";
       type string {
       }
     }
     list sip-server-address {
       key name;
       ordered-by user;
       description "SIP Servers list of IPv6 addresses available to the client";
       leaf name {
         description "SIP Server's IPv6 address";
         type jt:ipv6addr;
       }
       uses apply-advanced;
     }
     list dns-server {
       key name;
       ordered-by user;
       description "Domain name servers available to the client";
       leaf name {
         description "DNS server's IPv6 address";
         type jt:ipv6addr;
       }
       uses apply-advanced;
     }
     list option {
       key name;
       ordered-by user;
       description "DHCP option";
       leaf name {
         description "DHCP option identifier code";
         type union {
           type uint32;
           type string {
             pattern "<.*>|$.*";
           }
         }
       }
       choice option-type-choice {
         case case_1 {
           leaf flag {
             description "Boolean flag value";
             type enumeration {
               enum "true" {
                 description "True value";
               }
               enum "false" {
                 description "False value";
               }
               enum "on" {
                 description "On value";
               }
               enum "off" {
                 description "Off value";
               }
             }
           }
         }
         case case_2 {
           leaf byte {
             description "Unsigned 8-bit value";
             type union {
               type uint8;
               type string {
                 pattern "<.*>|$.*";
               }
             }
           }
         }
         case case_3 {
           leaf short {
             description "Signed 16-bit numeric value";
             type union {
               type int16;
               type string {
                 pattern "<.*>|$.*";
               }
             }
           }
         }
         case case_4 {
           leaf unsigned-short {
             description "Unsigned 16-bit numeric value";
             type union {
               type uint16;
               type string {
                 pattern "<.*>|$.*";
               }
             }
           }
         }
         case case_5 {
           leaf integer {
             description "Signed 32-bit numeric value";
             type union {
               type int32;
               type string {
                 pattern "<.*>|$.*";
               }
             }
           }
         }
         case case_6 {
           leaf unsigned-integer {
             description "Unsigned 32-bit numeric value";
             type union {
               type uint32;
               type string {
                 pattern "<.*>|$.*";
               }
             }
           }
         }
         case case_7 {
           leaf hex-string {
             description "Hexadecimal string";
             type string {
               length "1 .. 510";
             }
           }
         }
         case case_8 {
           leaf string {
             description "Character string value";
             type string {
               length "1 .. 254";
             }
           }
         }
         case case_9 {
           leaf ip-address {
             description "IP address value";
             type jt:ipv4addr;
           }
         }
         case case_10 {
           leaf ipv6-address {
             description "IPV6 address value";
             type jt:ipv6addr;
           }
         }
         case case_11 {
           container array {
             presence "enable array";
             description "Array of values";
             uses apply-advanced;
             choice option-type-array-choice {
               case case_1 {
                 leaf-list flag {
                   ordered-by user;
                   description "Array of boolean flag values";
                   type enumeration {
                     enum "true" {
                       description "True value";
                     }
                     enum "false" {
                       description "False value";
                     }
                     enum "on" {
                       description "On value";
                     }
                     enum "off" {
                       description "Off value";
                     }
                   }
                 }
               }
               case case_2 {
                 leaf-list byte {
                   ordered-by user;
                   description "Array of unsigned 8-bit values";
                   type union {
                     type uint8;
                     type string {
                       pattern "<.*>|$.*";
                     }
                   }
                 }
               }
               case case_3 {
                 leaf-list short {
                   ordered-by user;
                   description "Array of signed 16-bit numeric values";
                   type union {
                     type int16;
                     type string {
                       pattern "<.*>|$.*";
                     }
                   }
                 }
               }
               case case_4 {
                 leaf-list unsigned-short {
                   ordered-by user;
                   description "Array of 16-bit numeric values";
                   type union {
                     type uint16;
                     type string {
                       pattern "<.*>|$.*";
                     }
                   }
                 }
               }
               case case_5 {
                 leaf-list integer {
                   ordered-by user;
                   description "Array of signed 32-bit numeric values";
                   type union {
                     type int32;
                     type string {
                       pattern "<.*>|$.*";
                     }
                   }
                 }
               }
               case case_6 {
                 leaf-list unsigned-integer {
                   ordered-by user;
                   description "Array of unsigned 32-bit numeric values";
                   type union {
                     type uint32;
                     type string {
                       pattern "<.*>|$.*";
                     }
                   }
                 }
               }
               case case_7 {
                 leaf-list hex-string {
                   ordered-by user;
                   description "Hexadecimal string";
                   type string {
                     length "1 .. 510";
                   }
                 }
               }
               case case_8 {
                 leaf-list string {
                   ordered-by user;
                   description "Array of character string values";
                   type string {
                     length "1 .. 254";
                   }
                 }
               }
               case case_9 {
                 leaf-list ip-address {
                   ordered-by user;
                   description "Array of IP address values";
                   type jt:ipv4addr;
                 }
               }
               case case_10 {
                 leaf-list ipv6-address {
                   ordered-by user;
                   description "Array of IPv6 address values";
                   type jt:ipv6addr;
                 }
               }
             }
           }
         }
       }
     }
     leaf valid-lifetime {
       description "Valid lifetime advertised to clients";
       units "seconds";
       type string;
     }
     leaf preferred-lifetime {
       description "Preferred lifetime advertised to clients";
       units "seconds";
       type string;
     }
     leaf t1-percentage {
       description "T1 time as percentage of preferred lifetime or max lease";
       units "percent";
       type union {
         type string {
           pattern "<.*>|$.*";
         }
         type uint32 {
           range "0 .. 100";
         }
       }
     }
     leaf t2-percentage {
       description "T2 time as percentage of preferred lifetime or max lease";
       units "percent";
       type union {
         type string {
           pattern "<.*>|$.*";
         }
         type uint32 {
           range "0 .. 100";
         }
       }
     }
     leaf exclude-prefix-len {
       description "Length of IPv6 prefix to be excluded from delegated prefix";
       type union {
         type string {
           pattern "<.*>|$.*";
         }
         type uint32 {
           range "1 .. 128";
         }
       }
     }
     leaf t1-renewal-time {
       description "T1 renewal time";
       units "seconds";
       type union {
         type uint32;
         type string {
           pattern "<.*>|$.*";
         }
       }
     }
     leaf t2-rebinding-time {
       description "T2 rebinding time";
       units "seconds";
       type union {
         type uint32;
         type string {
           pattern "<.*>|$.*";
         }
       }
     }
   }
   grouping jdhcp-local-server-type {
     uses apply-advanced;
     container traceoptions {
       description "DHCP local server trace options";
       status deprecated;
       uses jdhcp-traceoptions-type;
     }
     container interface-traceoptions {
       description "DHCP local server interface trace options";
       status deprecated;
       uses jdhcp-interface-traceoptions-type;
     }
     container dhcpv6 {
       description "DHCPv6 configuration";
       uses dhcpv6-local-server-type;
     }
     list pool-match-order {
       key name;
       ordered-by user;
       description "Define order of attribute matching for pool selection";
       leaf name {
         description "Match type";
         type enumeration {
           enum "external-authority" {
             description "External authority handles address selection";
           }
           enum "ip-address-first" {
             description "IP address used first to select a pool";
           }
           enum "option-82" {
             description "Option 82 used in matching of pool";
           }
           enum "option-82-strict" {
             description "Option 82 used in strict matching of pool";
           }
         }
       }
       uses apply-advanced;
     }
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container reconfigure {
       description "DHCP reconfigure processing";
       presence "enable reconfigure";
       uses reconfigure-type;
     }
     container overrides {
       description "DHCP override processing";
       presence "enable overrides";
       uses override-local-server-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list group {
       key name;
       ordered-by user;
       description "Define a DHCP local server group";
       uses dhcp-local-server-group;
     }
     list dual-stack-group {
       key name;
       description "Define a DHCP dual stack group";
       uses dhcp-local-server-dual-stack-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     choice requested-ip-check {
       case case_1 {
         leaf requested-ip-network-match {
           description "Subnet to match server's address for active and giaddr for passive clients";
           default "8";
           type union {
             type string {
               pattern "<.*>|$.*";
             }
             type uint32 {
               range "0 .. 31";
             }
           }
         }
       }
       case case_2 {
         leaf requested-ip-interface-match {
           description "Use incoming-interface's subnet to check";
           type empty;
         }
       }
     }
     leaf no-snoop {
       description "Do not snoop DHCP packets";
       type empty;
     }
     container persistent-storage {
       description "Trigger to enable flat file storage";
       leaf automatic {
         description "Trigger automatically";
         type empty;
       }
     }
     container allow-leasequery {
       description "Allow DHCP leasequery";
       presence "enable allow-leasequery";
       uses server-leasequery-type;
     }
     container remote-id-mismatch {
       description "DHCP client remote-id mismatch";
       presence "enable remote-id-mismatch";
       uses dhcp-remote-id-mismatch-type;
     }
     container reauthenticate {
       presence "enable reauthenticate";
       description "DHCP client reauthenticate processing";
       uses apply-advanced;
       leaf lease-renewal {
         description "Reauthenticate on each renew, rebind, DISCOVER or SOLICIT";
         type empty;
       }
       leaf remote-id-mismatch {
         description "Reauthenticate on remote-id mismatch for renew, rebind and re-negotiation";
         type empty;
       }
       container actual-data-rate-change {
         description "Reauthenticate on data rate change";
         uses actual-data-rate-change-type;
       }
     }
     container allow-bulk-leasequery {
       description "Allow DHCP bulk leasequery";
       presence "enable allow-bulk-leasequery";
       uses server-bulk-leasequery-type;
     }
     container allow-active-leasequery {
       description "Allow DHCP active leasequery";
       presence "enable allow-active-leasequery";
       uses server-active-leasequery-type;
     }
     container active-leasequery {
       description "DHCPv4 active leasequery configuration";
       presence "enable active-leasequery";
       uses active-leasequery-v4-type;
     }
   }
   grouping actual-data-rate-change-type {
     description "Reauthenticate on data rate change processing";
     uses apply-advanced;
     container actual-data-rate-upstream {
       description "Actual data rate upstream";
       presence "enable actual-data-rate-upstream";
       uses actual-data-rate-type;
     }
     container actual-data-rate-downstream {
       description "Actual data rate downstream";
       presence "enable actual-data-rate-downstream";
       uses actual-data-rate-type;
     }
   }
   grouping actual-data-rate-type {
     description "Actual data rate type processing";
     uses apply-advanced;
     leaf threshold {
       description "Threshold in kbps";
       type union {
         type uint32;
         type string {
           pattern "<.*>|$.*";
         }
       }
     }
   }
   grouping dhcp-local-server-dual-stack-group {
     description "DHCP dual stack groups";
     leaf name {
       description "Dual stack group name";
       type string {
         length "1 .. 64";
       }
     }
     uses apply-advanced;
     container authentication {
       description "DHCP authentication";
       uses dual-stack-authentication-type;
     }
     leaf access-profile {
       description "Access profile to be used for jdhcpd";
       type string {
         length "1 .. 128";
       }
     }
     container dynamic-profile {
       description "Dynamic profile to use";
       uses dynamic-profile-type;
     }
     leaf service-profile {
       description "Dynamic profile to use for default service activation";
       type string {
         length "1 .. 128";
       }
     }
     leaf on-demand-address-allocation {
       description "Allocate addresses on demand";
       type empty;
     }
     container classification-key {
       description "Classification key for identifying dual stack household";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container liveness-detection {
       description "DHCP client liveness detection processing";
       uses dhcp-liveness-detection-dualstack-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping dhcp-local-server-group {
     description "DHCP groups";
     leaf name {
       description "Group name";
       type string {
         length "1 .. 64";
       }
     }
     uses apply-advanced;
     container authentication {
       description "DHCP authentication";
       uses authentication-type;
     }
     container liveness-detection {
       description "DHCP client liveness detection processing";
       uses dhcp-liveness-detection-type;
     }
     container reconfigure {
       description "DHCP reconfigure processing";
       presence "enable reconfigure";
       uses reconfigure-type;
     }
     container overrides {
       description "DHCP override processing";
       presence "enable overrides";
       uses override-local-server-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configuration";
       leaf name {
         description "Interface tag name";
         type string {
           length "1 .. 64";
         }
       }
       uses apply-advanced;
       container overrides {
         description "DHCP override processing";
         uses override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       presence "enable reauthenticate";
       description "DHCP client reauthenticate processing";
       uses apply-advanced;
       leaf lease-renewal {
         description "Reauthenticate on each renew, rebind, DISCOVER or SOLICIT";
         type empty;
       }
       leaf remote-id-mismatch {
         description "Reauthenticate on remote-id mismatch for renew, rebind and re-negotiation";
         type empty;
       }
       container actual-data-rate-change {
         description "Reauthenticate on data rate change";
         uses actual-data-rate-change-type;
       }
     }
   }
   grouping dhcpv6-local-server-type {
     uses apply-advanced;
     container authentication {
       description "DHCPv6 authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-local-server-type;
     }
     container route-suppression {
       description "Suppress access-internal and/or access route addition";
       uses dhcpv6-route-suppression-type;
     }
     list group {
       key name;
       ordered-by user;
       description "Define a DHCPv6 local server group";
       uses dhcpv6-local-server-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     choice requested-ip-check {
       case case_1 {
         leaf requested-ip-network-match {
           description "Subnet to match server's address for active and link-address for passive clients";
           default "16";
           type union {
             type string {
               pattern "<.*>|$.*";
             }
             type uint32 {
               range "0 .. 127";
             }
           }
         }
       }
       case case_2 {
         leaf requested-ip-interface-match {
           description "Use incoming-interface's subnet to check";
           type empty;
         }
       }
     }
     leaf no-snoop {
       description "Do not snoop DHCPV6 packets";
       type empty;
     }
     container persistent-storage {
       description "Trigger to enable flat file storage";
       leaf automatic {
         description "Trigger automatically";
         type empty;
       }
     }
     container server-duid-type {
       description "Define the DUID type to be used as the Server ID. Type supported is DUID-LL";
       uses duid-type;
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container allow-leasequery {
       description "Allow DHCPv6 leasequery";
       presence "enable allow-leasequery";
       uses server-leasequery-type;
     }
     container allow-bulk-leasequery {
       description "Allow DHCPv6 bulk leasequery";
       presence "enable allow-bulk-leasequery";
       uses server-bulk-leasequery-type;
     }
     container allow-active-leasequery {
       description "Allow DHCPv6 active leasequery";
       presence "enable allow-active-leasequery";
       uses server-active-leasequery-type;
     }
     container duplicate-clients {
       description "Allow duplicate clients";
       uses dhcpv6-duplicate-clients-type;
     }
     container active-leasequery {
       description "DHCPv6 active leasequery configuration";
       presence "enable active-leasequery";
       uses active-leasequery-v6-type;
     }
   }
   grouping dhcpv6-local-server-group {
     description "DHCP groups";
     leaf name {
       description "Group name";
       type string {
         length "1 .. 64";
       }
     }
     uses apply-advanced;
     container authentication {
       description "DHCP authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses dhcpv6-override-local-server-type;
     }
     container route-suppression {
       description "Suppress access-internal and/or access route addition";
       uses dhcpv6-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses dhcpv6-override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     list interface-tag {
       key name;
       description "Interface tag configuration";
       leaf name {
         description "Interface tag name";
         type string {
           length "1 .. 64";
         }
       }
       uses apply-advanced;
       container overrides {
         description "DHCP override processing";
         uses dhcpv6-override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
   }
   grouping dhcpv6-override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container client-negotiation-match {
       description "Use secondary match criteria for SOLICIT PDU";
       choice match-with {
         case case_1 {
           leaf incoming-interface {
             description "Use incoming interface";
             type empty;
           }
         }
       }
     }
     container process-inform {
       presence "enable process-inform";
       description "Process INFORMATION request PDUs";
       uses apply-advanced;
       leaf pool {
         description "Pool name for family inet6";
         type string {
           length "1 .. 64";
         }
       }
     }
     container delay-advertise {
       description "Filter options for dhcp-server";
       presence "enable delay-advertise";
       uses dhcpv6-filter-option;
     }
     leaf delegated-pool {
       description "Delegated pool name for inet6";
       type string {
         length "1 .. 64";
       }
     }
     leaf multi-address-embedded-option-response {
       description "If the client requests multiple addresses place the options in each address";
       type empty;
     }
     leaf always-process-option-request-option {
       description "Always process option even after address allocation failure";
       type empty;
     }
     leaf delete-binding-on-renegotiation {
       description "Delete binding on renegotiation";
       type empty;
     }
     leaf top-level-status-code {
       description "A top level status code option rather than encapsulated in IA for NoAddrsAvail in Advertise PDUs";
       type empty;
     }
     leaf always-add-option-dns-server {
       description "Add option-23, DNS recursive name server in Advertise and Reply";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
     leaf protocol-attributes {
       description "DHCPv6 attributes to use as defined under access protocol-attributes";
       type string {
         length "1 .. 64";
       }
     }
     leaf dual-stack {
       description "Dual stack group to use";
       type string {
         length "1 .. 64";
       }
     }
     leaf nak-unknown-rebind {
       description "Nak unknown rebind requests";
       type empty;
     }
     leaf nak-unknown-renew {
       description "Nak unknown renew requests";
       type empty;
     }
   }
   grouping dhcpv6-filter-option {
     description "Generic DHCPv6 filter processing";
     uses apply-advanced;
     leaf delay-time {
       description "Time delay between solicit and advertise";
       default "3";
       units "seconds";
       type union {
         type string {
           pattern "<.*>|$.*";
         }
         type uint32 {
           range "1 .. 30";
         }
       }
     }
     container based-on {
       description "Option number";
       uses apply-advanced;
       container option-18 {
         presence "enable option-18";
         description "Option 18";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-37 {
         presence "enable option-37";
         description "Option 37";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-15 {
         presence "enable option-15";
         description "Option 15";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-16 {
         presence "enable option-16";
         description "Option 16";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping dhcpv6-reconfigure-type {
     description "DHCPv6 reconfigure processing";
     uses apply-advanced;
     leaf strict {
       description "Only allow packets containing Reconfigure Accept Option";
       type empty;
     }
     leaf clear-on-abort {
       description "Delete client on reconfiguration abort";
       type empty;
     }
     leaf defer-nack-on-abort {
       description "Defer client NACK on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping duid-type {
     uses apply-advanced;
     leaf duid_ll {
       description "Link Layer Address based DUID ";
       type empty;
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     container multichassis-lag-replicate-state {
       presence "enable multichassis-lag-replicate-state";
       description "Enable multichassis lag replication";
       uses apply-advanced;
       leaf suppress-report {
         description "Enable mclag report suppression";
         type empty;
       }
     }
     container oism {
       description "Optimized inter subnet multicast options";
       uses apply-advanced;
       leaf install-star-g-routes {
         description "Install (*,G) multicast routes in data plane";
         type empty;
       }
     }
     leaf nexthop-hold-time {
       description "Nexthop hold time in milliseconds";
       units "milliseconds";
       type union {
         type string {
           pattern "<.*>|$.*";
         }
         type uint32 {
           range "1 .. 1000";
         }
       }
     }
     leaf multicast-router-job-pause {
       description "Pause multicast router handling job";
       type empty;
     }
     leaf multicast-router-no-flood-job-pause {
       description "Pause multicast router no-flood handling job";
       type empty;
     }
     leaf conserve-mcast-routes-in-pfe {
       description "Don't install snooping routes in forwarding plane";
       type empty;
     }
   }
   grouping juniper-packet-accounting-options {
     leaf name {
       description "Name for accounting group";
       type string;
       mandatory true;
     }
     uses apply-advanced;
     container output {
       description "Accounting data disposition";
       uses packet_accounting_output_type;
     }
   }
   grouping juniper-policy-options {
     uses apply-advanced;
     container satellite-policies {
       description "Satellite Policy configuration";
       uses satellite-policy-options;
     }
     list prefix-list {
       key name;
       description "Define a named set of address prefixes";
       leaf name {
         description "Prefix list name";
         type string;
       }
       uses apply-advanced;
       list prefix-list-item {
         key name;
         uses prefix_list_items;
       }
       leaf apply-path {
         description "Apply IP prefixes from a configuration statement";
         type string;
       }
     }
     list mac-list {
       key name;
       ordered-by user;
       description "Define a named set of mac addresses";
       leaf name {
         description "MAc Address list name";
         type string;
       }
       uses apply-advanced;
       list mac-addr-list-item {
         key name;
         uses mac_addr_list_items;
       }
     }
     list vsi-policy {
       key name;
       ordered-by user;
       description "Define a named set of VSI policies";
       leaf name {
         description "VSI policy name";
         type string;
       }
       uses apply-advanced;
       container from {
         description "Conditions to match the VSI policy";
         uses apply-advanced;
         list vsi-manager {
           key "vsi-manager-id vsi-type vsi-version vsi-instance";
           ordered-by user;
           description "VSI manager";
           leaf vsi-manager-id {
             description "VSI manager ID";
             type union {
               type string {
                 pattern "<.*>|$.*";
               }
               type uint32 {
                 range "1 .. 255";
               }
             }
           }
           leaf vsi-type {
             description "VSI type";
             type union {
               type string {
                 pattern "<.*>|$.*";
               }
               type uint32 {
                 range "1 .. 16777216";
               }
             }
           }
           leaf vsi-version {
             description "VSI version";
             type union {
               type string {
                 pattern "<.*>|$.*";
               }
               type uint32 {
                 range "1 .. 255";
               }
             }
           }
           leaf vsi-instance {
             description "VSI instance";
             type string;
           }
           uses apply-advanced;
         }
       }
       container then {
         description "Actions to take if 'from' conditions match";
         uses apply-advanced;
         leaf filter {
           description "Filter name";
           type string;
           mandatory true;
         }
       }
     }
     leaf skip-then-actions {
       description "Skip 'then' actions and allow route actions in 'from'";
       type empty;
     }
     list rib-list {
       key name;
       ordered-by user;
       description "Define a named set of RIB names or wildcards";
       leaf name {
         description "RIB list name";
         type string;
       }
       uses apply-advanced;
       list rib-list-item {
         key name;
         uses rib_list_items;
       }
     }
     list route-filter-list {
       key name;
       description "Define a named set of route-filter address prefixes";
       leaf name {
         description "Route filter list name";
         type string;
       }
       uses apply-advanced;
       list rf_list {
         key "address choice-ident choice-value";
         ordered-by user;
         uses route_filter_list_items;
       }
     }
     list source-address-filter-list {
       key name;
       description "Define a named set of source address filter address prefixes";
       leaf name {
         description "Source address filter list name";
         type string;
       }
       uses apply-advanced;
       list saf_list {
         key "address choice-ident choice-value";
         ordered-by user;
         uses source_address_filter_list_items;
       }
     }
     list fast-lookup-tuple-list {
       key name;
       description "Define a named set of address prefixes";
       leaf name {
         description "Five tuple combination list name";
         type string;
       }
       uses apply-advanced;
       list fast_lookup_tuple_list_item {
         key name;
         uses fast_lookup_tuple_list_items;
       }
     }
     list policy-statement {
       key name;
       description "Routing policy";
       leaf name {
         description "Name to identify a policy filter";
         type string;
       }
       uses apply-advanced;
       container defaults {
         description "Policy default behaviour";
         uses apply-advanced;
         container route-filter {
           description "Set route filter behaviour";
           choice scope-choice {
             case case_1 {
               leaf no-walkup {
                 description "Route filter walk up disable";
                 type empty;
               }
             }
             case case_2 {
               leaf walkup {
                 description "Route filter walk up enable";
                 type empty;
               }
             }
           }
         }
       }
       list term {
         key name;
         ordered-by user;
         description "Policy term";
         leaf name {
           type string;
         }
         uses apply-advanced;
         container from {
           description "Conditions to match the source of a route";
           uses apply-advanced;
           leaf instance {
             description "Routing protocol instance";
             type string;
           }
           leaf instance-any {
             description "Any routing protocol instance";
             type empty;
           }
           leaf-list instance-list {
             description "A list of routing protocol instances";
             type string;
           }
           leaf-list igp-instance {
             description "IGP instance";
             type string;
           }
           leaf igp-instance-regex {
             description "IGP instance name regular expression";
             type jt:regular-expression;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
               enum "inet-srte" {
                 description "IPv4 srtte family";
               }
               enum "inet6-srte" {
                 description "IPv6 srte family";
               }
               enum "inet-flow" {
                 description "IPv4 flow family";
               }
               enum "inet6-flow" {
                 description "IPv6 flow family";
               }
               enum "inet-vpn-flow" {
                 description "IPv4 vpn flow family";
               }
               enum "inet6-vpn-flow" {
                 description "IPv6 vpn flow family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
               enum "rib-export" {
                 description "RIB export clone routes";
               }
               enum "igmp" {
                 description "IGMP";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf bgp-srte-discriminator {
             description "Srte discriminator";
             type union {
               type uint32;
               type string {
                 pattern "<.*>|$.*";
               }
             }
           }
           leaf srte-color {
             description "Srte color";
             type union {
               type uint32;
               type string {
                 pattern "<.*>|$.*";
               }
             }
           }
           leaf programmed {
             description "API-programmed route";
             type empty;
           }
           list protocol-instance {
             key name;
             ordered-by user;
             description "To match protocol-instance";
             leaf name {
               type enumeration {
                 enum "aggregate" {
                   description "Aggregate routes";
                 }
                 enum "bgp" {
                   description "BGP";
                 }
                 enum "direct" {
                   description "Directly connected routes";
                 }
                 enum "dvmrp" {
                   description "Distance Vector Multicast Routing Protocol";
                 }
                 enum "isis" {
                   description "Intermediate System-to-Intermediate System";
                 }
                 enum "esis" {
                   description "End System-to-Intermediate System";
                 }
                 enum "l-isis" {
                   description "Labelled ISIS";
                 }
                 enum "l2circuit" {
                   description "Layer 2 circuits";
                 }
                 enum "l2vpn" {
                   description "Layer 2 MPLS virtual private networks";
                 }
                 enum "local" {
                   description "Local system addresses";
                 }
                 enum "ospf" {
                   description "Open Shortest Path First";
                 }
                 enum "ospf2" {
                   description "Open Shortest Path First Version 2";
                 }
                 enum "ospf3" {
                   description "Open Shortest Path First Version 3";
                 }
                 enum "l-ospf" {
                   description "Labelled OSPF";
                 }
                 enum "pim" {
                   description "Protocol Independent Multicast";
                 }
                 enum "rip" {
                   description "Routing Information Protocol";
                 }
                 enum "ripng" {
                   description "Routing Information Protocol next generation";
                 }
                 enum "static" {
                   description "Statically defined addresses";
                 }
                 enum "arp" {
                   description "Addresses learned from ARP";
                 }
                 enum "frr" {
                   description "Addresses created by Host Fast Re-route";
                 }
                 enum "mpls" {
                   description "Multiprotocol Label Switching";
                 }
                 enum "ldp" {
                   description "Label Distribution Protocol";
                 }
                 enum "rsvp" {
                   description "Resource Reservation Protocol";
                 }
                 enum "msdp" {
                   description "Multicast Source Discovery Protocol";
                 }
                 enum "route-target" {
                   description "Local route target VPN membership";
                 }
                 enum "access" {
                   description "Access server routes";
                 }
                 enum "access-internal" {
                   description "Internal routes to directly connected clients";
                 }
                 enum "anchor" {
                   description "Anchor routes connected to UEs";
                 }
                 enum "bgp-static" {
                   description "BGP static routes";
                 }
                 enum "vpls" {
                   description "Virtual Private LAN Service";
                 }
                 enum "evpn" {
                   description "Ethernet VPN Service";
                 }
                 enum "spring-te" {
                   description "SPRING Traffic-Engineered";
                 }
                 enum "bgp-ls-epe" {
                   description "Addresses created by BGP-LS egress TE";
                 }
                 enum "express-segments" {
                   description "Express-segment routes";
                 }
                 enum "rift" {
                   description "RIFT routes";
                 }
                 enum "l2-learned-host-routing" {
                   description "Layer2-learned host routes";
                 }
                 enum "srv6-isis" {
                   description "SRV6 ISIS";
                 }
                 enum "ari-ts" {
                   description "ARI TS routes";
                 }
                 enum "srv6" {
                   description "Segment Routing IPv6 local route";
                 }
                 enum "rib-export" {
                   description "RIB export clone routes";
                 }
                 enum "igmp" {
                   description "IGMP";
                 }
                 enum "any" {
                   description "Any route";
                 }
               }
             }
             uses apply-advanced;
             leaf-list protocol-instance-name {
               description "Protocol instance name";
               type string;
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           container validation-database-instance {
             presence "enable validation-database-instance";
             description "Name to identify a validation-state with DB name";
             uses apply-advanced;
             leaf database-name {
               description "Route Validation Database name to be looked at";
               type string;
             }
             leaf state {
               description "Name to identify a validation-state";
               type enumeration {
                 enum "valid" {
                   description "Match for valid database validation-state";
                 }
                 enum "invalid" {
                   description "Match for invalid database validation-state";
                 }
                 enum "unknown" {
                   description "Match for unknown database validation-state";
                 }
               }
               mandatory true;
             }
           }
           list nexthop-weight {
             key "choice-ident choice-value weight";
             ordered-by user;
             description "Weight of the gateway";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf weight {
               description "Weight of the gateway";
               type union {
                 type string {
                   pattern "<.*>|$.*";
                 }
                 type uint32 {
                   range "1 .. 65535";
                 }
               }
             }
             uses apply-advanced;
             choice weight_type {
               case case_1 {
                 leaf all-nexthop {
                   description "All the gateway weight should be matched";
                   type empty;
                 }
               }
             }
           }
           list nexthop-ecmp {
             key "choice-ident choice-value ecmp";
             ordered-by user;
             description "Qualify nexthop equal cost multipath gateways";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf ecmp {
               description "Number of equal cost multipath gateways";
               type union {
                 type string {
                   pattern "<.*>|$.*";
                 }
                 type uint32 {
                   range "1 .. 512";
                 }
               }
             }
             uses apply-advanced;
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf-list tag2 {
             ordered-by user;
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
           choice lsp-name-type {
             case case_1 {
               leaf lsp {
                 description "Label switched path name";
                 type string {
                 }
               }
             }
             case case_2 {
               leaf lsp-regex {
                 description "Label switched path name regular expression";
                 type string {
                 }
               }
             }
           }
           container source-routing-path {
             presence "enable source-routing-path";
             description "Spring-te lsp policy attributes";
             leaf name-regex {
               description "Spring-te lsp name regex";
               type string {
               }
             }
             leaf dest {
               description "Spring-te lsp IPV4/IPV6 destination without color";
               type jt:ipaddr;
             }
             leaf origin {
               description "Spring-te lsp origin address";
               type jt:ipaddr;
             }
             leaf tunnel-source {
               description "Spring-te lsp source protocol";
               type enumeration {
                 enum "pcep" {
                   description "Spring-te lsp src pcep";
                 }
                 enum "bgp" {
                   description "Spring-te lsp src bgp";
                 }
               }
             }
             leaf route-distinguisher {
               description "Spring-te lsp route distinguisher";
               type union {
                 type uint32;
                 type string {
                   pattern "<.*>|$.*";
                 }
               }
             }
             leaf color {
               description "Spring-te lsp color";
               type union {
                 type uint32;
                 type string {
                   pattern "<.*>|$.*";
                 }
               }
             }
           }
           list route-filter {
             key "address choice-ident choice-value";
             ordered-by user;
             description "List of routes to match";
             uses control_route_filter_type;
           }
           list source-address-filter {
             key "address choice-ident choice-value";
             ordered-by user;
             description "List of source addresses to match";
             uses control_source_address_filter_type;
           }
           list prefix-list {
             key name;
             ordered-by user;
             description "List of prefix-lists of routes to match";
             uses control_prefix_list_type;
           }
           list rib-list {
             key name;
             ordered-by user;
             description "List of routing-tables";
             uses control_rib_list_type;
           }
           list as-path-neighbors {
             key "list-type list-name";
             ordered-by user;
             description "List of peer AS to match";
             uses control_as_list_type;
           }
           list as-path-origins {
             key "list-type list-name";
             ordered-by user;
             description "List of originating AS to match";
             uses control_as_list_type;
           }
           list as-path-transits {
             key "list-type list-name";
             ordered-by user;
             description "List of originating AS to match";
             uses control_as_list_type;
           }
           list prefix-list-filter {
             key "list_name choice-ident choice-value";
             ordered-by user;
             description "List of prefix-list-filters to match";
             uses control_prefix_list_filter_type;
           }
           list route-filter-list {
             key name;
             ordered-by user;
             description "List of route-filter-lists of routes to match";
             uses control_route_filter_list_type;
           }
           list source-address-filter-list {
             key name;
             ordered-by user;
             description "List of source-address-filter-lists of routes to match";
             uses control_source_address_filter_list_type;
           }
           list rtf-prefix-list {
             key name;
             ordered-by user;
             description "List of rtf-prefix-lists of routes to match";
             uses control_rtf_prefix_list_type;
           }
           container multicast-scope {
             description "Multicast scope to match";
             choice scope-choice {
               case case_1 {
                 leaf node-local {
                   description "Node-local scope";
                   type empty;
                 }
               }
               case case_2 {
                 leaf link-local {
                   description "Link-local scope";
                   type empty;
                 }
               }
               case case_3 {
                 leaf site-local {
                   description "Site-local scope";
                   type empty;
                 }
               }
               case case_4 {
                 leaf organization-local {
                   description "Organization-local scope";
                   type empty;
                 }
               }
               case case_5 {
                 leaf global {
                   description "Global scope";
                   type empty;
                 }
               }
               case case_6 {
                 leaf scope_value {
                   description "Scope value";
                   type union {
                     type string {
                       pattern "<.*>|$.*";
                     }
                     type uint32 {
                       range "0 .. 15";
                     }
                   }
                 }
               }
             }
             choice scope-operator {
               case case_1 {
                 leaf orhigher {
                   description "Match higher values";
                   type empty;
                 }
               }
               case case_2 {
                 leaf orlower {
                   description "Match lower values";
                   type empty;
                 }
               }
             }
           }
           leaf aggregate-contributor {
             description "Match more specifics of an aggregate";
             type empty;
           }
           leaf state {
             description "Route state";
             type enumeration {
               enum "active" {
                 description "Active route";
               }
               enum "inactive" {
                 description "Inactive route";
               }
             }
           }
           leaf-list tunnel-type {
             ordered-by user;
             description "Tunnel type";
             type enumeration {
               enum "gre" {
                 description "GRE tunnel";
               }
               enum "udp" {
                 description "UDP tunnel";
               }
               enum "ipip" {
                 description "IPIP tunnel";
               }
             }
           }
           leaf route-type {
             description "Route type";
             type enumeration {
               enum "internal" {
                 description "Internal route";
               }
               enum "external" {
                 description "External route";
               }
             }
           }
           leaf-list nlri-route-type {
             ordered-by user;
             description "Route type from NLRI";
             type union {
               type string {
                 pattern "<.*>|$.*";
               }
               type uint32 {
                 range "1 .. 10";
               }
             }
           }
           leaf-list evpn-tag {
             ordered-by user;
             description "Tag in EVPN Route";
             type union {
               type string {
                 pattern "<.*>|$.*";
               }
               type uint32 {
                 range "0 .. 4294967295";
               }
             }
           }
           leaf-list evpn-esi {
             ordered-by user;
             description "ESI in EVPN Route";
             type string;
           }
           list mac-filter-list {
             key name;
             ordered-by user;
             description "List of mac-filter-list macs to match";
             uses control_mac_address_filter_list_type;
           }
           leaf evpn-mac-route {
             description "EVPN Mac Route type";
             type enumeration {
               enum "mac-only" {
                 description "MAC route";
               }
               enum "mac-ipv4" {
                 description "MAC IPV4 route";
               }
               enum "mac-ipv6" {
                 description "MAC IPV6 route";
               }
             }
           }
           leaf-list bridge-domain-id {
             ordered-by user;
             description "Bridge Domain Identifier (Vlan or VNI)";
             type union {
               type string {
                 pattern "<.*>|$.*";
               }
               type uint32 {
                 range "0 .. 4294967295";
               }
             }
           }
           leaf next-hop-type {
             description "Next-hop type";
             type enumeration {
               enum "merged" {
                 description "Merged next hop";
               }
             }
           }
           leaf-list condition {
             ordered-by user;
             description "Condition to match on";
             type string;
           }
           container route-target-prefix-count {
             description "Limit number of BGP prefixes with a 'Route Target' set";
             presence "enable route-target-prefix-count";
             uses prefix_count_type;
           }
           list community-count {
             key name;
             ordered-by user;
             description "Number of BGP communities";
             uses community_count_type;
           }
           list large-community-count {
             key name;
             ordered-by user;
             description "Number of Large BGP communities";
             uses community_count_type;
           }
           list as-path-unique-count {
             key name;
             ordered-by user;
             description "Number of unique BGP ASes excluding confederations";
             uses as-path-unique-count-type;
           }
           list as-path-calc-length {
             key name;
             ordered-by user;
             description "Number of BGP ASes excluding confederations";
             uses as-path-calc-length-type;
           }
           container traffic-engineering {
             presence "enable traffic-engineering";
             description "Traffic-Engineering related parameters";
             uses apply-advanced;
             leaf-list protocol {
               ordered-by user;
               description "Protocol that originated the entry";
               type enumeration {
                 enum "direct" {
                   description "Directly originated";
                 }
                 enum "ospf" {
                   description "OSPF originated";
                 }
                 enum "isis-level-1" {
                   description "ISIS level-1 originated";
                 }
                 enum "isis-level-2" {
                   description "ISIS level-2 originated";
                 }
                 enum "spring-te" {
                   description "SPRING-TE originated";
                 }
                 enum "static" {
                   description "Statically originated";
                 }
                 enum "unknown" {
                   description "Originated by unknown sources";
                 }
               }
             }
             container node {
               presence "enable node";
               description "Node-related parameters";
               uses apply-advanced;
               leaf as {
                 description "AS number";
                 type string {
                 }
               }
               leaf node-type {
                 description "Real or pseudo-node";
                 type enumeration {
                   enum "router" {
                     description "Real node";
                   }
                   enum "pseudo-node" {
                     description "Pseudo-node";
                   }
                 }
               }
               leaf router-id {
                 description "IP prefix to match the router-id against";
                 type jt:ipprefix;
               }
               leaf sys-id {
                 description "ISO address of the node";
                 type jt:sysid;
               }
             }
             container ipv4-prefix {
               presence "enable ipv4-prefix";
               description "IPV4 prefix-related parameters";
               uses apply-advanced;
               leaf as {
                 description "AS number";
                 type string {
                 }
               }
               leaf router-id {
                 description "IP prefix to match the router-id against";
                 type jt:ipprefix;
               }
               leaf prefix {
                 description "IP prefix to match against";
                 type jt:ipprefix;
               }
               leaf sys-id {
                 description "ISO address of the node";
                 type jt:sysid;
               }
             }
             container ipv6-prefix {
               presence "enable ipv6-prefix";
               description "IPV6 prefix related parameters";
               uses apply-advanced;
               leaf as {
                 description "AS number";
                 type string {
                 }
               }
               leaf router-id {
                 description "IPv6 prefix to match the router-id against";
                 type jt:ipprefix;
               }
               leaf prefix {
                 description "IPv6 prefix to match against";
                 type jt:ipv6prefix;
               }
               leaf sys-id {
                 description "ISO address of the node";
                 type jt:sysid;
               }
             }
             container srv6-sid {
               presence "enable srv6-sid";
               description "SRV6 SID related parameters";
               uses apply-advanced;
               leaf as {
                 description "AS number";
                 type string {
                 }
               }
               leaf router-id {
                 description "SRv6 SID to match the router-id against";
                 type jt:ipprefix;
               }
               leaf sid {
                 description "SRv6 SID to match against";
                 type jt:ipv6addr;
               }
               leaf sys-id {
                 description "ISO address of the node";
                 type jt:sysid;
               }
             }
             container spring-te {
               presence "enable spring-te";
               description "SPRING-TE policy related parameters";
               uses apply-advanced;
               leaf node-as {
                 description "Node AS number";
                 type string {
                 }
               }
               leaf router-id {
                 description "IP prefix to match against the node for the SPRING TE policy";
                 type jt:ipprefix;
               }
               leaf color {
                 description "Color of the SPRING-TE policy candidate path";
                 type union {
                   type uint32;
                   type string {
                     pattern "<.*>|$.*";
                   }
                 }
               }
               leaf discriminator {
                 description "Discriminator of the SPRING-TE policy candidate path";
                 type union {
                   type uint32;
                   type string {
                     pattern "<.*>|$.*";
                   }
                 }
               }
               leaf endpoint {
                 description "Endpoint of the SPRING-TE policy candidate path";
                 type jt:ipaddr;
               }
               leaf protocol-origin {
                 description "Protocol originating the SPRING-TE policy candidate path";
                 type enumeration {
                   enum "bgp" {
                     description "SPRING-TE policy candidate path originated by BGP";
                   }
                   enum "cli" {
                     description "SPRING-TE policy candidate path originated by cli";
                   }
                   enum "pcep" {
                     description "SPRING-TE policy candidate path originated by PCEP";
                   }
                 }
               }
               leaf origin-as {
                 description "AS number of the node creating the SPRING-TE policy candidate path";
                 type string {
                 }
               }
               leaf origin-addr {
                 description "Address of the node originating the SPRING-TE policy candidate path";
                 type jt:ipaddr;
               }
             }
             container link {
               presence "enable link";
               description "Link-related parameters";
               uses apply-advanced;
               container from {
                 description "Specify parameter of the 'from' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
               container to {
                 description "Specify parameters of the 'to' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
             }
             leaf identifier {
               description "BGP-TE identifier";
               type union {
                 type string {
                   pattern "<.*>|$.*";
                 }
                 type uint64 {
                   range "2 .. 18446744073709551615";
                 }
               }
             }
           }
           leaf-list route-distinguisher {
             ordered-by user;
             description "Name of the route-distinguisher";
             type string;
           }
           leaf prefix-segment {
             description "Prefix segment present in route extended data";
             type empty;
           }
           list flowspec-attribute {
             key name;
             ordered-by user;
             description "List of flowspec attributes to match";
             uses control_flowspec_attribute_type;
           }
         }
         container to {
           description "Conditions to match the destination of a route";
           uses apply-advanced;
           leaf instance {
             description "Routing protocol instance";
             type string;
           }
           leaf instance-any {
             description "Any routing protocol instance";
             type empty;
           }
           leaf-list instance-list {
             description "A list of routing protocol instances";
             type string;
           }
           leaf-list igp-instance {
             description "IGP instance";
             type string;
           }
           leaf igp-instance-regex {
             description "IGP instance name regular expression";
             type jt:regular-expression;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
               enum "inet-srte" {
                 description "IPv4 srtte family";
               }
               enum "inet6-srte" {
                 description "IPv6 srte family";
               }
               enum "inet-flow" {
                 description "IPv4 flow family";
               }
               enum "inet6-flow" {
                 description "IPv6 flow family";
               }
               enum "inet-vpn-flow" {
                 description "IPv4 vpn flow family";
               }
               enum "inet6-vpn-flow" {
                 description "IPv6 vpn flow family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
               enum "rib-export" {
                 description "RIB export clone routes";
               }
               enum "igmp" {
                 description "IGMP";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf bgp-srte-discriminator {
             description "Srte discriminator";
             type union {
               type uint32;
               type string {
                 pattern "<.*>|$.*";
               }
             }
           }
           leaf srte-color {
             description "Srte color";
             type union {
               type uint32;
               type string {
                 pattern "<.*>|$.*";
               }
             }
           }
           leaf programmed {
             description "API-programmed route";
             type empty;
           }
           list protocol-instance {
             key name;
             ordered-by user;
             description "To match protocol-instance";
             leaf name {
               type enumeration {
                 enum "aggregate" {
                   description "Aggregate routes";
                 }
                 enum "bgp" {
                   description "BGP";
                 }
                 enum "direct" {
                   description "Directly connected routes";
                 }
                 enum "dvmrp" {
                   description "Distance Vector Multicast Routing Protocol";
                 }
                 enum "isis" {
                   description "Intermediate System-to-Intermediate System";
                 }
                 enum "esis" {
                   description "End System-to-Intermediate System";
                 }
                 enum "l-isis" {
                   description "Labelled ISIS";
                 }
                 enum "l2circuit" {
                   description "Layer 2 circuits";
                 }
                 enum "l2vpn" {
                   description "Layer 2 MPLS virtual private networks";
                 }
                 enum "local" {
                   description "Local system addresses";
                 }
                 enum "ospf" {
                   description "Open Shortest Path First";
                 }
                 enum "ospf2" {
                   description "Open Shortest Path First Version 2";
                 }
                 enum "ospf3" {
                   description "Open Shortest Path First Version 3";
                 }
                 enum "l-ospf" {
                   description "Labelled OSPF";
                 }
                 enum "pim" {
                   description "Protocol Independent Multicast";
                 }
                 enum "rip" {
                   description "Routing Information Protocol";
                 }
                 enum "ripng" {
                   description "Routing Information Protocol next generation";
                 }
                 enum "static" {
                   description "Statically defined addresses";
                 }
                 enum "arp" {
                   description "Addresses learned from ARP";
                 }
                 enum "frr" {
                   description "Addresses created by Host Fast Re-route";
                 }
                 enum "mpls" {
                   description "Multiprotocol Label Switching";
                 }
                 enum "ldp" {
                   description "Label Distribution Protocol";
                 }
                 enum "rsvp" {
                   description "Resource Reservation Protocol";
                 }
                 enum "msdp" {
                   description "Multicast Source Discovery Protocol";
                 }
                 enum "route-target" {
                   description "Local route target VPN membership";
                 }
                 enum "access" {
                   description "Access server routes";
                 }
                 enum "access-internal" {
                   description "Internal routes to directly connected clients";
                 }
                 enum "anchor" {
                   description "Anchor routes connected to UEs";
                 }
                 enum "bgp-static" {
                   description "BGP static routes";
                 }
                 enum "vpls" {
                   description "Virtual Private LAN Service";
                 }
                 enum "evpn" {
                   description "Ethernet VPN Service";
                 }
                 enum "spring-te" {
                   description "SPRING Traffic-Engineered";
                 }
                 enum "bgp-ls-epe" {
                   description "Addresses created by BGP-LS egress TE";
                 }
                 enum "express-segments" {
                   description "Express-segment routes";
                 }
                 enum "rift" {
                   description "RIFT routes";
                 }
                 enum "l2-learned-host-routing" {
                   description "Layer2-learned host routes";
                 }
                 enum "srv6-isis" {
                   description "SRV6 ISIS";
                 }
                 enum "ari-ts" {
                   description "ARI TS routes";
                 }
                 enum "srv6" {
                   description "Segment Routing IPv6 local route";
                 }
                 enum "rib-export" {
                   description "RIB export clone routes";
                 }
                 enum "igmp" {
                   description "IGMP";
                 }
                 enum "any" {
                   description "Any route";
                 }
               }
             }
             uses apply-advanced;
             leaf-list protocol-instance-name {
               description "Protocol instance name";
               type string;
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           container validation-database-instance {
             presence "enable validation-database-instance";
             description "Name to identify a validation-state with DB name";
             uses apply-advanced;
             leaf database-name {
               description "Route Validation Database name to be looked at";
               type string;
             }
             leaf state {
               description "Name to identify a validation-state";
               type enumeration {
                 enum "valid" {
                   description "Match for valid database validation-state";
                 }
                 enum "invalid" {
                   description "Match for invalid database validation-state";
                 }
                 enum "unknown" {
                   description "Match for unknown database validation-state";
                 }
               }
               mandatory true;
             }
           }
           list nexthop-weight {
             key "choice-ident choice-value weight";
             ordered-by user;
             description "Weight of the gateway";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf weight {
               description "Weight of the gateway";
               type union {
                 type string {
                   pattern "<.*>|$.*";
                 }
                 type uint32 {
                   range "1 .. 65535";
                 }
               }
             }
             uses apply-advanced;
             choice weight_type {
               case case_1 {
                 leaf all-nexthop {
                   description "All the gateway weight should be matched";
                   type empty;
                 }
               }
             }
           }
           list nexthop-ecmp {
             key "choice-ident choice-value ecmp";
             ordered-by user;
             description "Qualify nexthop equal cost multipath gateways";
             leaf choice-ident {
               type enumeration {
                 enum "equal" {
                 }
                 enum "greater-than" {
                 }
                 enum "less-than" {
                 }
                 enum "greater-than-equal" {
                 }
                 enum "less-than-equal" {
                 }
               }
             }
             leaf choice-value {
               type string;
             }
             leaf ecmp {
               description "Number of equal cost multipath gateways";
               type union {
                 type string {
                   pattern "<.*>|$.*";
                 }
                 type uint32 {
                   range "1 .. 512";
                 }
               }
             }
             uses apply-advanced;
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf-list tag2 {
             ordered-by user;
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
           choice lsp-name-type {
             case case_1 {
               leaf lsp {
                 description "Label switched path name";
                 type string {
                 }
               }
             }
             case case_2 {
               leaf lsp-regex {
                 description "Label switched path name regular expression";
                 type string {
                 }
               }
             }
           }
           container source-routing-path {
             presence "enable source-routing-path";
             description "Spring-te lsp policy attributes";
             leaf name-regex {
               description "Spring-te lsp name regex";
               type string {
               }
             }
             leaf dest {
               description "Spring-te lsp IPV4/IPV6 destination without color";
               type jt:ipaddr;
             }
             leaf origin {
               description "Spring-te lsp origin address";
               type jt:ipaddr;
             }
             leaf tunnel-source {
               description "Spring-te lsp source protocol";
               type enumeration {
                 enum "pcep" {
                   description "Spring-te lsp src pcep";
                 }
                 enum "bgp" {
                   description "Spring-te lsp src bgp";
                 }
               }
             }
             leaf route-distinguisher {
               description "Spring-te lsp route distinguisher";
               type union {
                 type uint32;
                 type string {
                   pattern "<.*>|$.*";
                 }
               }
             }
             leaf color {
               description "Spring-te lsp color";
               type union {
                 type uint32;
                 type string {
                   pattern "<.*>|$.*";
                 }
               }
             }
           }
         }
         container then {
           description "Actions to take if 'from' and 'to' conditions match";
           uses apply-advanced;
           container metric {
             description "Metric value";
             uses apply-advanced;
             choice metric_action {
               case case_1 {
                 leaf metric {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
               case case_4 {
                 container igp {
                   presence "enable igp";
                   description "Track the IGP metric (BGP only)";
                   leaf metric_offset {
                     description "Metric offset for MED";
                     type union {
                       type int32;
                       type string {
                         pattern "<.*>|$.*";
                       }
                     }
                   }
                 }
               }
               case case_5 {
                 container minimum-igp {
                   presence "enable minimum-igp";
                   description "Track the minimum IGP metric (BGP only)";
                   leaf metric_offset {
                     description "Metric offset for MED";
                     type union {
                       type int32;
                       type string {
                         pattern "<.*>|$.*";
                       }
                     }
                   }
                 }
               }
               case case_6 {
                 container expression {
                   description "Calculate value based on route metric and metric2";
                   uses metric_expression_type;
                 }
               }
               case case_7 {
                 leaf aigp {
                   description "Use aigp, if it exists, to set the IGP metric";
                   type empty;
                 }
               }
               case case_8 {
                 container effective-aigp {
                   presence "enable effective-aigp";
                   description "Track the effective AIGP metric (BGP only)";
                   leaf metric_offset {
                     description "Metric offset for MED";
                     type union {
                       type int32;
                       type string {
                         pattern "<.*>|$.*";
                       }
                     }
                   }
                 }
               }
               case case_9 {
                 container minimum-effective-aigp {
                   presence "enable minimum-effective-aigp";
                   description "Track the minimum effective AIGP metric (BGP only)";
                   leaf metric_offset {
                     description "Metric offset for MED";
                     type union {
                       type int32;
                       type string {
                         pattern "<.*>|$.*";
                       }
                     }
                   }
                 }
               }
             }
           }
           container metric2 {
             description "Metric value 2";
             uses apply-advanced;
             choice metric_action {
               case case_1 {
                 leaf metric2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric3 {
             description "Metric value 3";
             uses apply-advanced;
             choice metric_action {
               case case_1 {
                 leaf metric3 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric4 {
             description "Metric value 4";
             uses apply-advanced;
             choice metric_action {
               case case_1 {
                 leaf metric4 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag {
             description "Tag string";
             uses apply-advanced;
             choice metric_action {
               case case_1 {
                 leaf tag {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag2 {
             description "Tag string 2";
             uses apply-advanced;
             choice metric_action {
               case case_1 {
                 leaf tag2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference {
             description "Preference value";
             uses apply-advanced;
             choice metric_action {
               case case_1 {
                 leaf preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference2 {
             description "Preference value 2";
             uses apply-advanced;
             choice metric_action {
               case case_1 {
                 leaf preference2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color {
             description "Color (preference) value";
             uses apply-advanced;
             choice metric_action {
               case case_1 {
                 leaf color {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color2 {
             description "Color (preference) value 2";
             uses apply-advanced;
             choice metric_action {
               case case_1 {
                 leaf color2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container local-preference {
             description "Local preference associated with a route";
             uses apply-advanced;
             choice metric_action {
               case case_1 {
                 leaf local-preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container credibility {
             description "TED credibility value for entries from BGP-TE";
             uses apply-advanced;
             choice metric_action {
               case case_1 {
                 leaf credibility {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           leaf priority {
             description "Set priority for route installation";
             type enumeration {
               enum "high" {
                 description "Set priority to high";
               }
               enum "medium" {
                 description "Set priority to medium";
               }
               enum "low" {
                 description "Set priority to low";
               }
             }
           }
           container prefix-segment {
             description "Set prefix segment attributes";
             uses apply-advanced;
             list algorithm {
               key name;
               description "Set prefix segment attributes for strict/flex algorithm ";
               max-elements 15;
               leaf name {
                 description "Set prefix segment for strict/flex algorithm";
                 type union {
                   type string {
                     pattern "<.*>|$.*";
                   }
                   type uint32 {
                     range "1 .. 255";
                   }
                 }
                 mandatory true;
               }
               leaf index {
                 description "Set prefix segment index id";
                 type union {
                   type string {
                     pattern "<.*>|$.*";
                   }
                   type uint32 {
                     range "0 .. 1048575";
                   }
                 }
                 mandatory true;
               }
               leaf node-segment {
                 description "Set node segment flag for this prefix segment";
                 type empty;
               }
             }
             leaf index {
               description "Set prefix segment index id";
               type union {
                 type string {
                   pattern "<.*>|$.*";
                 }
                 type uint32 {
                   range "0 .. 1048575";
                 }
               }
             }
             leaf node-segment {
               description "Set node segment flag for default prefix segment";
               type empty;
             }
             leaf redistribute {
               description "Redistribute prefix-segment from route entry";
               type empty;
             }
           }
           leaf label-allocation {
             description "Set label allocation mode";
             type enumeration {
               enum "per-table" {
                 description "Set per-table label allocation mode";
               }
               enum "per-nexthop" {
                 description "Set per-nexthop label allocation mode";
               }
               enum "per-table-localize" {
                 description "Set per-table-localize label allocation mode";
               }
             }
           }
           container add-path {
             description "Set BGP add-path attributes";
             leaf send-count {
               description "Number of add-paths sent";
               type union {
                 type string {
                   pattern "<.*>|$.*";
                 }
                 type uint32 {
                   range "2 .. 64";
                 }
               }
             }
           }
           leaf fib-install-priority {
             description "Set Fib Instalation priority of a route";
             type enumeration {
               enum "high" {
                 description "Set Fib install priority  to high";
               }
               enum "medium" {
                 description "Set Fib install priority to medium ";
               }
             }
           }
           leaf validation-state {
             description "Set validation-state of a route";
             type enumeration {
               enum "valid" {
                 description "Set validaton-state to valid";
               }
               enum "invalid" {
                 description "Set validation-state to invalid";
               }
               enum "unknown" {
                 description "Set validation-state to unknown";
               }
             }
           }
           leaf origin {
             description "BGP path origin";
             type enumeration {
               enum "igp" {
                 description "Path originated in the local IGP";
               }
               enum "egp" {
                 description "Path originated in another AS";
               }
               enum "incomplete" {
                 description "Path was learned by some other means";
               }
             }
           }
           container srv6 {
             description "Configure SID with 128 bit address";
             leaf sid {
               description "IPv6 Address";
               type jt:ipv6addr;
             }
             leaf locator {
               description "Name of locator";
               type string;
             }
             choice locator_type {
               case case_1 {
                 leaf micro-dt4-sid {
                   description "Micro SID type dt4";
                   type empty;
                 }
               }
               case case_2 {
                 leaf micro-dt6-sid {
                   description "Micro SID type dt6";
                   type empty;
                 }
               }
               case case_3 {
                 leaf micro-dt46-sid {
                   description "Micro SID type dt46";
                   type empty;
                 }
               }
               case case_4 {
                 leaf end-dtm-sid {
                   description "SID type dtm";
                   type empty;
                 }
               }
             }
           }
           container aigp-originate {
             presence "enable aigp-originate";
             description "Originate a BGP AIGP attribute";
             leaf effective-metric {
               description "Metric associated with non-BGP route";
               type empty;
             }
             leaf distance {
               description "AIGP distance";
               type union {
                 type uint32;
                 type string {
                   pattern "<.*>|$.*";
                 }
               }
             }
           }
           container aigp-adjust {
             description "Adjust a BGP AIGP attribute";
             choice math-op {
               case case_1 {
                 leaf add {
                   type empty;
                 }
               }
               case case_2 {
                 leaf subtract {
                   type empty;
                 }
               }
               case case_3 {
                 leaf multiply {
                   type empty;
                 }
               }
               case case_4 {
                 leaf divide {
                   type empty;
                 }
               }
             }
             choice adjust-value {
               case case_1 {
                 leaf user-value {
                   description "Adjustment value";
                   type union {
                     type uint64;
                     type string {
                       pattern "<.*>|$.*";
                     }
                   }
                 }
               }
               case case_2 {
                 leaf distance-to-protocol-nexthop {
                   description "Metric2";
                   type empty;
                 }
               }
             }
           }
           list community {
             key "choice-ident choice-value community-name";
             ordered-by user;
             description "BGP community properties associated with a route";
             leaf choice-ident {
               type enumeration {
                 enum "equal-literal" {
                 }
                 enum "set" {
                 }
                 enum "plus-literal" {
                 }
                 enum "add" {
                 }
                 enum "minus-literal" {
                 }
                 enum "delete" {
                 }
               }
             }
             leaf choice-value {
               type string;
             }
             leaf community-name {
               description "Name to identify a BGP community";
               type string;
             }
           }
           list inline-community {
             key "choice-ident choice-value inline-community-member";
             ordered-by user;
             description "Set BGP community properties associated with a route inline";
             leaf choice-ident {
               type enumeration {
                 enum "equal-literal" {
                 }
                 enum "set" {
                 }
                 enum "plus-literal" {
                 }
                 enum "add" {
                 }
                 enum "minus-literal" {
                 }
                 enum "delete" {
                 }
               }
             }
             leaf choice-value {
               type string;
             }
             leaf inline-community-member {
               description "Inline BGP community members";
               type string;
             }
           }
           list tunnel-attribute {
             key "choice-ident choice-value tunnel-attribute-name";
             ordered-by user;
             description "BGP tunnel attribute associated with a route";
             leaf choice-ident {
               type enumeration {
                 enum "set" {
                 }
                 enum "remove" {
                 }
               }
             }
             leaf choice-value {
               type string;
             }
             leaf tunnel-attribute-name {
               description "Name of a tunnel attribute , or 'all'";
               type string;
             }
           }
           container assisted-replication {
             presence "enable assisted-replication";
             description "Deterministic AR replicator knobs";
             uses apply-advanced;
             leaf-list replicator-ip {
               description "Set deterministic AR replicator ip for the flow";
               type jt:ipaddr;
               max-elements 1;
             }
             leaf strict {
               description "Do not use any other replicator";
               type empty;
             }
             leaf-list fallback-replicator-ip {
               description "Set Fallback replicator-ip";
               type jt:ipaddr;
               max-elements 1;
             }
           }
           leaf damping {
             description "Define BGP route flap damping parameters";
             type string;
           }
           container aggregate-bandwidth {
             presence "enable aggregate-bandwidth";
             description "Advertise aggregate outbound link bandwidth";
             uses apply-advanced;
             choice transitive-type {
               case case_1 {
                 leaf transitive {
                   description "Transitive flag for link bandwidth";
                   type empty;
                 }
               }
               case case_2 {
                 leaf non-transitive {
                   description "Non-Transitive flag for link bandwidth";
                   type empty;
                 }
               }
             }
             leaf divide-equal {
               description "Divide-equal";
               type empty;
             }
           }
           container aggregate-weight {
             presence "enable aggregate-weight";
             description "Advertise aggregate outbound count";
             uses apply-advanced;
             leaf multiplier {
               description "Adjust the aggregate-weight by multiplying it with a given value, default is 1";
               default "1";
               type union {
                 type string {
                   pattern "<.*>|$.*";
                 }
                 type uint16 {
                   range "1 .. 32";
                 }
               }
             }
           }
           container auto-link-bandwidth {
             presence "enable auto-link-bandwidth";
             description "Auto sense and attach link bandwidth community";
             uses apply-advanced;
             choice transitive-type {
               case case_1 {
                 leaf transitive {
                   description "Transitive flag for link bandwidth";
                   type empty;
                 }
               }
               case case_2 {
                 leaf non-transitive {
                   description "Non-Transitive flag for link bandwidth";
                   type empty;
                 }
               }
             }
           }
           leaf limit-bandwidth {
             description "Limit advertised aggregate outbound link bandwidth";
             type union {
               type uint64;
               type string {
                 pattern "<.*>|$.*";
               }
             }
           }
           leaf no-entropy-label-capability {
             description "Don't advertise entropy label capability";
             type empty;
           }
           leaf as-path-prepend {
             description "Prepend AS numbers to an AS path (BGP only)";
             type string;
           }
           leaf as-path-replace {
             description "Replace sequence of AS numbers/'private' with local AS";
             type string;
           }
           container as-path-expand {
             description "Prepend AS numbers prior to adding local-as (BGP only)";
             choice aspath_exp_value {
               case case_1 {
                 container last-as {
                   presence "enable last-as";
                   description "Prepend last AS";
                   leaf count {
                     description "Repeat count";
                     type union {
                       type string {
                         pattern "<.*>|$.*";
                       }
                       type uint32 {
                         range "1 .. 32";
                       }
                     }
                   }
                 }
               }
               case case_2 {
                 container local-as {
                   presence "enable local-as";
                   description "Prepend local AS";
                   leaf count {
                     description "Repeat count";
                     type union {
                       type string {
                         pattern "<.*>|$.*";
                       }
                       type uint32 {
                         range "1 .. 32";
                       }
                     }
                   }
                 }
               }
               case case_3 {
                 container asn {
                   presence "enable asn";
                   description "Prepend AS";
                   uses apply-advanced;
                   leaf as-value {
                     description "AS value";
                     type union {
                       type uint32;
                       type string {
                         pattern "<.*>|$.*";
                       }
                     }
                     mandatory true;
                   }
                   leaf count {
                     description "Repeat count";
                     type union {
                       type string {
                         pattern "<.*>|$.*";
                       }
                       type uint32 {
                         range "1 .. 32";
                       }
                     }
                   }
                 }
               }
               case case_4 {
                 leaf aspath {
                   description "AS path string";
                   type string;
                 }
               }
             }
           }
           container next-hop {
             description "Set the address of the next-hop router";
             choice nexthop_value {
               case case_1 {
                 leaf self {
                   description "Use a local address as the next-hop address";
                   type empty;
                 }
               }
               case case_2 {
                 leaf peer-address {
                   description "Use the remote peer address as the next-hop address";
                   type empty;
                 }
               }
               case case_3 {
                 leaf address {
                   description "Next-hop address";
                   type jt:ipaddr;
                 }
               }
               case case_4 {
                 leaf reject {
                   description "Use a reject next hop";
                   type empty;
                 }
               }
               case case_5 {
                 leaf discard {
                   description "Use a discard next hop";
                   type empty;
                 }
               }
               case case_6 {
                 leaf next-table {
                   description "Perform a forwarding lookup in the specified table";
                   type string;
                 }
               }
             }
             leaf no-resolution {
               description "Don't resolve nexthop reachability";
               type empty;
             }
           }
           container install-nexthop {
             description "Choose the next hop to be used for forwarding";
             choice strict_type {
               case case_1 {
                 leaf strict {
                   description "Do not use any other available next hops";
                   type empty;
                 }
               }
               case case_2 {
                 leaf strict-named-lsp {
                   description "Do not use any other non-lsp next hops";
                   type empty;
                 }
               }
             }
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
             container except {
               description "Do not choose to install matching next hops";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
                 case case_8 {
                   leaf macsec-interfaces {
                     description "Next-hop for MACsec interfaces";
                     type empty;
                   }
                 }
               }
               container fallback {
                 description "Backup option";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                   case case_8 {
                     leaf macsec-interfaces {
                       description "Next-hop for MACsec interfaces";
                       type empty;
                     }
                   }
                 }
                 container except {
                   description "Do not choose to install matching next hops";
                   uses apply-advanced;
                   choice nexthop-value {
                     case case_1 {
                       leaf-list lsp {
                         ordered-by user;
                         description "Next-hop LSP name";
                         type string;
                       }
                     }
                     case case_2 {
                       leaf-list lsp-regex {
                         ordered-by user;
                         description "Next-hop LSP name regular expression";
                         type string;
                       }
                     }
                     case case_3 {
                       leaf-list static-lsp {
                         ordered-by user;
                         description "Next-hop static LSP name";
                         type string;
                       }
                     }
                     case case_4 {
                       leaf-list static-lsp-regex {
                         ordered-by user;
                         description "Next-hop static LSP name regular expression";
                         type string;
                       }
                     }
                     case case_5 {
                       leaf non-lsp-nexthop {
                         description "Next-hop with non-lsp";
                         type empty;
                       }
                     }
                     case case_6 {
                       leaf non-labelled-nexthop {
                         description "Next-hop without tag";
                         type empty;
                       }
                     }
                     case case_7 {
                       leaf overlay-vxlan-interfaces {
                         description "Next-hop for vxlan interfaces";
                         type empty;
                       }
                     }
                     case case_8 {
                       leaf macsec-interfaces {
                         description "Next-hop for MACsec interfaces";
                         type empty;
                       }
                     }
                   }
                 }
               }
             }
             container fallback {
               description "Backup option ";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
                 case case_8 {
                   leaf macsec-interfaces {
                     description "Next-hop for MACsec interfaces";
                     type empty;
                   }
                 }
               }
               container except {
                 description "Do not choose to install matching next hops";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                   case case_8 {
                     leaf macsec-interfaces {
                       description "Next-hop for MACsec interfaces";
                       type empty;
                     }
                   }
                 }
               }
             }
           }
           leaf trace {
             description "Log matches to a trace file";
             type empty;
           }
           container external {
             presence "enable external";
             description "External route";
             uses apply-advanced;
             leaf type {
               description "OSPF external metric type";
               type union {
                 type string {
                   pattern "<.*>|$.*";
                 }
                 type int32 {
                   range "1 .. 2";
                 }
               }
             }
             leaf nssa-only {
               description "Clear P-bit on lsa type 7";
               type empty;
             }
           }
           container load-balance {
             description "Type of load balancing in forwarding table";
             choice load_balance_type {
               case case_1 {
                 leaf per-packet {
                   description "Load balance on a per-packet basis deprecated, use per-flow instead";
                   type empty;
                 }
               }
               case case_2 {
                 leaf per-flow {
                   description "Load balance on a per-flow basis";
                   type empty;
                 }
               }
               case case_3 {
               }
               case case_4 {
               }
               case case_5 {
                 leaf consistent-hash {
                   description "Give a prefix consistent load-balancing";
                   type empty;
                 }
               }
               case case_6 {
               }
               case case_7 {
               }
               case case_8 {
               }
               case case_9 {
               }
               case case_10 {
               }
               case case_11 {
               }
             }
           }
           container advertise-locator {
             presence "enable advertise-locator";
             description "Advertise SRv6 Locator";
             uses apply-advanced;
             leaf internal {
               description "Advertise locator as Interal route";
               type empty;
             }
           }
           leaf set-down-bit {
             description "Set down bit";
             type empty;
           }
           leaf analyze {
             description "Send to registered controllers for analysis";
             type empty;
           }
           leaf class {
             description "Set class-of-service parameters";
             type string;
           }
           leaf destination-class {
             description "Set destination class in forwarding table";
             type string;
           }
           leaf source-class {
             description "Set source class in forwarding table";
             type string;
           }
           leaf forwarding-class {
             description "Set source or destination class in forwarding table";
             type string;
           }
           container map-to-interface {
             description "Set output logical interface";
             choice map_to_interface_value {
               case case_1 {
                 leaf self {
                   description "Map the interface to itself";
                   type empty;
                 }
               }
               case case_2 {
                 leaf interface {
                   description "Output logical interface";
                   type union {
                     type jt:interface-name;
                     type string {
                       pattern "<.*>|$.*";
                     }
                   }
                 }
               }
             }
           }
           leaf-list ssm-source {
             ordered-by user;
             description "List of Sources for SSM mapping";
             type jt:ipaddr;
           }
           container p2mp-lsp-root {
             description "P2mp lsp root address";
             uses apply-advanced;
             leaf address {
               description "Ipv4 root address";
               type jt:ipv4addr;
             }
           }
           leaf cos-next-hop-map {
             description "Set CoS-based next-hop map in forwarding table";
             type string;
           }
           leaf dynamic-tunnel-attributes {
             description "Choose the dynamic tunnel attributes used for forwarding";
             type string;
           }
           leaf tunnel-end-point-address {
             description "Set tunnel end-point address of tunnel";
             type jt:ipaddr;
           }
           leaf selected-mldp-egress {
             description "This node should act as egress node for MLDP inband signalling";
             type empty;
           }
           leaf mhop-bfd-port {
             description "Use port number 4784 for MPLS-BFD as per RFC5884";
             type empty;
           }
           leaf no-backup {
             description "This prefix should not have backup";
             type empty;
           }
           leaf default-action {
             description "Set default policy action";
             type enumeration {
               enum "accept" {
                 description "Accept a route";
               }
               enum "reject" {
                 description "Reject a route";
               }
             }
           }
           leaf next {
             description "Skip to next policy or term";
             type enumeration {
               enum "policy" {
                 description "Skip to next policy filter";
               }
               enum "term" {
                 description "Skip to next term in a policy filter";
               }
             }
           }
           choice accept_reject {
             case case_1 {
               leaf accept {
                 description "Accept a route";
                 type empty;
               }
             }
             case case_2 {
               leaf reject {
                 description "Reject a route";
                 type empty;
               }
             }
           }
           container bgp-output-queue-priority {
             description "Set the BGP Update output queue priority.";
             choice class {
               case case_1 {
                 leaf priority {
                   description "Output queue priority; higher is better";
                   type union {
                     type string {
                       pattern "<.*>|$.*";
                     }
                     type uint32 {
                       range "1 .. 16";
                     }
                   }
                 }
               }
               case case_2 {
                 leaf expedited {
                   description "Expedited queue; highest priority";
                   type empty;
                 }
               }
             }
           }
           leaf multipath-resolve {
             description "Use all paths for resolution over this prefix";
             type empty;
           }
           leaf source-routing-path-template {
             description "Spring-te template to apply";
             type string {
             }
           }
           leaf label-allocation-fallback-reject {
             description "Suppress prefix export when label allocation fails";
             type empty;
           }
           leaf resolution-map {
             description "Set resolution map modes";
             type string;
           }
           leaf ignore-service-label {
             description "Ignore service labels";
             type empty;
           }
           container prefix-attribute-flags {
             presence "enable prefix-attribute-flags";
             description "Set ISIS prefix attribute flags sub TLV";
             uses apply-advanced;
             leaf node-segment-flag {
               description "Set node segment flag ";
               type empty;
             }
             leaf external-prefix-flag {
               description "Set external prefix flag ";
               type empty;
             }
             leaf anycast-flag {
               description "Set anycast flag ";
               type empty;
             }
             leaf entropy-label-capability-flag {
               description "Set entropy label capability flag ";
               type empty;
             }
           }
           container ipv4-source-router-id {
             presence "enable ipv4-source-router-id";
             description "Set IPv4 source router id in advertisement";
             uses apply-advanced;
             leaf router-id {
               description "Specify IPv4 address";
               type jt:ipaddr;
             }
           }
           container ipv6-source-router-id {
             presence "enable ipv6-source-router-id";
             description "Set IPv6 source router id in advertisement";
             uses apply-advanced;
             leaf router-id {
               description "Specify IPv6 address";
               type jt:ipv6addr;
             }
           }
           leaf request-long-lived-ack {
             description "Advertise route after forwarding is programmed";
             type empty;
           }
           leaf send-withdrawal-on-route-change {
             description "Withdraw route if change is not acked from forwarding";
             type empty;
           }
           container slice {
             description "Configure Policy Slice action";
             leaf slice-name {
               description "Slice Name";
               type string {
                 length "1 .. 64";
               }
             }
           }
           leaf filter {
             description "Set firewall-filter name";
             type string {
             }
           }
           leaf strip-as-path {
             description "Remove the incoming BGP as-path and replace with local AS";
             type empty;
           }
           container request-acknowledgements {
             description "Set request acknowledgement";
             leaf nexthop-ack {
               description "Set nexthop acknowledgement ";
               type empty;
             }
             leaf route-ack {
               description "Set route acknowledgement ";
               type empty;
             }
           }
           container rib-export-strip {
             description "Strip attributes from a route";
             uses apply-advanced;
             leaf cluster-list {
               description "Strip cluster list from the route";
               type empty;
             }
           }
           list tunnel-termination-profile {
             key name;
             ordered-by user;
             description "Tunnel termination profiles associated with a route";
             leaf name {
               description "Name of a tunnel termination profile";
               type string;
             }
           }
           leaf flow-route-accounting {
             description "Enable accounting for flow routes";
             type empty;
           }
           leaf otc-local-role {
             description "Override local role without negotiation";
             type enumeration {
               enum "provider" {
                 description "Provider role";
               }
               enum "peer" {
                 description "Peer role";
               }
               enum "customer" {
                 description "Customer role";
               }
               enum "route-server" {
                 description "Route server role";
               }
               enum "route-server-client" {
                 description "Route server client role";
               }
             }
           }
         }
       }
       container from {
         description "Conditions to match the source of a route";
         uses apply-advanced;
         leaf instance {
           description "Routing protocol instance";
           type string;
         }
         leaf instance-any {
           description "Any routing protocol instance";
           type empty;
         }
         leaf-list instance-list {
           description "A list of routing protocol instances";
           type string;
         }
         leaf-list igp-instance {
           description "IGP instance";
           type string;
         }
         leaf igp-instance-regex {
           description "IGP instance name regular expression";
           type jt:regular-expression;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
             enum "inet-srte" {
               description "IPv4 srtte family";
             }
             enum "inet6-srte" {
               description "IPv6 srte family";
             }
             enum "inet-flow" {
               description "IPv4 flow family";
             }
             enum "inet6-flow" {
               description "IPv6 flow family";
             }
             enum "inet-vpn-flow" {
               description "IPv4 vpn flow family";
             }
             enum "inet6-vpn-flow" {
               description "IPv6 vpn flow family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "express-segments" {
               description "Express-segment routes";
             }
             enum "rift" {
               description "RIFT routes";
             }
             enum "l2-learned-host-routing" {
               description "Layer2-learned host routes";
             }
             enum "srv6-isis" {
               description "SRV6 ISIS";
             }
             enum "ari-ts" {
               description "ARI TS routes";
             }
             enum "srv6" {
               description "Segment Routing IPv6 local route";
             }
             enum "rib-export" {
               description "RIB export clone routes";
             }
             enum "igmp" {
               description "IGMP";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf bgp-srte-discriminator {
           description "Srte discriminator";
           type union {
             type uint32;
             type string {
               pattern "<.*>|$.*";
             }
           }
         }
         leaf srte-color {
           description "Srte color";
           type union {
             type uint32;
             type string {
               pattern "<.*>|$.*";
             }
           }
         }
         leaf programmed {
           description "API-programmed route";
           type empty;
         }
         list protocol-instance {
           key name;
           ordered-by user;
           description "To match protocol-instance";
           leaf name {
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
               enum "rib-export" {
                 description "RIB export clone routes";
               }
               enum "igmp" {
                 description "IGMP";
               }
               enum "any" {
                 description "Any route";
               }
             }
           }
           uses apply-advanced;
           leaf-list protocol-instance-name {
             description "Protocol instance name";
             type string;
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         container validation-database-instance {
           presence "enable validation-database-instance";
           description "Name to identify a validation-state with DB name";
           uses apply-advanced;
           leaf database-name {
             description "Route Validation Database name to be looked at";
             type string;
           }
           leaf state {
             description "Name to identify a validation-state";
             type enumeration {
               enum "valid" {
                 description "Match for valid database validation-state";
               }
               enum "invalid" {
                 description "Match for invalid database validation-state";
               }
               enum "unknown" {
                 description "Match for unknown database validation-state";
               }
             }
             mandatory true;
           }
         }
         list nexthop-weight {
           key "choice-ident choice-value weight";
           ordered-by user;
           description "Weight of the gateway";
           leaf choice-ident {
             type enumeration {
               enum "equal" {
               }
               enum "greater-than" {
               }
               enum "less-than" {
               }
               enum "greater-than-equal" {
               }
               enum "less-than-equal" {
               }
             }
           }
           leaf choice-value {
             type string;
           }
           leaf weight {
             description "Weight of the gateway";
             type union {
               type string {
                 pattern "<.*>|$.*";
               }
               type uint32 {
                 range "1 .. 65535";
               }
             }
           }
           uses apply-advanced;
           choice weight_type {
             case case_1 {
               leaf all-nexthop {
                 description "All the gateway weight should be matched";
                 type empty;
               }
             }
           }
         }
         list nexthop-ecmp {
           key "choice-ident choice-value ecmp";
           ordered-by user;
           description "Qualify nexthop equal cost multipath gateways";
           leaf choice-ident {
             type enumeration {
               enum "equal" {
               }
               enum "greater-than" {
               }
               enum "less-than" {
               }
               enum "greater-than-equal" {
               }
               enum "less-than-equal" {
               }
             }
           }
           leaf choice-value {
             type string;
           }
           leaf ecmp {
             description "Number of equal cost multipath gateways";
             type union {
               type string {
                 pattern "<.*>|$.*";
               }
               type uint32 {
                 range "1 .. 512";
               }
             }
           }
           uses apply-advanced;
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf-list tag2 {
           ordered-by user;
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
         choice lsp-name-type {
           case case_1 {
             leaf lsp {
               description "Label switched path name";
               type string {
               }
             }
           }
           case case_2 {
             leaf lsp-regex {
               description "Label switched path name regular expression";
               type string {
               }
             }
           }
         }
         container source-routing-path {
           presence "enable source-routing-path";
           description "Spring-te lsp policy attributes";
           leaf name-regex {
             description "Spring-te lsp name regex";
             type string {
             }
           }
           leaf dest {
             description "Spring-te lsp IPV4/IPV6 destination without color";
             type jt:ipaddr;
           }
           leaf origin {
             description "Spring-te lsp origin address";
             type jt:ipaddr;
           }
           leaf tunnel-source {
             description "Spring-te lsp source protocol";
             type enumeration {
               enum "pcep" {
                 description "Spring-te lsp src pcep";
               }
               enum "bgp" {
                 description "Spring-te lsp src bgp";
               }
             }
           }
           leaf route-distinguisher {
             description "Spring-te lsp route distinguisher";
             type union {
               type uint32;
               type string {
                 pattern "<.*>|$.*";
               }
             }
           }
           leaf color {
             description "Spring-te lsp color";
             type union {
               type uint32;
               type string {
                 pattern "<.*>|$.*";
               }
             }
           }
         }
         list route-filter {
           key "address choice-ident choice-value";
           ordered-by user;
           description "List of routes to match";
           uses control_route_filter_type;
         }
         list source-address-filter {
           key "address choice-ident choice-value";
           ordered-by user;
           description "List of source addresses to match";
           uses control_source_address_filter_type;
         }
         list prefix-list {
           key name;
           ordered-by user;
           description "List of prefix-lists of routes to match";
           uses control_prefix_list_type;
         }
         list rib-list {
           key name;
           ordered-by user;
           description "List of routing-tables";
           uses control_rib_list_type;
         }
         list as-path-neighbors {
           key "list-type list-name";
           ordered-by user;
           description "List of peer AS to match";
           uses control_as_list_type;
         }
         list as-path-origins {
           key "list-type list-name";
           ordered-by user;
           description "List of originating AS to match";
           uses control_as_list_type;
         }
         list as-path-transits {
           key "list-type list-name";
           ordered-by user;
           description "List of originating AS to match";
           uses control_as_list_type;
         }
         list prefix-list-filter {
           key "list_name choice-ident choice-value";
           ordered-by user;
           description "List of prefix-list-filters to match";
           uses control_prefix_list_filter_type;
         }
         list route-filter-list {
           key name;
           ordered-by user;
           description "List of route-filter-lists of routes to match";
           uses control_route_filter_list_type;
         }
         list source-address-filter-list {
           key name;
           ordered-by user;
           description "List of source-address-filter-lists of routes to match";
           uses control_source_address_filter_list_type;
         }
         list rtf-prefix-list {
           key name;
           ordered-by user;
           description "List of rtf-prefix-lists of routes to match";
           uses control_rtf_prefix_list_type;
         }
         container multicast-scope {
           description "Multicast scope to match";
           choice scope-choice {
             case case_1 {
               leaf node-local {
                 description "Node-local scope";
                 type empty;
               }
             }
             case case_2 {
               leaf link-local {
                 description "Link-local scope";
                 type empty;
               }
             }
             case case_3 {
               leaf site-local {
                 description "Site-local scope";
                 type empty;
               }
             }
             case case_4 {
               leaf organization-local {
                 description "Organization-local scope";
                 type empty;
               }
             }
             case case_5 {
               leaf global {
                 description "Global scope";
                 type empty;
               }
             }
             case case_6 {
               leaf scope_value {
                 description "Scope value";
                 type union {
                   type string {
                     pattern "<.*>|$.*";
                   }
                   type uint32 {
                     range "0 .. 15";
                   }
                 }
               }
             }
           }
           choice scope-operator {
             case case_1 {
               leaf orhigher {
                 description "Match higher values";
                 type empty;
               }
             }
             case case_2 {
               leaf orlower {
                 description "Match lower values";
                 type empty;
               }
             }
           }
         }
         leaf aggregate-contributor {
           description "Match more specifics of an aggregate";
           type empty;
         }
         leaf state {
           description "Route state";
           type enumeration {
             enum "active" {
               description "Active route";
             }
             enum "inactive" {
               description "Inactive route";
             }
           }
         }
         leaf-list tunnel-type {
           ordered-by user;
           description "Tunnel type";
           type enumeration {
             enum "gre" {
               description "GRE tunnel";
             }
             enum "udp" {
               description "UDP tunnel";
             }
             enum "ipip" {
               description "IPIP tunnel";
             }
           }
         }
         leaf route-type {
           description "Route type";
           type enumeration {
             enum "internal" {
               description "Internal route";
             }
             enum "external" {
               description "External route";
             }
           }
         }
         leaf-list nlri-route-type {
           ordered-by user;
           description "Route type from NLRI";
           type union {
             type string {
               pattern "<.*>|$.*";
             }
             type uint32 {
               range "1 .. 10";
             }
           }
         }
         leaf-list evpn-tag {
           ordered-by user;
           description "Tag in EVPN Route";
           type union {
             type string {
               pattern "<.*>|$.*";
             }
             type uint32 {
               range "0 .. 4294967295";
             }
           }
         }
         leaf-list evpn-esi {
           ordered-by user;
           description "ESI in EVPN Route";
           type string;
         }
         list mac-filter-list {
           key name;
           ordered-by user;
           description "List of mac-filter-list macs to match";
           uses control_mac_address_filter_list_type;
         }
         leaf evpn-mac-route {
           description "EVPN Mac Route type";
           type enumeration {
             enum "mac-only" {
               description "MAC route";
             }
             enum "mac-ipv4" {
               description "MAC IPV4 route";
             }
             enum "mac-ipv6" {
               description "MAC IPV6 route";
             }
           }
         }
         leaf-list bridge-domain-id {
           ordered-by user;
           description "Bridge Domain Identifier (Vlan or VNI)";
           type union {
             type string {
               pattern "<.*>|$.*";
             }
             type uint32 {
               range "0 .. 4294967295";
             }
           }
         }
         leaf next-hop-type {
           description "Next-hop type";
           type enumeration {
             enum "merged" {
               description "Merged next hop";
             }
           }
         }
         leaf-list condition {
           ordered-by user;
           description "Condition to match on";
           type string;
         }
         container route-target-prefix-count {
           description "Limit number of BGP prefixes with a 'Route Target' set";
           presence "enable route-target-prefix-count";
           uses prefix_count_type;
         }
         list community-count {
           key name;
           ordered-by user;
           description "Number of BGP communities";
           uses community_count_type;
         }
         list large-community-count {
           key name;
           ordered-by user;
           description "Number of Large BGP communities";
           uses community_count_type;
         }
         list as-path-unique-count {
           key name;
           ordered-by user;
           description "Number of unique BGP ASes excluding confederations";
           uses as-path-unique-count-type;
         }
         list as-path-calc-length {
           key name;
           ordered-by user;
           description "Number of BGP ASes excluding confederations";
           uses as-path-calc-length-type;
         }
         container traffic-engineering {
           presence "enable traffic-engineering";
           description "Traffic-Engineering related parameters";
           uses apply-advanced;
           leaf-list protocol {
             ordered-by user;
             description "Protocol that originated the entry";
             type enumeration {
               enum "direct" {
                 description "Directly originated";
               }
               enum "ospf" {
                 description "OSPF originated";
               }
               enum "isis-level-1" {
                 description "ISIS level-1 originated";
               }
               enum "isis-level-2" {
                 description "ISIS level-2 originated";
               }
               enum "spring-te" {
                 description "SPRING-TE originated";
               }
               enum "static" {
                 description "Statically originated";
               }
               enum "unknown" {
                 description "Originated by unknown sources";
               }
             }
           }
           container node {
             presence "enable node";
             description "Node-related parameters";
             uses apply-advanced;
             leaf as {
               description "AS number";
               type string {
               }
             }
             leaf node-type {
               description "Real or pseudo-node";
               type enumeration {
                 enum "router" {
                   description "Real node";
                 }
                 enum "pseudo-node" {
                   description "Pseudo-node";
                 }
               }
             }
             leaf router-id {
               description "IP prefix to match the router-id against";
               type jt:ipprefix;
             }
             leaf sys-id {
               description "ISO address of the node";
               type jt:sysid;
             }
           }
           container ipv4-prefix {
             presence "enable ipv4-prefix";
             description "IPV4 prefix-related parameters";
             uses apply-advanced;
             leaf as {
               description "AS number";
               type string {
               }
             }
             leaf router-id {
               description "IP prefix to match the router-id against";
               type jt:ipprefix;
             }
             leaf prefix {
               description "IP prefix to match against";
               type jt:ipprefix;
             }
             leaf sys-id {
               description "ISO address of the node";
               type jt:sysid;
             }
           }
           container ipv6-prefix {
             presence "enable ipv6-prefix";
             description "IPV6 prefix related parameters";
             uses apply-advanced;
             leaf as {
               description "AS number";
               type string {
               }
             }
             leaf router-id {
               description "IPv6 prefix to match the router-id against";
               type jt:ipprefix;
             }
             leaf prefix {
               description "IPv6 prefix to match against";
               type jt:ipv6prefix;
             }
             leaf sys-id {
               description "ISO address of the node";
               type jt:sysid;
             }
           }
           container srv6-sid {
             presence "enable srv6-sid";
             description "SRV6 SID related parameters";
             uses apply-advanced;
             leaf as {
               description "AS number";
               type string {
               }
             }
             leaf router-id {
               description "SRv6 SID to match the router-id against";
               type jt:ipprefix;
             }
             leaf sid {
               description "SRv6 SID to match against";
               type jt:ipv6addr;
             }
             leaf sys-id {
               description "ISO address of the node";
               type jt:sysid;
             }
           }
           container spring-te {
             presence "enable spring-te";
             description "SPRING-TE policy related parameters";
             uses apply-advanced;
             leaf node-as {
               description "Node AS number";
               type string {
               }
             }
             leaf router-id {
               description "IP prefix to match against the node for the SPRING TE policy";
               type jt:ipprefix;
             }
             leaf color {
               description "Color of the SPRING-TE policy candidate path";
               type union {
                 type uint32;
                 type string {
                   pattern "<.*>|$.*";
                 }
               }
             }
             leaf discriminator {
               description "Discriminator of the SPRING-TE policy candidate path";
               type union {
                 type uint32;
                 type string {
                   pattern "<.*>|$.*";
                 }
               }
             }
             leaf endpoint {
               description "Endpoint of the SPRING-TE policy candidate path";
               type jt:ipaddr;
             }
             leaf protocol-origin {
               description "Protocol originating the SPRING-TE policy candidate path";
               type enumeration {
                 enum "bgp" {
                   description "SPRING-TE policy candidate path originated by BGP";
                 }
                 enum "cli" {
                   description "SPRING-TE policy candidate path originated by cli";
                 }
                 enum "pcep" {
                   description "SPRING-TE policy candidate path originated by PCEP";
                 }
               }
             }
             leaf origin-as {
               description "AS number of the node creating the SPRING-TE policy candidate path";
               type string {
               }
             }
             leaf origin-addr {
               description "Address of the node originating the SPRING-TE policy candidate path";
               type jt:ipaddr;
             }
           }
           container link {
             presence "enable link";
             description "Link-related parameters";
             uses apply-advanced;
             container from {
               description "Specify parameter of the 'from' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
             container to {
               description "Specify parameters of the 'to' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
           }
           leaf identifier {
             description "BGP-TE identifier";
             type union {
               type string {
                 pattern "<.*>|$.*";
               }
               type uint64 {
                 range "2 .. 18446744073709551615";
               }
             }
           }
         }
         leaf-list route-distinguisher {
           ordered-by user;
           description "Name of the route-distinguisher";
           type string;
         }
         leaf prefix-segment {
           description "Prefix segment present in route extended data";
           type empty;
         }
         list flowspec-attribute {
           key name;
           ordered-by user;
           description "List of flowspec attributes to match";
           uses control_flowspec_attribute_type;
         }
       }
       container to {
         description "Conditions to match the destination of a route";
         uses apply-advanced;
         leaf instance {
           description "Routing protocol instance";
           type string;
         }
         leaf instance-any {
           description "Any routing protocol instance";
           type empty;
         }
         leaf-list instance-list {
           description "A list of routing protocol instances";
           type string;
         }
         leaf-list igp-instance {
           description "IGP instance";
           type string;
         }
         leaf igp-instance-regex {
           description "IGP instance name regular expression";
           type jt:regular-expression;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
             enum "inet-srte" {
               description "IPv4 srtte family";
             }
             enum "inet6-srte" {
               description "IPv6 srte family";
             }
             enum "inet-flow" {
               description "IPv4 flow family";
             }
             enum "inet6-flow" {
               description "IPv6 flow family";
             }
             enum "inet-vpn-flow" {
               description "IPv4 vpn flow family";
             }
             enum "inet6-vpn-flow" {
               description "IPv6 vpn flow family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "express-segments" {
               description "Express-segment routes";
             }
             enum "rift" {
               description "RIFT routes";
             }
             enum "l2-learned-host-routing" {
               description "Layer2-learned host routes";
             }
             enum "srv6-isis" {
               description "SRV6 ISIS";
             }
             enum "ari-ts" {
               description "ARI TS routes";
             }
             enum "srv6" {
               description "Segment Routing IPv6 local route";
             }
             enum "rib-export" {
               description "RIB export clone routes";
             }
             enum "igmp" {
               description "IGMP";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf bgp-srte-discriminator {
           description "Srte discriminator";
           type union {
             type uint32;
             type string {
               pattern "<.*>|$.*";
             }
           }
         }
         leaf srte-color {
           description "Srte color";
           type union {
             type uint32;
             type string {
               pattern "<.*>|$.*";
             }
           }
         }
         leaf programmed {
           description "API-programmed route";
           type empty;
         }
         list protocol-instance {
           key name;
           ordered-by user;
           description "To match protocol-instance";
           leaf name {
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "express-segments" {
                 description "Express-segment routes";
               }
               enum "rift" {
                 description "RIFT routes";
               }
               enum "l2-learned-host-routing" {
                 description "Layer2-learned host routes";
               }
               enum "srv6-isis" {
                 description "SRV6 ISIS";
               }
               enum "ari-ts" {
                 description "ARI TS routes";
               }
               enum "srv6" {
                 description "Segment Routing IPv6 local route";
               }
               enum "rib-export" {
                 description "RIB export clone routes";
               }
               enum "igmp" {
                 description "IGMP";
               }
               enum "any" {
                 description "Any route";
               }
             }
           }
           uses apply-advanced;
           leaf-list protocol-instance-name {
             description "Protocol instance name";
             type string;
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         container validation-database-instance {
           presence "enable validation-database-instance";
           description "Name to identify a validation-state with DB name";
           uses apply-advanced;
           leaf database-name {
             description "Route Validation Database name to be looked at";
             type string;
           }
           leaf state {
             description "Name to identify a validation-state";
             type enumeration {
               enum "valid" {
                 description "Match for valid database validation-state";
               }
               enum "invalid" {
                 description "Match for invalid database validation-state";
               }
               enum "unknown" {
                 description "Match for unknown database validation-state";
               }
             }
             mandatory true;
           }
         }
         list nexthop-weight {
           key "choice-ident choice-value weight";
           ordered-by user;
           description "Weight of the gateway";
           leaf choice-ident {
             type enumeration {
               enum "equal" {
               }
               enum "greater-than" {
               }
               enum "less-than" {
               }
               enum "greater-than-equal" {
               }
               enum "less-than-equal" {
               }
             }
           }
           leaf choice-value {
             type string;
           }
           leaf weight {
             description "Weight of the gateway";
             type union {
               type string {
                 pattern "<.*>|$.*";
               }
               type uint32 {
                 range "1 .. 65535";
               }
             }
           }
           uses apply-advanced;
           choice weight_type {
             case case_1 {
               leaf all-nexthop {
                 description "All the gateway weight should be matched";
                 type empty;
               }
             }
           }
         }
         list nexthop-ecmp {
           key "choice-ident choice-value ecmp";
           ordered-by user;
           description "Qualify nexthop equal cost multipath gateways";
           leaf choice-ident {
             type enumeration {
               enum "equal" {
               }
               enum "greater-than" {
               }
               enum "less-than" {
               }
               enum "greater-than-equal" {
               }
               enum "less-than-equal" {
               }
             }
           }
           leaf choice-value {
             type string;
           }
           leaf ecmp {
             description "Number of equal cost multipath gateways";
             type union {
               type string {
                 pattern "<.*>|$.*";
               }
               type uint32 {
                 range "1 .. 512";
               }
             }
           }
           uses apply-advanced;
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf-list tag2 {
           ordered-by user;
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
         choice lsp-name-type {
           case case_1 {
             leaf lsp {
               description "Label switched path name";
               type string {
               }
             }
           }
           case case_2 {
             leaf lsp-regex {
               description "Label switched path name regular expression";
               type string {
               }
             }
           }
         }
         container source-routing-path {
           presence "enable source-routing-path";
           description "Spring-te lsp policy attributes";
           leaf name-regex {
             description "Spring-te lsp name regex";
             type string {
             }
           }
           leaf dest {
             description "Spring-te lsp IPV4/IPV6 destination without color";
             type jt:ipaddr;
           }
           leaf origin {
             description "Spring-te lsp origin address";
             type jt:ipaddr;
           }
           leaf tunnel-source {
             description "Spring-te lsp source protocol";
             type enumeration {
               enum "pcep" {
                 description "Spring-te lsp src pcep";
               }
               enum "bgp" {
                 description "Spring-te lsp src bgp";
               }
             }
           }
           leaf route-distinguisher {
             description "Spring-te lsp route distinguisher";
             type union {
               type uint32;
               type string {
                 pattern "<.*>|$.*";
               }
             }
           }
           leaf color {
             description "Spring-te lsp color";
             type union {
               type uint32;
               type string {
                 pattern "<.*>|$.*";
               }
             }
           }
         }
       }
       container then {
         description "Actions to take if 'from' and 'to' conditions match";
         uses apply-advanced;
         container metric {
           description "Metric value";
           uses apply-advanced;
           choice metric_action {
             case case_1 {
               leaf metric {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
             case case_4 {
               container igp {
                 presence "enable igp";
                 description "Track the IGP metric (BGP only)";
                 leaf metric_offset {
                   description "Metric offset for MED";
                   type union {
                     type int32;
                     type string {
                       pattern "<.*>|$.*";
                     }
                   }
                 }
               }
             }
             case case_5 {
               container minimum-igp {
                 presence "enable minimum-igp";
                 description "Track the minimum IGP metric (BGP only)";
                 leaf metric_offset {
                   description "Metric offset for MED";
                   type union {
                     type int32;
                     type string {
                       pattern "<.*>|$.*";
                     }
                   }
                 }
               }
             }
             case case_6 {
               container expression {
                 description "Calculate value based on route metric and metric2";
                 uses metric_expression_type;
               }
             }
             case case_7 {
               leaf aigp {
                 description "Use aigp, if it exists, to set the IGP metric";
                 type empty;
               }
             }
             case case_8 {
               container effective-aigp {
                 presence "enable effective-aigp";
                 description "Track the effective AIGP metric (BGP only)";
                 leaf metric_offset {
                   description "Metric offset for MED";
                   type union {
                     type int32;
                     type string {
                       pattern "<.*>|$.*";
                     }
                   }
                 }
               }
             }
             case case_9 {
               container minimum-effective-aigp {
                 presence "enable minimum-effective-aigp";
                 description "Track the minimum effective AIGP metric (BGP only)";
                 leaf metric_offset {
                   description "Metric offset for MED";
                   type union {
                     type int32;
                     type string {
                       pattern "<.*>|$.*";
                     }
                   }
                 }
               }
             }
           }
         }
         container metric2 {
           description "Metric value 2";
           uses apply-advanced;
           choice metric_action {
             case case_1 {
               leaf metric2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric3 {
           description "Metric value 3";
           uses apply-advanced;
           choice metric_action {
             case case_1 {
               leaf metric3 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric4 {
           description "Metric value 4";
           uses apply-advanced;
           choice metric_action {
             case case_1 {
               leaf metric4 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag {
           description "Tag string";
           uses apply-advanced;
           choice metric_action {
             case case_1 {
               leaf tag {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag2 {
           description "Tag string 2";
           uses apply-advanced;
           choice metric_action {
             case case_1 {
               leaf tag2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference {
           description "Preference value";
           uses apply-advanced;
           choice metric_action {
             case case_1 {
               leaf preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference2 {
           description "Preference value 2";
           uses apply-advanced;
           choice metric_action {
             case case_1 {
               leaf preference2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color {
           description "Color (preference) value";
           uses apply-advanced;
           choice metric_action {
             case case_1 {
               leaf color {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color2 {
           description "Color (preference) value 2";
           uses apply-advanced;
           choice metric_action {
             case case_1 {
               leaf color2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container local-preference {
           description "Local preference associated with a route";
           uses apply-advanced;
           choice metric_action {
             case case_1 {
               leaf local-preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container credibility {
           description "TED credibility value for entries from BGP-TE";
           uses apply-advanced;
           choice metric_action {
             case case_1 {
               leaf credibility {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         leaf priority {
           description "Set priority for route installation";
           type enumeration {
             enum "high" {
               description "Set priority to high";
             }
             enum "medium" {
               description "Set priority to medium";
             }
             enum "low" {
               description "Set priority to low";
             }
           }
         }
         container prefix-segment {
           description "Set prefix segment attributes";
           uses apply-advanced;
           list algorithm {
             key name;
             description "Set prefix segment attributes for strict/flex algorithm ";
             max-elements 15;
             leaf name {
               description "Set prefix segment for strict/flex algorithm";
               type union {
                 type string {
                   pattern "<.*>|$.*";
                 }
                 type uint32 {
                   range "1 .. 255";
                 }
               }
               mandatory true;
             }
             leaf index {
               description "Set prefix segment index id";
               type union {
                 type string {
                   pattern "<.*>|$.*";
                 }
                 type uint32 {
                   range "0 .. 1048575";
                 }
               }
               mandatory true;
             }
             leaf node-segment {
               description "Set node segment flag for this prefix segment";
               type empty;
             }
           }
           leaf index {
             description "Set prefix segment index id";
             type union {
               type string {
                 pattern "<.*>|$.*";
               }
               type uint32 {
                 range "0 .. 1048575";
               }
             }
           }
           leaf node-segment {
             description "Set node segment flag for default prefix segment";
             type empty;
           }
           leaf redistribute {
             description "Redistribute prefix-segment from route entry";
             type empty;
           }
         }
         leaf label-allocation {
           description "Set label allocation mode";
           type enumeration {
             enum "per-table" {
               description "Set per-table label allocation mode";
             }
             enum "per-nexthop" {
               description "Set per-nexthop label allocation mode";
             }
             enum "per-table-localize" {
               description "Set per-table-localize label allocation mode";
             }
           }
         }
         container add-path {
           description "Set BGP add-path attributes";
           leaf send-count {
             description "Number of add-paths sent";
             type union {
               type string {
                 pattern "<.*>|$.*";
               }
               type uint32 {
                 range "2 .. 64";
               }
             }
           }
         }
         leaf fib-install-priority {
           description "Set Fib Instalation priority of a route";
           type enumeration {
             enum "high" {
               description "Set Fib install priority  to high";
             }
             enum "medium" {
               description "Set Fib install priority to medium ";
             }
           }
         }
         leaf validation-state {
           description "Set validation-state of a route";
           type enumeration {
             enum "valid" {
               description "Set validaton-state to valid";
             }
             enum "invalid" {
               description "Set validation-state to invalid";
             }
             enum "unknown" {
               description "Set validation-state to unknown";
             }
           }
         }
         leaf origin {
           description "BGP path origin";
           type enumeration {
             enum "igp" {
               description "Path originated in the local IGP";
             }
             enum "egp" {
               description "Path originated in another AS";
             }
             enum "incomplete" {
               description "Path was learned by some other means";
             }
           }
         }
         container srv6 {
           description "Configure SID with 128 bit address";
           leaf sid {
             description "IPv6 Address";
             type jt:ipv6addr;
           }
           leaf locator {
             description "Name of locator";
             type string;
           }
           choice locator_type {
             case case_1 {
               leaf micro-dt4-sid {
                 description "Micro SID type dt4";
                 type empty;
               }
             }
             case case_2 {
               leaf micro-dt6-sid {
                 description "Micro SID type dt6";
                 type empty;
               }
             }
             case case_3 {
               leaf micro-dt46-sid {
                 description "Micro SID type dt46";
                 type empty;
               }
             }
             case case_4 {
               leaf end-dtm-sid {
                 description "SID type dtm";
                 type empty;
               }
             }
           }
         }
         container aigp-originate {
           presence "enable aigp-originate";
           description "Originate a BGP AIGP attribute";
           leaf effective-metric {
             description "Metric associated with non-BGP route";
             type empty;
           }
           leaf distance {
             description "AIGP distance";
             type union {
               type uint32;
               type string {
                 pattern "<.*>|$.*";
               }
             }
           }
         }
         container aigp-adjust {
           description "Adjust a BGP AIGP attribute";
           choice math-op {
             case case_1 {
               leaf add {
                 type empty;
               }
             }
             case case_2 {
               leaf subtract {
                 type empty;
               }
             }
             case case_3 {
               leaf multiply {
                 type empty;
               }
             }
             case case_4 {
               leaf divide {
                 type empty;
               }
             }
           }
           choice adjust-value {
             case case_1 {
               leaf user-value {
                 description "Adjustment value";
                 type union {
                   type uint64;
                   type string {
                     pattern "<.*>|$.*";
                   }
                 }
               }
             }
             case case_2 {
               leaf distance-to-protocol-nexthop {
                 description "Metric2";
                 type empty;
               }
             }
           }
         }
         list community {
           key "choice-ident choice-value community-name";
           ordered-by user;
           description "BGP community properties associated with a route";
           leaf choice-ident {
             type enumeration {
               enum "equal-literal" {
               }
               enum "set" {
               }
               enum "plus-literal" {
               }
               enum "add" {
               }
               enum "minus-literal" {
               }
               enum "delete" {
               }
             }
           }
           leaf choice-value {
             type string;
           }
           leaf community-name {
             description "Name to identify a BGP community";
             type string;
           }
         }
         list inline-community {
           key "choice-ident choice-value inline-community-member";
           ordered-by user;
           description "Set BGP community properties associated with a route inline";
           leaf choice-ident {
             type enumeration {
               enum "equal-literal" {
               }
               enum "set" {
               }
               enum "plus-literal" {
               }
               enum "add" {
               }
               enum "minus-literal" {
               }
               enum "delete" {
               }
             }
           }
           leaf choice-value {
             type string;
           }
           leaf inline-community-member {
             description "Inline BGP community members";
             type string;
           }
         }
         list tunnel-attribute {
           key "choice-ident choice-value tunnel-attribute-name";
           ordered-by user;
           description "BGP tunnel attribute associated with a route";
           leaf choice-ident {
             type enumeration {
               enum "set" {
               }
               enum "remove" {
               }
             }
           }
           leaf choice-value {
             type string;
           }
           leaf tunnel-attribute-name {
             description "Name of a tunnel attribute , or 'all'";
             type string;
           }
         }
         container assisted-replication {
           presence "enable assisted-replication";
           description "Deterministic AR replicator knobs";
           uses apply-advanced;
           leaf-list replicator-ip {
             description "Set deterministic AR replicator ip for the flow";
             type jt:ipaddr;
             max-elements 1;
           }
           leaf strict {
             description "Do not use any other replicator";
             type empty;
           }
           leaf-list fallback-replicator-ip {
             description "Set Fallback replicator-ip";
             type jt:ipaddr;
             max-elements 1;
           }
         }
         leaf damping {
           description "Define BGP route flap damping parameters";
           type string;
         }
         container aggregate-bandwidth {
           presence "enable aggregate-bandwidth";
           description "Advertise aggregate outbound link bandwidth";
           uses apply-advanced;
           choice transitive-type {
             case case_1 {
               leaf transitive {
                 description "Transitive flag for link bandwidth";
                 type empty;
               }
             }
             case case_2 {
               leaf non-transitive {
                 description "Non-Transitive flag for link bandwidth";
                 type empty;
               }
             }
           }
           leaf divide-equal {
             description "Divide-equal";
             type empty;
           }
         }
         container aggregate-weight {
           presence "enable aggregate-weight";
           description "Advertise aggregate outbound count";
           uses apply-advanced;
           leaf multiplier {
             description "Adjust the aggregate-weight by multiplying it with a given value, default is 1";
             default "1";
             type union {
               type string {
                 pattern "<.*>|$.*";
               }
               type uint16 {
                 range "1 .. 32";
               }
             }
           }
         }
         container auto-link-bandwidth {
           presence "enable auto-link-bandwidth";
           description "Auto sense and attach link bandwidth community";
           uses apply-advanced;
           choice transitive-type {
             case case_1 {
               leaf transitive {
                 description "Transitive flag for link bandwidth";
                 type empty;
               }
             }
             case case_2 {
               leaf non-transitive {
                 description "Non-Transitive flag for link bandwidth";
                 type empty;
               }
             }
           }
         }
         leaf limit-bandwidth {
           description "Limit advertised aggregate outbound link bandwidth";
           type union {
             type uint64;
             type string {
               pattern "<.*>|$.*";
             }
           }
         }
         leaf no-entropy-label-capability {
           description "Don't advertise entropy label capability";
           type empty;
         }
         leaf as-path-prepend {
           description "Prepend AS numbers to an AS path (BGP only)";
           type string;
         }
         leaf as-path-replace {
           description "Replace sequence of AS numbers/'private' with local AS";
           type string;
         }
         container as-path-expand {
           description "Prepend AS numbers prior to adding local-as (BGP only)";
           choice aspath_exp_value {
             case case_1 {
               container last-as {
                 presence "enable last-as";
                 description "Prepend last AS";
                 leaf count {
                   description "Repeat count";
                   type union {
                     type string {
                       pattern "<.*>|$.*";
                     }
                     type uint32 {
                       range "1 .. 32";
                     }
                   }
                 }
               }
             }
             case case_2 {
               container local-as {
                 presence "enable local-as";
                 description "Prepend local AS";
                 leaf count {
                   description "Repeat count";
                   type union {
                     type string {
                       pattern "<.*>|$.*";
                     }
                     type uint32 {
                       range "1 .. 32";
                     }
                   }
                 }
               }
             }
             case case_3 {
               container asn {
                 presence "enable asn";
                 description "Prepend AS";
                 uses apply-advanced;
                 leaf as-value {
                   description "AS value";
                   type union {
                     type uint32;
                     type string {
                       pattern "<.*>|$.*";
                     }
                   }
                   mandatory true;
                 }
                 leaf count {
                   description "Repeat count";
                   type union {
                     type string {
                       pattern "<.*>|$.*";
                     }
                     type uint32 {
                       range "1 .. 32";
                     }
                   }
                 }
               }
             }
             case case_4 {
               leaf aspath {
                 description "AS path string";
                 type string;
               }
             }
           }
         }
         container next-hop {
           description "Set the address of the next-hop router";
           choice nexthop_value {
             case case_1 {
               leaf self {
                 description "Use a local address as the next-hop address";
                 type empty;
               }
             }
             case case_2 {
               leaf peer-address {
                 description "Use the remote peer address as the next-hop address";
                 type empty;
               }
             }
             case case_3 {
               leaf address {
                 description "Next-hop address";
                 type jt:ipaddr;
               }
             }
             case case_4 {
               leaf reject {
                 description "Use a reject next hop";
                 type empty;
               }
             }
             case case_5 {
               leaf discard {
                 description "Use a discard next hop";
                 type empty;
               }
             }
             case case_6 {
               leaf next-table {
                 description "Perform a forwarding lookup in the specified table";
                 type string;
               }
             }
           }
           leaf no-resolution {
             description "Don't resolve nexthop reachability";
             type empty;
           }
         }
         container install-nexthop {
           description "Choose the next hop to be used for forwarding";
           choice strict_type {
             case case_1 {
               leaf strict {
                 description "Do not use any other available next hops";
                 type empty;
               }
             }
             case case_2 {
               leaf strict-named-lsp {
                 description "Do not use any other non-lsp next hops";
                 type empty;
               }
             }
           }
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
             container fallback {
               description "Backup option";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
                 case case_8 {
                   leaf macsec-interfaces {
                     description "Next-hop for MACsec interfaces";
                     type empty;
                   }
                 }
               }
               container except {
                 description "Do not choose to install matching next hops";
                 uses apply-advanced;
                 choice nexthop-value {
                   case case_1 {
                     leaf-list lsp {
                       ordered-by user;
                       description "Next-hop LSP name";
                       type string;
                     }
                   }
                   case case_2 {
                     leaf-list lsp-regex {
                       ordered-by user;
                       description "Next-hop LSP name regular expression";
                       type string;
                     }
                   }
                   case case_3 {
                     leaf-list static-lsp {
                       ordered-by user;
                       description "Next-hop static LSP name";
                       type string;
                     }
                   }
                   case case_4 {
                     leaf-list static-lsp-regex {
                       ordered-by user;
                       description "Next-hop static LSP name regular expression";
                       type string;
                     }
                   }
                   case case_5 {
                     leaf non-lsp-nexthop {
                       description "Next-hop with non-lsp";
                       type empty;
                     }
                   }
                   case case_6 {
                     leaf non-labelled-nexthop {
                       description "Next-hop without tag";
                       type empty;
                     }
                   }
                   case case_7 {
                     leaf overlay-vxlan-interfaces {
                       description "Next-hop for vxlan interfaces";
                       type empty;
                     }
                   }
                   case case_8 {
                     leaf macsec-interfaces {
                       description "Next-hop for MACsec interfaces";
                       type empty;
                     }
                   }
                 }
               }
             }
           }
           container fallback {
             description "Backup option ";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
             container except {
               description "Do not choose to install matching next hops";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
                 case case_5 {
                   leaf non-lsp-nexthop {
                     description "Next-hop with non-lsp";
                     type empty;
                   }
                 }
                 case case_6 {
                   leaf non-labelled-nexthop {
                     description "Next-hop without tag";
                     type empty;
                   }
                 }
                 case case_7 {
                   leaf overlay-vxlan-interfaces {
                     description "Next-hop for vxlan interfaces";
                     type empty;
                   }
                 }
                 case case_8 {
                   leaf macsec-interfaces {
                     description "Next-hop for MACsec interfaces";
                     type empty;
                   }
                 }
               }
             }
           }
         }
         leaf trace {
           description "Log matches to a trace file";
           type empty;
         }
         container external {
           presence "enable external";
           description "External route";
           uses apply-advanced;
           leaf type {
             description "OSPF external metric type";
             type union {
               type string {
                 pattern "<.*>|$.*";
               }
               type int32 {
                 range "1 .. 2";
               }
             }
           }
           leaf nssa-only {
             description "Clear P-bit on lsa type 7";
             type empty;
           }
         }
         container load-balance {
           description "Type of load balancing in forwarding table";
           choice load_balance_type {
             case case_1 {
               leaf per-packet {
                 description "Load balance on a per-packet basis deprecated, use per-flow instead";
                 type empty;
               }
             }
             case case_2 {
               leaf per-flow {
                 description "Load balance on a per-flow basis";
                 type empty;
               }
             }
             case case_3 {
             }
             case case_4 {
             }
             case case_5 {
               leaf consistent-hash {
                 description "Give a prefix consistent load-balancing";
                 type empty;
               }
             }
             case case_6 {
             }
             case case_7 {
             }
             case case_8 {
             }
             case case_9 {
             }
             case case_10 {
             }
             case case_11 {
             }
           }
         }
         container advertise-locator {
           presence "enable advertise-locator";
           description "Advertise SRv6 Locator";
           uses apply-advanced;
           leaf internal {
             description "Advertise locator as Interal route";
             type empty;
           }
         }
         leaf set-down-bit {
           description "Set down bit";
           type empty;
         }
         leaf analyze {
           description "Send to registered controllers for analysis";
           type empty;
         }
         leaf class {
           description "Set class-of-service parameters";
           type string;
         }
         leaf destination-class {
           description "Set destination class in forwarding table";
           type string;
         }
         leaf source-class {
           description "Set source class in forwarding table";
           type string;
         }
         leaf forwarding-class {
           description "Set source or destination class in forwarding table";
           type string;
         }
         container map-to-interface {
           description "Set output logical interface";
           choice map_to_interface_value {
             case case_1 {
               leaf self {
                 description "Map the interface to itself";
                 type empty;
               }
             }
             case case_2 {
               leaf interface {
                 description "Output logical interface";
                 type union {
                   type jt:interface-name;
                   type string {
                     pattern "<.*>|$.*";
                   }
                 }
               }
             }
           }
         }
         leaf-list ssm-source {
           ordered-by user;
           description "List of Sources for SSM mapping";
           type jt:ipaddr;
         }
         container p2mp-lsp-root {
           description "P2mp lsp root address";
           uses apply-advanced;
           leaf address {
             description "Ipv4 root address";
             type jt:ipv4addr;
           }
         }
         leaf cos-next-hop-map {
           description "Set CoS-based next-hop map in forwarding table";
           type string;
         }
         leaf dynamic-tunnel-attributes {
           description "Choose the dynamic tunnel attributes used for forwarding";
           type string;
         }
         leaf tunnel-end-point-address {
           description "Set tunnel end-point address of tunnel";
           type jt:ipaddr;
         }
         leaf selected-mldp-egress {
           description "This node should act as egress node for MLDP inband signalling";
           type empty;
         }
         leaf mhop-bfd-port {
           description "Use port number 4784 for MPLS-BFD as per RFC5884";
           type empty;
         }
         leaf no-backup {
           description "This prefix should not have backup";
           type empty;
         }
         leaf default-action {
           description "Set default policy action";
           type enumeration {
             enum "accept" {
               description "Accept a route";
             }
             enum "reject" {
               description "Reject a route";
             }
           }
         }
         leaf next {
           description "Skip to next policy or term";
           type enumeration {
             enum "policy" {
               description "Skip to next policy filter";
             }
             enum "term" {
               description "Skip to next term in a policy filter";
             }
           }
         }
         choice accept_reject {
           case case_1 {
             leaf accept {
               description "Accept a route";
               type empty;
             }
           }
           case case_2 {
             leaf reject {
               description "Reject a route";
               type empty;
             }
           }
         }
         container bgp-output-queue-priority {
           description "Set the BGP Update output queue priority.";
           choice class {
             case case_1 {
               leaf priority {
                 description "Output queue priority; higher is better";
                 type union {
                   type string {
                     pattern "<.*>|$.*";
                   }
                   type uint32 {
                     range "1 .. 16";
                   }
                 }
               }
             }
             case case_2 {
               leaf expedited {
                 description "Expedited queue; highest priority";
                 type empty;
               }
             }
           }
         }
         leaf multipath-resolve {
           description "Use all paths for resolution over this prefix";
           type empty;
         }
         leaf source-routing-path-template {
           description "Spring-te template to apply";
           type string {
           }
         }
         leaf label-allocation-fallback-reject {
           description "Suppress prefix export when label allocation fails";
           type empty;
         }
         leaf resolution-map {
           description "Set resolution map modes";
           type string;
         }
         leaf ignore-service-label {
           description "Ignore service labels";
           type empty;
         }
         container prefix-attribute-flags {
           presence "enable prefix-attribute-flags";
           description "Set ISIS prefix attribute flags sub TLV";
           uses apply-advanced;
           leaf node-segment-flag {
             description "Set node segment flag ";
             type empty;
           }
           leaf external-prefix-flag {
             description "Set external prefix flag ";
             type empty;
           }
           leaf anycast-flag {
             description "Set anycast flag ";
             type empty;
           }
           leaf entropy-label-capability-flag {
             description "Set entropy label capability flag ";
             type empty;
           }
         }
         container ipv4-source-router-id {
           presence "enable ipv4-source-router-id";
           description "Set IPv4 source router id in advertisement";
           uses apply-advanced;
           leaf router-id {
             description "Specify IPv4 address";
             type jt:ipaddr;
           }
         }
         container ipv6-source-router-id {
           presence "enable ipv6-source-router-id";
           description "Set IPv6 source router id in advertisement";
           uses apply-advanced;
           leaf router-id {
             description "Specify IPv6 address";
             type jt:ipv6addr;
           }
         }
         leaf request-long-lived-ack {
           description "Advertise route after forwarding is programmed";
           type empty;
         }
         leaf send-withdrawal-on-route-change {
           description "Withdraw route if change is not acked from forwarding";
           type empty;
         }
         container slice {
           description "Configure Policy Slice action";
           leaf slice-name {
             description "Slice Name";
             type string {
               length "1 .. 64";
             }
           }
         }
         leaf filter {
           description "Set firewall-filter name";
           type string {
           }
         }
         leaf strip-as-path {
           description "Remove the incoming BGP as-path and replace with local AS";
           type empty;
         }
         container request-acknowledgements {
           description "Set request acknowledgement";
           leaf nexthop-ack {
             description "Set nexthop acknowledgement ";
             type empty;
           }
           leaf route-ack {
             description "Set route acknowledgement ";
             type empty;
           }
         }
         container rib-export-strip {
           description "Strip attributes from a route";
           uses apply-advanced;
           leaf cluster-list {
             description "Strip cluster list from the route";
             type empty;
           }
         }
         list tunnel-termination-profile {
           key name;
           ordered-by user;
           description "Tunnel termination profiles associated with a route";
           leaf name {
             description "Name of a tunnel termination profile";
             type string;
           }
         }
         leaf flow-route-accounting {
           description "Enable accounting for flow routes";
           type empty;
         }
         leaf otc-local-role {
           description "Override local role without negotiation";
           type enumeration {
             enum "provider" {
               description "Provider role";
             }
             enum "peer" {
               description "Peer role";
             }
             enum "customer" {
               description "Customer role";
             }
             enum "route-server" {
               description "Route server role";
             }
             enum "route-server-client" {
               description "Route server client role";
             }
           }
         }
       }
     }
     list tunnel-attribute {
       key name;
       ordered-by user;
       description "BGP tunnel attributes definition";
       leaf name {
         description "Tunnel attribute name";
         type string {
         }
       }
       uses apply-advanced;
       leaf tunnel-type {
         description "Tunnel type";
         type enumeration {
           enum "ipip" {
             description "Tunnel type IP-IN-IP";
           }
           enum "udp" {
             description "Tunnel type X-IN-UDP";
           }
         }
         mandatory true;
       }
       leaf tunnel-color {
         description "Tunnel color";
         type union {
           type uint32;
           type string {
             pattern "<.*>|$.*";
           }
         }
       }
       leaf remote-end-point {
         description "Tunnel remote end point";
         type jt:ipaddr;
       }
     }
     list condition {
       key name;
       description "Define a route advertisement condition";
       leaf name {
         description "Name to identify Condition";
         type string;
       }
       uses apply-advanced;
       choice condition_type {
         case case_1 {
         }
         case case_2 {
           container if-route-exists {
             presence "enable if-route-exists";
             description "Route exists in a specific routing table";
             uses apply-advanced;
             container address-family {
               presence "enable address-family";
               description "Indicates the address family of the route to match on";
               uses apply-advanced;
               choice address-family {
                 case case_1 {
                   container inet {
                     presence "enable inet";
                     description "Route to match corresponds to an inet/inet6 prefix";
                     uses apply-advanced;
                     leaf address {
                       description "Exact address of the route";
                       type jt:ipprefix;
                       mandatory true;
                     }
                     leaf table {
                       description "Routing table in which route should exist";
                       type string;
                       mandatory true;
                     }
                   }
                 }
                 case case_2 {
                   container ccc {
                     presence "enable ccc";
                     description "Route to match corresponds to a ccc prefix";
                     uses apply-advanced;
                     leaf address {
                       description "Logical interface used to establish ccc route";
                       type union {
                         type jt:interface-name;
                         type string {
                           pattern "<.*>|$.*";
                         }
                       }
                       mandatory true;
                     }
                     leaf table {
                       description "Routing table in which route should exist";
                       type string;
                       mandatory true;
                     }
                     leaf standby {
                       description "Indicates if route must be in standby state to be considered a match";
                       type empty;
                     }
                     leaf peer-unit {
                       description "Associated LT ifl's peer-unit. Required for LT-based routes";
                       type union {
                         type string {
                           pattern "<.*>|$.*";
                         }
                         type uint32 {
                           range "0 .. 8192";
                         }
                       }
                     }
                   }
                 }
               }
             }
             leaf address {
               description "Exact address of the route";
               type jt:ipprefix;
             }
             leaf table {
               description "Routing table in which route should exist";
               type string;
             }
           }
         }
       }
     }
     list rtf-prefix-list {
       key name;
       description "Define a named set of family route target prefixes";
       leaf name {
         description "RTF prefix list name";
         type string;
       }
       uses apply-advanced;
       list prefix-list {
         key name;
         uses rtf_prefix_list_items;
       }
     }
     list resolution-map {
       key name;
       ordered-by user;
       description "Define a set of PNH resolution modes";
       leaf name {
         description "Resolution Map name";
         type string;
       }
       uses apply-advanced;
       leaf-list mode {
         ordered-by user;
         description "List of resolution modes in order that defines fallback mechanism";
         type enumeration {
           enum "ip-color" {
             description "Colored-IP PNH Resolution Mode";
           }
           enum "color-only" {
             description "Color-only PNH Resolution Mode";
           }
         }
       }
     }
     list flowspec-attribute {
       key name;
       ordered-by user;
       description "Define flowspec attributes";
       leaf name {
         description "Flowspec attribute name";
         type string;
       }
       uses apply-advanced;
       container match {
         presence "enable match";
         description "Define flowspec match attributes";
         uses apply-advanced;
         leaf destination-v6-prefix-offset {
           description "Flowspec match v6 destination prefix offset";
           type empty;
         }
         container dscp {
           presence "enable dscp";
           description "Flowspec match diffserv code point";
           uses apply-advanced;
           leaf-list value {
             ordered-by user;
             description "Dscp value";
             type union {
               type string {
                 pattern "<.*>|$.*";
               }
               type uint32 {
                 range "0 .. 2147483646";
               }
             }
           }
         }
         container fragment {
           presence "enable fragment";
           description "Flowspec match fragment";
           uses apply-advanced;
           leaf-list value {
             ordered-by user;
             description "Fragment value";
             type enumeration {
               enum "dont-fragment" {
                 description "Don't Fragment flag is set";
               }
               enum "not-a-fragment" {
                 description "Not a fragment";
               }
               enum "is-fragment" {
                 description "Fragmented packet";
               }
               enum "first-fragment" {
                 description "First fragment";
               }
               enum "last-fragment" {
                 description "Last fragment";
               }
             }
           }
         }
         container icmp-code {
           presence "enable icmp-code";
           description "Flowspec match ICMP message code";
           uses apply-advanced;
           leaf-list value {
             ordered-by user;
             description "Icmp code value";
             type string;
           }
         }
         container icmp-type {
           presence "enable icmp-type";
           description "Flowspec match ICMP type";
           uses apply-advanced;
           leaf-list value {
             ordered-by user;
             description "Icmp type value";
             type string;
           }
         }
         container icmp6-code {
           presence "enable icmp6-code";
           description "Flowspec match ICMP6 message code";
           uses apply-advanced;
           leaf-list value {
             ordered-by user;
             description "Icmp6 code value";
             type string;
           }
         }
         container icmp6-type {
           presence "enable icmp6-type";
           description "Flowspec match ICMP6 type";
           uses apply-advanced;
           leaf-list value {
             ordered-by user;
             description "Icmp6 type value";
             type string;
           }
         }
         container packet-length {
           presence "enable packet-length";
           description "Flowspec match packet length";
           uses apply-advanced;
           leaf-list value {
             ordered-by user;
             description "Packet length value";
             type union {
               type string {
                 pattern "<.*>|$.*";
               }
               type uint32 {
                 range "0 .. 2147483646";
               }
             }
           }
         }
         container protocol {
           presence "enable protocol";
           description "Flowspec match protocol";
           uses apply-advanced;
           leaf-list value {
             ordered-by user;
             description "Protocol value";
             type string;
           }
         }
         leaf source-v6-prefix-offset {
           description "Flowspec match v6 source prefix-offset";
           type empty;
         }
         container tcp-flags {
           presence "enable tcp-flags";
           description "Flowspec match tcp-flags";
           uses apply-advanced;
           leaf-list value {
             ordered-by user;
             description "Tcp-flag value";
             type string;
           }
         }
         container flow-label {
           presence "enable flow-label";
           description "Flowspec match flow-label";
           uses apply-advanced;
           leaf-list value {
             ordered-by user;
             description "Flow label value";
             type union {
               type string {
                 pattern "<.*>|$.*";
               }
               type uint32 {
                 range "0 .. 2147483646";
               }
             }
           }
         }
         leaf source {
           description "Flowspec match source";
           type empty;
         }
         leaf destination {
           description "Flowspec match destination";
           type empty;
         }
         container port {
           presence "enable port";
           description "Flowspec match port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
           container port-count {
             presence "enable port-count";
             description "Number of port values in a flowspec route";
             leaf port-count-value {
               type union {
                 type uint32;
                 type string {
                   pattern "<.*>|$.*";
                 }
               }
               mandatory true;
             }
             choice modifier {
               case case_1 {
                 leaf equal {
                   description "Equal to the port value count";
                   type empty;
                 }
               }
               case case_2 {
                 leaf orhigher {
                   description "Higher than or equal to the port value count";
                   type empty;
                 }
               }
               case case_3 {
                 leaf orlower {
                   description "Lower than or equal to the port value count";
                   type empty;
                 }
               }
             }
           }
           container range-count {
             presence "enable range-count";
             description "Number of port ranges in a flowspec route";
             leaf range-count-value {
               type union {
                 type uint32;
                 type string {
                   pattern "<.*>|$.*";
                 }
               }
               mandatory true;
             }
             choice modifier {
               case case_1 {
                 leaf equal {
                   description "Equal to the port ranges count";
                   type empty;
                 }
               }
               case case_2 {
                 leaf orhigher {
                   description "Higher than or equal to the port ranges count";
                   type empty;
                 }
               }
               case case_3 {
                 leaf orlower {
                   description "Lower than or equal to the port ranges count";
                   type empty;
                 }
               }
             }
           }
           container cumulative-count {
             presence "enable cumulative-count";
             description "Number of port values and ranges in a flowspec route";
             leaf cumulative-count-value {
               type union {
                 type uint32;
                 type string {
                   pattern "<.*>|$.*";
                 }
               }
               mandatory true;
             }
             choice modifier {
               case case_1 {
                 leaf equal {
                   description "Equal to the port value and range count";
                   type empty;
                 }
               }
               case case_2 {
                 leaf orhigher {
                   description "Higher than or equal to the port value and range count";
                   type empty;
                 }
               }
               case case_3 {
                 leaf orlower {
                   description "Lower than or equal to the port value and range count";
                   type empty;
                 }
               }
             }
           }
         }
         container destination-port {
           presence "enable destination-port";
           description "Flowspec match destination-port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
           container port-count {
             presence "enable port-count";
             description "Number of port values in a flowspec route";
             leaf port-count-value {
               type union {
                 type uint32;
                 type string {
                   pattern "<.*>|$.*";
                 }
               }
               mandatory true;
             }
             choice modifier {
               case case_1 {
                 leaf equal {
                   description "Equal to the port value count";
                   type empty;
                 }
               }
               case case_2 {
                 leaf orhigher {
                   description "Higher than or equal to the port value count";
                   type empty;
                 }
               }
               case case_3 {
                 leaf orlower {
                   description "Lower than or equal to the port value count";
                   type empty;
                 }
               }
             }
           }
           container range-count {
             presence "enable range-count";
             description "Number of port ranges in a flowspec route";
             leaf range-count-value {
               type union {
                 type uint32;
                 type string {
                   pattern "<.*>|$.*";
                 }
               }
               mandatory true;
             }
             choice modifier {
               case case_1 {
                 leaf equal {
                   description "Equal to the port ranges count";
                   type empty;
                 }
               }
               case case_2 {
                 leaf orhigher {
                   description "Higher than or equal to the port ranges count";
                   type empty;
                 }
               }
               case case_3 {
                 leaf orlower {
                   description "Lower than or equal to the port ranges count";
                   type empty;
                 }
               }
             }
           }
           container cumulative-count {
             presence "enable cumulative-count";
             description "Number of port values and ranges in a flowspec route";
             leaf cumulative-count-value {
               type union {
                 type uint32;
                 type string {
                   pattern "<.*>|$.*";
                 }
               }
               mandatory true;
             }
             choice modifier {
               case case_1 {
                 leaf equal {
                   description "Equal to the port value and range count";
                   type empty;
                 }
               }
               case case_2 {
                 leaf orhigher {
                   description "Higher than or equal to the port value and range count";
                   type empty;
                 }
               }
               case case_3 {
                 leaf orlower {
                   description "Lower than or equal to the port value and range count";
                   type empty;
                 }
               }
             }
           }
         }
         container source-port {
           presence "enable source-port";
           description "Flowspec match source-port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
           container port-count {
             presence "enable port-count";
             description "Number of port values in a flowspec route";
             leaf port-count-value {
               type union {
                 type uint32;
                 type string {
                   pattern "<.*>|$.*";
                 }
               }
               mandatory true;
             }
             choice modifier {
               case case_1 {
                 leaf equal {
                   description "Equal to the port value count";
                   type empty;
                 }
               }
               case case_2 {
                 leaf orhigher {
                   description "Higher than or equal to the port value count";
                   type empty;
                 }
               }
               case case_3 {
                 leaf orlower {
                   description "Lower than or equal to the port value count";
                   type empty;
                 }
               }
             }
           }
           container range-count {
             presence "enable range-count";
             description "Number of port ranges in a flowspec route";
             leaf range-count-value {
               type union {
                 type uint32;
                 type string {
                   pattern "<.*>|$.*";
                 }
               }
               mandatory true;
             }
             choice modifier {
               case case_1 {
                 leaf equal {
                   description "Equal to the port ranges count";
                   type empty;
                 }
               }
               case case_2 {
                 leaf orhigher {
                   description "Higher than or equal to the port ranges count";
                   type empty;
                 }
               }
               case case_3 {
                 leaf orlower {
                   description "Lower than or equal to the port ranges count";
                   type empty;
                 }
               }
             }
           }
           container cumulative-count {
             presence "enable cumulative-count";
             description "Number of port values and ranges in a flowspec route";
             leaf cumulative-count-value {
               type union {
                 type uint32;
                 type string {
                   pattern "<.*>|$.*";
                 }
               }
               mandatory true;
             }
             choice modifier {
               case case_1 {
                 leaf equal {
                   description "Equal to the port value and range count";
                   type empty;
                 }
               }
               case case_2 {
                 leaf orhigher {
                   description "Higher than or equal to the port value and range count";
                   type empty;
                 }
               }
               case case_3 {
                 leaf orlower {
                   description "Lower than or equal to the port value and range count";
                   type empty;
                 }
               }
             }
           }
         }
       }
       container invert-match {
         presence "enable invert-match";
         description "Define invert of flowspec match attributes";
         uses apply-advanced;
         leaf destination-v6-prefix-offset {
           description "Flowspec match v6 destination prefix offset";
           type empty;
         }
         container dscp {
           presence "enable dscp";
           description "Flowspec match diffserv code point";
           uses apply-advanced;
           leaf-list value {
             ordered-by user;
             description "Dscp value";
             type union {
               type string {
                 pattern "<.*>|$.*";
               }
               type uint32 {
                 range "0 .. 2147483646";
               }
             }
           }
         }
         container fragment {
           presence "enable fragment";
           description "Flowspec match fragment";
           uses apply-advanced;
           leaf-list value {
             ordered-by user;
             description "Fragment value";
             type enumeration {
               enum "dont-fragment" {
                 description "Don't Fragment flag is set";
               }
               enum "not-a-fragment" {
                 description "Not a fragment";
               }
               enum "is-fragment" {
                 description "Fragmented packet";
               }
               enum "first-fragment" {
                 description "First fragment";
               }
               enum "last-fragment" {
                 description "Last fragment";
               }
             }
           }
         }
         container icmp-code {
           presence "enable icmp-code";
           description "Flowspec match ICMP message code";
           uses apply-advanced;
           leaf-list value {
             ordered-by user;
             description "Icmp code value";
             type string;
           }
         }
         container icmp-type {
           presence "enable icmp-type";
           description "Flowspec match ICMP type";
           uses apply-advanced;
           leaf-list value {
             ordered-by user;
             description "Icmp type value";
             type string;
           }
         }
         container icmp6-code {
           presence "enable icmp6-code";
           description "Flowspec match ICMP6 message code";
           uses apply-advanced;
           leaf-list value {
             ordered-by user;
             description "Icmp6 code value";
             type string;
           }
         }
         container icmp6-type {
           presence "enable icmp6-type";
           description "Flowspec match ICMP6 type";
           uses apply-advanced;
           leaf-list value {
             ordered-by user;
             description "Icmp6 type value";
             type string;
           }
         }
         container packet-length {
           presence "enable packet-length";
           description "Flowspec match packet length";
           uses apply-advanced;
           leaf-list value {
             ordered-by user;
             description "Packet length value";
             type union {
               type string {
                 pattern "<.*>|$.*";
               }
               type uint32 {
                 range "0 .. 2147483646";
               }
             }
           }
         }
         container protocol {
           presence "enable protocol";
           description "Flowspec match protocol";
           uses apply-advanced;
           leaf-list value {
             ordered-by user;
             description "Protocol value";
             type string;
           }
         }
         leaf source-v6-prefix-offset {
           description "Flowspec match v6 source prefix-offset";
           type empty;
         }
         container tcp-flags {
           presence "enable tcp-flags";
           description "Flowspec match tcp-flags";
           uses apply-advanced;
           leaf-list value {
             ordered-by user;
             description "Tcp-flag value";
             type string;
           }
         }
         container flow-label {
           presence "enable flow-label";
           description "Flowspec match flow-label";
           uses apply-advanced;
           leaf-list value {
             ordered-by user;
             description "Flow label value";
             type union {
               type string {
                 pattern "<.*>|$.*";
               }
               type uint32 {
                 range "0 .. 2147483646";
               }
             }
           }
         }
         leaf source {
           description "Flowspec match source";
           type empty;
         }
         leaf destination {
           description "Flowspec match destination";
           type empty;
         }
         container port {
           presence "enable port";
           description "Flowspec match port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
         }
         container destination-port {
           presence "enable destination-port";
           description "Flowspec match destination-port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
         }
         container source-port {
           presence "enable source-port";
           description "Flowspec match source-port";
           uses apply-advanced;
           list port-value {
             key name;
             ordered-by user;
             description "Flowspec match port value";
             leaf name {
               type enumeration {
                 enum "exact" {
                   description "Exactly match the port value";
                 }
                 enum "contains" {
                   description "Contains the port value";
                 }
               }
             }
             leaf-list value {
               ordered-by user;
               type string;
             }
           }
           list port-range {
             key "port-range-value choice-ident choice-value";
             ordered-by user;
             description "Flowspec match port range";
             leaf port-range-value {
               description "Port range in 'x - y' format";
               type string {
               }
             }
             leaf choice-ident {
               type enumeration {
                 enum "exact" {
                 }
                 enum "contains" {
                 }
                 enum "part-of" {
                 }
               }
             }
             leaf choice-value {
               type string;
             }
           }
         }
       }
       container action {
         presence "enable action";
         description "Define flowspec action attributes";
         uses apply-advanced;
         leaf rate-limit {
           description "Flowspec action rate-limit";
           type empty;
         }
         leaf mark {
           description "Flowspec action traffic-mark";
           type empty;
         }
         leaf redirect {
           description "Flowspec action redirect-ip";
           type empty;
         }
         leaf routing-instance {
           description "Flowspec action redirect-routing-instance";
           type empty;
         }
         leaf sample {
           description "Flowspec action sample";
           type empty;
         }
       }
     }
     list tunnel-termination-profile {
       key name;
       ordered-by user;
       description "Tunnel termination profile definition";
       leaf name {
         description "Tunnel profile name";
         type string;
       }
       uses apply-advanced;
       leaf source-ip {
         description "Tunnel source address";
         type jt:ipaddr;
       }
       leaf destination-ip {
         description "Tunnel destination address";
         type jt:ipaddr;
       }
       leaf protocol {
         description "Tunnel protocol";
         type enumeration {
           enum "ip-in-ip" {
             description "Tunnel protocol IP-IN-IP";
           }
         }
         mandatory true;
       }
       leaf decap-network-instance {
         description "Decap instance name";
         type string;
       }
     }
   }
   grouping as-path-calc-length-type {
     description "Calculated BGP AS_PATH length per BGP rules";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping as-path-unique-count-type {
     description "Number of unique BGP ASes excluding confederation ASes";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping community_count_type {
     description "Number of BGP communities";
     leaf name {
       description "Number of communities";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal	values";
           type empty;
         }
       }
       case case_3 {
         leaf orlower {
           description "Match lower or equal values";
           type empty;
         }
       }
     }
   }
   grouping control_as_list_type {
     leaf list-type {
       description "Type as-list or as-list-group";
       type enumeration {
         enum "as-list" {
           description " Type as-list";
         }
         enum "as-list-group" {
           description "Type as-list-group";
         }
       }
     }
     leaf list-name {
       description "Name of as-list or as-list-group";
       type string;
     }
     uses apply-advanced;
   }
   grouping control_flowspec_attribute_type {
     leaf name {
       description "Name of flowspec-attribute";
       type string;
     }
     uses apply-advanced;
   }
   grouping control_mac_address_filter_list_type {
     leaf name {
       description "Name of mac-filter-list of macs to match";
       type string;
     }
     uses apply-advanced;
   }
   grouping control_prefix_list_filter_type {
     leaf list_name {
       description "Name of prefix-list of routes to match";
       type string;
     }
     leaf choice-ident {
       type enumeration {
         enum "exact" {
         }
         enum "longer" {
         }
         enum "orlonger" {
         }
       }
     }
     leaf choice-value {
       type string;
     }
     uses apply-advanced;
     leaf invert-match {
       description "Invert the result of the prefix-list-filter matching";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping control_prefix_list_type {
     leaf name {
       description "Name of prefix-list of routes to match";
       type string;
     }
     uses apply-advanced;
     leaf invert-match {
       description "Invert the result of the prefix-list matching";
       type empty;
     }
   }
   grouping control_rib_list_type {
     leaf name {
       description "Name of rib-list";
       type string;
     }
     uses apply-advanced;
   }
   grouping control_route_filter_list_type {
     leaf name {
       description "Name of route-filter-list of routes to match";
       type string;
     }
     uses apply-advanced;
     choice modifier {
       case case_1 {
         leaf exact {
           description "Exactly match the prefix length";
           type empty;
         }
       }
       case case_2 {
         leaf longer {
           description "Mask is greater than the prefix length";
           type empty;
         }
       }
       case case_3 {
         leaf orlonger {
           description "Mask is greater than or equal to the prefix length";
           type empty;
         }
       }
       case case_4 {
         leaf upto {
           description "Mask falls between two prefix lengths";
           type string {
           }
         }
       }
       case case_5 {
         leaf prefix-length-range {
           description "Mask falls between two prefix lengths";
           type string {
           }
         }
       }
     }
     leaf invert-match {
       description "Invert the result of the route-filter-list matching";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping control_route_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     leaf get-route-range {
       description "Get the range";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping control_rtf_prefix_list_type {
     description "RTF prefix list";
     leaf name {
       description "Name of rtf-prefix-list of routes to match";
       type string;
     }
     uses apply-advanced;
   }
   grouping control_source_address_filter_list_type {
     leaf name {
       description "Name of source-address-filter-list of routes to match";
       type string;
     }
     uses apply-advanced;
   }
   grouping control_source_address_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping fast_lookup_tuple_list_items {
     leaf name {
       description "As <destination-address>:<source-address>:<proto>:<src-port>:<dest-port>";
       type string {
       }
     }
     uses apply-advanced;
   }
   grouping juniper-port-mirror-options {
     uses apply-advanced;
     container traceoptions {
       description "Port-mirroring trace options";
       uses sampling_traceoptions_type;
     }
     leaf disable {
       description "Disable the global port-mirroring instance";
       type empty;
     }
     leaf disable-all-instances {
       description "Disable the all port-mirroring instances";
       type empty;
     }
     container input {
       description "Settings for sampling of input packets";
       uses pm_family_input_type;
     }
     container family {
       description "Address family of packets to mirror";
       container inet {
         description "Mirror IPv4 packets";
         uses apply-advanced;
         container input {
           description "Settings for sampling of input packets";
           status deprecated;
           uses pm_family_input_type;
         }
         container output {
           description "One or more next hops for port-mirrored packets";
           uses inet_pm_family_output_type;
         }
       }
       container inet6 {
         description "Mirror IPv6 packets";
         uses apply-advanced;
         container input {
           description "Settings for sampling of input packets";
           status deprecated;
           uses pm_family_input_type;
         }
         container output {
           description "One or more next hops for port-mirrored packets";
           uses inet6_pm_family_output_type;
         }
       }
       container mpls {
         description "Mirror MPLS packets";
         uses apply-advanced;
         container input {
           description "Settings for sampling of input packets";
           status deprecated;
           uses pm_family_input_type;
         }
         container output {
           description "One or more next hops for port-mirrored packets";
           uses mpls_pm_family_output_type;
         }
       }
       container vpls {
         description "Mirror Layer-2 bridged/vpls packets";
         uses apply-advanced;
         container input {
           description "Settings for sampling of input packets";
           status deprecated;
           uses pm_family_input_type;
         }
         container output {
           description "Destination for port-mirrored packets";
           uses layer2_pm_family_output_type;
         }
       }
       container ethernet-switching {
         description "Mirror Layer-2 ethernet-switched packets";
         uses apply-advanced;
         container output {
           description "Destination for port-mirrored packets";
           uses layer2_pm_family_output_type;
         }
       }
       container ccc {
         description "Mirror layer-2 ccc packets";
         uses apply-advanced;
         container input {
           description "Settings for sampling of input packets";
           status deprecated;
           uses pm_family_input_type;
         }
         container output {
           description "Destination for port-mirrored packets";
           uses layer2_pm_family_output_type;
         }
       }
     }
     list instance {
       key name;
       ordered-by user;
       description "Instance of port-mirroring parameters";
       leaf name {
         description "Name for port-mirroring instance";
         type string {
           length "1 .. 63";
         }
         mandatory true;
       }
       uses apply-advanced;
       leaf disable {
         description "Disable the this port-mirroring instance";
         type empty;
       }
       choice input_params_or_instance {
         case case_1 {
           container input {
             description "Settings for sampling of input packets";
             uses pm_family_input_type;
           }
         }
         case case_2 {
           leaf input-parameters-instance {
             description "Name of port-mirroring instance to use for input parameters";
             type string;
           }
         }
       }
       container family {
         description "Address family of packets to mirror";
         container inet {
           description "Mirror IPv4 packets";
           uses apply-advanced;
           container input {
             description "Settings for sampling of input packets";
             status deprecated;
             uses pm_family_input_type;
           }
           container output {
             description "One or more next hops for port-mirrored packets";
             uses inet_pm_family_output_type;
           }
         }
         container inet6 {
           description "Mirror IPv6 packets";
           uses apply-advanced;
           container input {
             description "Settings for sampling of input packets";
             status deprecated;
             uses pm_family_input_type;
           }
           container output {
             description "One or more next hops for port-mirrored packets";
             uses inet6_pm_family_output_type;
           }
         }
         container mpls {
           description "Mirror MPLS packets";
           uses apply-advanced;
           container input {
             description "Settings for sampling of input packets";
             status deprecated;
             uses pm_family_input_type;
           }
           container output {
             description "One or more next hops for port-mirrored packets";
             uses mpls_pm_family_output_type;
           }
         }
         container vpls {
           description "Mirror Layer-2 bridged/vpls packets";
           uses apply-advanced;
           container input {
             description "Settings for sampling of input packets";
             status deprecated;
             uses pm_family_input_type;
           }
           container output {
             description "Destination for port-mirrored packets";
             uses layer2_pm_family_output_type;
           }
         }
         container ethernet-switching {
           description "Mirror Layer-2 ethernet-switched packets";
           uses apply-advanced;
           container output {
             description "Destination for port-mirrored packets";
             uses layer2_pm_family_output_type;
           }
         }
         container ccc {
           description "Mirror layer-2 ccc packets";
           uses apply-advanced;
           container input {
             description "Settings for sampling of input packets";
             status deprecated;
             uses pm_family_input_type;
           }
           container output {
             description "Destination for port-mirrored packets";
             uses layer2_pm_family_output_type;
           }
         }
       }
     }
   }
   grouping inet6_pm_family_output_type {
     uses apply-advanced;
     choice interface-or-next-hop-index {
       case case_1 {
         list interface {
           key name;
           description "Interfaces through which to send sampled traffic";
           uses inet6_pm_intf_type;
         }
       }
       case case_2 {
       }
     }
     leaf no-filter-check {
       description "Do not check for filters on port-mirroring interface";
       type empty;
     }
     leaf ipv6-address {
       description "ERSPAN Destination IPv6 Address";
       type jt:ipv6addr;
     }
   }
   grouping inet6_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet6_next_hop_type;
     }
   }
   grouping inet6_next_hop_type {
     description "Address of next hop through which to send sampled traffic";
     leaf name {
       type jt:ipv6addr;
     }
     uses apply-advanced;
   }
   grouping inet_pm_family_output_type {
     uses apply-advanced;
     choice interface-or-next-hop-index {
       case case_1 {
         list interface {
           key name;
           description "Interfaces through which to send sampled traffic";
           uses inet_pm_intf_type;
         }
       }
       case case_2 {
       }
     }
     leaf no-filter-check {
       description "Do not check for filters on port-mirroring interface";
       type empty;
     }
     leaf ip-address {
       description "ERSPAN Destination IP Address";
       type jt:ipv4addr;
     }
     list routing-instance {
       key name;
       description "Routing instances";
       max-elements 1;
       uses inet_pm_output-routing-instance-type;
     }
   }
   grouping inet_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet_next_hop_type {
     description "Address of next hop through which to send sampled traffic";
     leaf name {
       type jt:ipv4addr;
     }
     uses apply-advanced;
   }
   grouping inet_pm_output-routing-instance-type {
     leaf name {
       description "Routing instance name";
       type string {
       }
     }
     uses apply-advanced;
     leaf ip-address {
       description "ERSPAN Destination IP Address";
       type jt:ipv4addr;
     }
   }
   grouping juniper-protocols {
     uses apply-advanced;
     container neighbor-discovery {
       presence "enable neighbor-discovery";
       description "IPv6 neighbor discovery";
       uses apply-advanced;
       leaf onlink-subnet-only {
         description "Onlink subnet only knob";
         type empty;
       }
       leaf no-dad-on-state-change {
         description "Disable DAD on interface state change";
         type empty;
       }
       container ndp-proxy {
         description "Configure NDP PROXY behaviour";
         uses apply-advanced;
         leaf no-proxy-on-resolve {
           description "Disable proxy on unresolved address";
           type empty;
         }
         leaf proxy-force-resolve {
           description "Enable Neighbor Solicitation for already learned address";
           type empty;
         }
         leaf user-route-proxy {
           description "Enable ND proxy for user routes";
           type empty;
         }
       }
       container dad-proxy {
         description "Configure DAD PROXY behaviour";
         uses apply-advanced;
         leaf no-proxy-on-resolve {
           description "Disable proxy on unresolved address";
           type empty;
         }
       }
     }
     container iccp {
       description "ICCP options";
       uses apply-advanced;
       leaf local-ip-addr {
         description "Local IP address to use by default for all peers";
         type jt:ipv4addr;
         mandatory true;
       }
       leaf session-establishment-hold-time {
         description "Time within which connection must succeed with peers";
         default "300";
         units "seconds";
         type union {
           type string {
             pattern "<.*>|$.*";
           }
           type uint32 {
             range "45 .. 600";
           }
         }
       }
       leaf authentication-key {
         description "MD5 authentication key for all peers";
         type string {
           length "1 .. 126";
         }
       }
       list peer {
         key name;
         description "Redundancy Group Configuration";
         max-elements 1;
         uses peer-group;
       }
       container traceoptions {
         description "Trace options for ICCP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     container ilmi {
       description "Interim Local Management Interface Protocol configuration";
       uses apply-advanced;
       container traceoptions {
         description "ILMI trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "database" {
                 description "Trace database events";
               }
               enum "routing-socket" {
                 description "Trace Routing socket events";
               }
               enum "state" {
                 description "Trace state change events";
               }
               enum "debug" {
                 description "Trace debug messages";
               }
               enum "event" {
                 description "Trace event handler events";
               }
               enum "packet" {
                 description "Trace packet events";
               }
               enum "all" {
                 description "Trace all areas of code";
               }
             }
           }
         }
       }
     }
     container lacp {
       description "Link Aggregation Control Protocol configuration";
       uses apply-advanced;
       container traceoptions {
         description "LACP trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Events and packet types to include in the trace";
           leaf name {
             type enumeration {
               enum "configuration" {
                 description "Configuration events";
               }
               enum "routing-socket" {
                 description "Routing socket events";
               }
               enum "process" {
                 description "Process events";
               }
               enum "startup" {
                 description "Process startup events";
               }
               enum "protocol" {
                 description "Protocol events";
               }
               enum "packet" {
                 description "LACP packets";
               }
               enum "ppm" {
                 description "LACP PPM messages";
               }
               enum "bfd" {
                 description "LACP BFD events";
               }
               enum "mc-ae" {
                 description "Multi-chassis AE messages";
               }
               enum "all" {
                 description "All events and packets";
               }
             }
           }
         }
       }
       leaf ppm {
         description "Force PPM processing";
         type enumeration {
           enum "centralized" {
             description "Centralized PPM processing";
           }
           enum "inline" {
             description "Distributed inline PPM processing";
           }
         }
       }
       container context-history {
         presence "enable context-history";
         description "LACP Context history for debugging purpose";
         uses apply-advanced;
         leaf ctxt-limit {
           description "Change limit for maximum number of entries for context history";
           default "100000";
           type union {
             type string {
               pattern "<.*>|$.*";
             }
             type uint32 {
               range "0 .. 500000";
             }
           }
         }
       }
     }
     container oam {
       description "Operation, Administration, and Management configuration";
       uses apply-advanced;
       container ethernet {
         description "OAM configuration for Ethernet";
         uses apply-advanced;
         container link-fault-management {
           description "802.3ah Ethernet OAM configuration";
           uses apply-advanced;
           container traceoptions {
             description "Trace options for link-fault management";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 units "bytes";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "action-profile" {
                     description "Trace action profile invocation events";
                   }
                   enum "all" {
                     description "Trace everything";
                   }
                 }
               }
             }
           }
           list action-profile {
             key name;
             ordered-by user;
             description "Define an action profile";
             leaf name {
               description "Name of action profile";
               type string {
                 length "1 .. 32";
               }
             }
             uses apply-advanced;
             container event {
               description "Events this action profile will check";
               uses apply-advanced;
               leaf link-adjacency-loss {
                 description "Loss of adjacency with OAM peer";
                 type empty;
               }
               leaf protocol-down {
                 description "Upper layer indication on protocol down";
                 type empty;
               }
               container link-event-rate {
                 uses apply-advanced;
                 leaf symbol-period {
                   description "Rate of receiving symbol period events";
                   units "error(s) per 100 symbol";
                   type union {
                     type string {
                       pattern "<.*>|$.*";
                     }
                     type int32 {
                       range "1 .. 100";
                     }
                   }
                 }
                 leaf frame-error {
                   description "Rate of receiving frame error events";
                   units "error(s) per 100 milli-second";
                   type union {
                     type string {
                       pattern "<.*>|$.*";
                     }
                     type int32 {
                       range "1 .. 1000";
                     }
                   }
                 }
                 leaf frame-period {
                   description "Rate of receiving frame period events";
                   units "error(s) per 100 frames";
                   type union {
                     type string {
                       pattern "<.*>|$.*";
                     }
                     type int32 {
                       range "1 .. 100";
                     }
                   }
                 }
                 leaf frame-period-summary {
                   description "Rate of receiving frame period summary events";
                   units "error(s) per second";
                   type union {
                     type string {
                       pattern "<.*>|$.*";
                     }
                     type int32 {
                       range "1 .. 1000";
                     }
                   }
                 }
               }
             }
             container action {
               description "Action to take on specified events";
               uses apply-advanced;
               leaf syslog {
                 description "Generate syslog message";
                 type empty;
               }
               leaf link-down {
                 description "Mark the interface down for transit traffic";
                 type empty;
               }
               leaf send-critical-event {
                 description "Start sending OAM PDUs with critical event bit set";
                 type empty;
               }
             }
           }
           list interface {
             key name;
             ordered-by user;
             description "Interface on which to set Ethernet OAM parameters";
             leaf name {
               description "Interface name";
               type union {
                 type jt:interface-device;
                 type string {
                   pattern "<.*>|$.*";
                 }
               }
             }
             uses apply-advanced;
             leaf-list apply-action-profile {
               ordered-by user;
               description "Apply the specified action profile on the interface";
               type string;
             }
             leaf pdu-interval {
               description "Periodic OAM protocol data unit interval";
               default "1000";
               units "milliseconds";
               type union {
                 type string {
                   pattern "<.*>|$.*";
                 }
                 type int32 {
                   range "100 .. 1000";
                 }
               }
             }
             leaf loopback-tracking {
               description "Enable link down on loopback detection";
               type empty;
             }
             leaf detect-loc {
               description "Detects initial lack of adjacency formation";
               type empty;
             }
             leaf link-discovery {
               description "Mode of discovery";
               default "active";
               type enumeration {
                 enum "active" {
                 }
                 enum "passive" {
                 }
               }
             }
             leaf pdu-threshold {
               description "Number of PDUs missed before declaring peer lost";
               default "3";
               type union {
                 type string {
                   pattern "<.*>|$.*";
                 }
                 type int32;
               }
             }
             leaf remote-loopback {
               description "Put remote DTE into remote-loopback mode";
               type empty;
             }
             container negotiation-options {
               description "802.3ah features supported on the interface";
               uses apply-advanced;
               leaf no-allow-link-events {
                 description "Do not emit periodic PDUs detailing framing and symbol errors";
                 type empty;
               }
               leaf allow-remote-loopback {
                 description "Allow local port to be put into loopback mode";
                 type empty;
               }
             }
             container event-thresholds {
               description "Thresholds for sending 802.3ah events";
               uses apply-advanced;
               leaf symbol-period {
                 description "Threshold for sending symbol period events";
                 default "1";
                 type union {
                   type string {
                     pattern "<.*>|$.*";
                   }
                   type int32 {
                     range "0 .. 100";
                   }
                 }
               }
               leaf frame-error {
                 description "Threshold for sending frame error events";
                 default "1";
                 type union {
                   type string {
                     pattern "<.*>|$.*";
                   }
                   type int32 {
                     range "0 .. 100";
                   }
                 }
               }
               leaf frame-period {
                 description "Threshold for sending frame period error events";
                 default "1";
                 type union {
                   type string {
                     pattern "<.*>|$.*";
                   }
                   type int32 {
                     range "0 .. 100";
                   }
                 }
               }
               leaf frame-period-summary {
                 description "Threshold for sending frame period summary error events";
                 default "1";
                 type union {
                   type string {
                     pattern "<.*>|$.*";
                   }
                   type int32 {
                     range "0 .. 100";
                   }
                 }
               }
             }
           }
         }
         container connectivity-fault-management {
           description "Configurations related to 802.1ag ethernet oam";
           uses apply-advanced;
           container performance-monitoring {
             description "Configurations related to ethernet performance monitoring";
             uses apply-advanced;
             leaf hardware-assisted-timestamping {
               description "Enable timestamping feature in hardware";
               type empty;
             }
             leaf delegate-server-processing {
               description "Delegate performance measurement request handling to PFE";
               type empty;
             }
             leaf hardware-assisted-keepalives {
               description "Enable/Disable delegating keepalives to hardware";
               type enumeration {
                 enum "enable" {
                   description "Enable delegate keepalives handling to Hardware";
                 }
                 enum "disable" {
                   description "Disable delegate keepalives handling to Hardware (default)";
                 }
               }
             }
             leaf hardware-assisted-pm {
               description "Enable inline support for performance monitoring";
               type empty;
             }
             leaf enhanced-sla-iterator {
               description "Enable Enhanced SLA Iterator Cycle-time";
               type empty;
             }
             leaf measurement-interval {
               description "Enables measurement-interval based PM (MEF 36 mode). Default 15 min in enhanced-cfm-mode";
               units "minutes";
               type enumeration {
                 enum "2" {
                   description "2 minutes measurement interval";
                 }
                 enum "5" {
                   description "5 minutes measurement interval";
                 }
                 enum "15" {
                   description "15 minutes measurement interval";
                 }
                 enum "30" {
                   description "30 minutes measurement interval";
                 }
                 enum "60" {
                   description "1 hour measurement interval";
                 }
               }
             }
             leaf legacy-pm-display {
               description "Display Legacy PM output (for DM) in MEF mode.";
               type empty;
             }
             list sla-iterator-profiles {
               key name;
               ordered-by user;
               description "Configuration related to an sla monitoring iterator";
               leaf name {
                 type string;
               }
               uses apply-advanced;
               leaf disable {
                 description "Disable the iterator profile";
                 type empty;
               }
               leaf measurement-type {
                 description "Choice of the type of Y.1731(SLA measurement) frame to be sent";
                 type enumeration {
                   enum "two-way-delay" {
                     description "Y.1731 2-way DM frames are sent for this profile";
                   }
                   enum "loss" {
                     description "Y.1731 LM frames are sent for this profile";
                   }
                   enum "slm" {
                     description "Y.1731 SLM frames are sent for this profile";
                   }
                   enum "statistical-frame-loss" {
                     description "Y.1731 2-way DM frames for statistical frame loss are sent for this profile";
                   }
                 }
                 mandatory true;
               }
               leaf flap-trap-monitor {
                 description "Configurable timer value 1-360";
                 units "seconds";
                 type union {
                   type string {
                     pattern "<.*>|$.*";
                   }
                   type uint32 {
                     range "1 .. 360";
                   }
                 }
               }
               leaf cycle-time {
                 description "Time period of an iterator profile";
                 default "1000";
                 units "milliseconds";
                 type union {
                   type string {
                     pattern "<.*>|$.*";
                   }
                   type uint32;
                 }
               }
               leaf iteration-period {
                 description "Maximum services under this iterator profile";
                 default "2000";
                 units "connections";
                 type union {
                   type string {
                     pattern "<.*>|$.*";
                   }
                   type uint32 {
                     range "1 .. 2000";
                   }
                 }
               }
               container calculation-weight {
                 presence "enable calculation-weight";
                 description "Configure delay and delay variation calculation weight";
                 uses apply-advanced;
                 leaf delay {
                   description "Weight used in delay calculation";
                   default "1";
                   type union {
                     type string {
                       pattern "<.*>|$.*";
                     }
                     type uint32 {
                       range "1 .. 65535";
                     }
                   }
                 }
                 leaf delay-variation {
                   description "Weight used in delay-variation calculation";
                   default "1";
                   type union {
                     type string {
                       pattern "<.*>|$.*";
                     }
                     type uint32 {
                       range "1 .. 65535";
                     }
                   }
                 }
               }
               container avg-flr-forward-threshold {
                 presence "enable avg-flr-forward-threshold";
                 description "Avg forward flr threshold";
                 uses apply-advanced;
                 leaf avg-flr-forward {
                   description "Avg forward flr threshold value in mili-percent";
                   type union {
                     type string {
                       pattern "<.*>|$.*";
                     }
                     type uint32 {
                       range "1 .. 100000";
                     }
                   }
                   mandatory true;
                 }
                 leaf flap-trap-monitor {
                   description "Configurable timer value 1-360";
                   units "seconds";
                   type union {
                     type string {
                       pattern "<.*>|$.*";
                     }
                     type uint32 {
                       range "1 .. 360";
                     }
                   }
                 }
               }
               container avg-flr-backward-threshold {
                 presence "enable avg-flr-backward-threshold";
                 description "Avg backward flr threshold";
                 uses apply-advanced;
                 leaf avg-flr-backward {
                   description "Avg backward flr threshold value in mili-percent";
                   type union {
                     type string {
                       pattern "<.*>|$.*";
                     }
                     type uint32 {
                       range "1 .. 100000";
                     }
                   }
                   mandatory true;
                 }
                 leaf flap-trap-monitor {
                   description "Configurable timer value 1-360";
                   units "seconds";
                   type union {
                     type string {
                       pattern "<.*>|$.*";
                     }
                     type uint32 {
                       range "1 .. 360";
                     }
                   }
                 }
               }
               container avg-fd-twoway-threshold {
                 presence "enable avg-fd-twoway-threshold";
                 description "Avg frame delay threshold value";
                 uses apply-advanced;
                 leaf avg-fd-twoway {
                   description "Avg frame delay threshold value in mili-percent";
                   units "microseconds";
                   type union {
                     type string {
                       pattern "<.*>|$.*";
                     }
                     type uint32 {
                       range "1 .. 4294967295";
                     }
                   }
                   mandatory true;
                 }
                 leaf flap-trap-monitor {
                   description "Configurable timer value 1-360";
                   units "seconds";
                   type union {
                     type string {
                       pattern "<.*>|$.*";
                     }
                     type uint32 {
                       range "1 .. 360";
                     }
                   }
                 }
               }
               container avg-fdv-twoway-threshold {
                 presence "enable avg-fdv-twoway-threshold";
                 description "Avg frame delay variance threshold";
                 uses apply-advanced;
                 leaf avg-fdv-twoway {
                   description "Avg frame delay variance threshold value in mili-percent";
                   units "microseconds";
                   type union {
                     type string {
                       pattern "<.*>|$.*";
                     }
                     type uint32 {
                       range "1 .. 4294967295";
                     }
                   }
                   mandatory true;
                 }
                 leaf flap-trap-monitor {
                   description "Configurable timer value 1-360";
                   units "seconds";
                   type union {
                     type string {
                       pattern "<.*>|$.*";
                     }
                     type uint32 {
                       range "1 .. 360";
                     }
                   }
                 }
               }
               container frame-delay {
                 description "Bin configuration for frame delay";
                 uses apply-advanced;
                 leaf num-bins {
                   description "Max number of bins";
                   type union {
                     type string {
                       pattern "<.*>|$.*";
                     }
                     type uint32 {
                       range "2 .. 5";
                     }
                   }
                   mandatory true;
                 }
                 container two-way {
                   presence "enable two-way";
                   description "Bin configuration for 2way frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
               container frame-delay-range {
                 description "Bin configuration for frame delay range";
                 uses apply-advanced;
                 leaf num-bins {
                   description "Max number of bins";
                   type union {
                     type string {
                       pattern "<.*>|$.*";
                     }
                     type uint32 {
                       range "2 .. 5";
                     }
                   }
                   mandatory true;
                 }
                 container two-way {
                   presence "enable two-way";
                   description "Bin configuration for 2way frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
               container ifdv {
                 description "Bin configuration for IFDV";
                 uses apply-advanced;
                 leaf num-bins {
                   description "Max number of bins";
                   type union {
                     type string {
                       pattern "<.*>|$.*";
                     }
                     type uint32 {
                       range "2 .. 5";
                     }
                   }
                   mandatory true;
                 }
                 container two-way {
                   presence "enable two-way";
                   description "Bin configuration for 2way IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
             }
             list interface {
               key name;
               ordered-by user;
               description "Name of interface for the performance monitoring";
               leaf name {
                 description "Interface name";
                 type union {
                   type jt:interface-unit;
                   type string {
                     pattern "<.*>|$.*";
                   }
                 }
               }
               leaf enable-multiclass-loss-measurement {
                 description "Disable multiclass loss measurement in hardware";
                 type empty;
               }
               leaf code-point-based-lm-accounting {
                 description "Enable code point based loss measurement in hardware";
                 type empty;
               }
               leaf priority-based-lm-accounting {
                 description "Enable priority based loss measurement in hardware";
                 type empty;
               }
             }
             leaf enable-multiclass-loss-measurement {
               description "Disable multiclass loss measurement in hardware";
               type empty;
             }
             leaf code-point-based-lm-accounting {
               description "Enable code point based loss measurement in hardware";
               type empty;
             }
             leaf priority-based-lm-accounting {
               description "Enable priority based loss measurement in hardware";
               type empty;
             }
             leaf colorless-loss-measurement {
               description "Enable colorless loss measurement in hardware";
               type empty;
             }
           }
           leaf no-aggregate-delegate-processing {
             description "Do not distribute aggregate session to pfe";
             type empty;
           }
           leaf enhanced-cfm-mode {
             description "Enables Enhanced CFM Mode";
             type empty;
           }
           container traceoptions {
             description "Trace options for connectivity fault management";
             presence "enable traceoptions";
             uses cfm-traceoptions;
           }
           list action-profile {
             key name;
             ordered-by user;
             description "Action profiles to use when one or more remote maintenance association endpoints are down";
             leaf name {
               description "Name of action profile";
               type string;
             }
             uses apply-advanced;
             container event {
               description "Events that need to be monitored";
               uses apply-advanced;
               leaf-list interface-status-tlv {
                 ordered-by user;
                 description "Values that need to be monitored in interface status TLV";
                 type enumeration {
                   enum "down" {
                     description "Interface is administratively down";
                   }
                   enum "lower-layer-down" {
                     description "Interface is physically down";
                   }
                 }
               }
               leaf-list port-status-tlv {
                 ordered-by user;
                 description "Values that need to be monitored in port status TLV";
                 type enumeration {
                   enum "blocked" {
                     description "Port is blocked";
                   }
                 }
               }
               leaf adjacency-loss {
                 description "Connectivity is lost";
                 type empty;
               }
               leaf rdi {
                 description "RDI received from some MEP";
                 type empty;
               }
               leaf connection-protection-tlv {
                 description "Values that need to be monitored in connection protection TLV";
                 type enumeration {
                   enum "using-working-path" {
                     description "Service traffic is using working path";
                   }
                   enum "using-protection-path" {
                     description "Service traffic is using protection path";
                   }
                 }
               }
             }
             container action {
               uses apply-advanced;
               leaf interface-down {
                 description "Mark the interface as down";
                 type empty;
               }
               leaf revertive-interface-down {
                 description "Wait for CC loss-threshold to bring back the interface up";
                 type empty;
               }
               leaf non-revertive-interface-down {
                 description "Interface will not be brought up when CC is received";
                 type empty;
               }
               leaf propagate-remote-mac-flush {
                 description "Remote mac-flush";
                 type empty;
               }
               leaf interface-group-down {
                 description "Mark the interface group as down";
                 type empty;
               }
               leaf asynchronous-notification {
                 description "Generate asynchronous notification (Laser-off for optical phys)";
                 type empty;
               }
               container log-and-generate-ais {
                 uses apply-advanced;
                 leaf-list level {
                   description "Server maintenance domain levels range";
                   type union {
                     type string {
                       pattern "<.*>|$.*";
                     }
                     type uint32 {
                       range "1 .. 7";
                     }
                   }
                 }
                 leaf interval {
                   description "Interval between AIS messages";
                   default "1s";
                   type enumeration {
                     enum "1s" {
                     }
                     enum "1m" {
                     }
                   }
                 }
                 leaf priority {
                   description "802.1p priority of AIS packet";
                   default "0";
                   type union {
                     type string {
                       pattern "<.*>|$.*";
                     }
                     type uint32 {
                       range "0 .. 7";
                     }
                   }
                 }
               }
             }
             container clear-action {
               uses apply-advanced;
               container interface-down {
                 description "Mark the interface as down";
                 leaf peer-interface {
                   description "Mark the interface as down";
                   type empty;
                 }
               }
               leaf propagate-remote-mac-flush {
                 description "Remote  mac flush";
                 type empty;
               }
             }
             container default-actions {
               description "Action that needs to be taken";
               uses apply-advanced;
               leaf interface-down {
                 description "Bring the interface down";
                 type empty;
               }
             }
           }
           container policer {
             description "Rate limit Ethernet OAM packets for all sessions";
             uses apply-advanced;
             leaf continuity-check {
               description "Policer to rate limit Continuity Check Ethernet OAM messages";
               type string;
             }
             leaf other {
               description "Policer to rate limit non Continuity Check Ethernet OAM messages";
               type string;
             }
             leaf all {
               description "Policer to rate limit all Ethernet OAM messages";
               type string;
             }
           }
           container linktrace {
             presence "enable linktrace";
             description "Linktrace protocol global options";
             uses apply-advanced;
             leaf path-database-size {
               description "Number of linktrace reply entries to be stored per linktrace request";
               default "100";
               type union {
                 type string {
                   pattern "<.*>|$.*";
                 }
                 type uint32 {
                   range "1 .. 255";
                 }
               }
             }
             leaf age {
               description "Time after which a stale request-response entry is deleted";
               default "10m";
               type enumeration {
                 enum "10s" {
                 }
                 enum "30s" {
                 }
                 enum "1m" {
                 }
                 enum "10m" {
                 }
                 enum "30m" {
                 }
               }
             }
           }
           container context-history {
             presence "enable context-history";
             description "Context history limit (0..5000000)";
             uses apply-advanced;
             leaf ctxt-limit {
               description "Context history limit [...] ";
               type union {
                 type string {
                   pattern "<.*>|$.*";
                 }
                 type uint32 {
                   range "0 .. 5000000";
                 }
               }
             }
           }
           list maintenance-domain {
             key name;
             description "Maintenance domain configuration";
             leaf name {
               type string;
             }
             uses apply-advanced;
             list bridge-domain {
               key name;
               ordered-by user;
               description "Bridge-domain information for the default maintenance domain";
               leaf name {
                 description "Bridge domain name";
                 type string;
               }
               leaf-list vlan-id {
                 ordered-by user;
                 description "VLAN id";
                 type string;
               }
             }
             list virtual-switch {
               key name;
               ordered-by user;
               description "Virtual switch Bridge-domain information for the default maintenance domain";
               leaf name {
                 description "Routing instance of type virtual switch";
                 type string;
               }
               uses apply-advanced;
               list bridge-domain {
                 key name;
                 ordered-by user;
                 leaf name {
                   description "Bridge domain name";
                   type string;
                 }
                 leaf-list vlan-id {
                   ordered-by user;
                   description "VLAN id";
                   type string;
                 }
               }
             }
             list instance {
               key name;
               ordered-by user;
               description "VPLS instance name for the default maintenance domain";
               leaf name {
                 description "VPLS routing instance name";
                 type string;
               }
             }
             list interface {
               key name;
               ordered-by user;
               description "Name of interface for the default maintenance domain";
               leaf name {
                 description "Interface name";
                 type union {
                   type jt:interface-unit;
                   type string {
                     pattern "<.*>|$.*";
                   }
                 }
               }
             }
             leaf level {
               description "Level value for maintenance domain";
               type union {
                 type string {
                   pattern "<.*>|$.*";
                 }
                 type uint8 {
                   range "0 .. 7";
                 }
               }
             }
             leaf name-format {
               description "Format of maintenance domain name";
               type enumeration {
                 enum "none" {
                   description "No format specified";
                 }
                 enum "dns" {
                   description "Character string similar to Domain Name System name";
                 }
                 enum "mac+2oct" {
                   description "MAC address with 2 octet integer (xx:xx:xx:xx:xx:xx.Y format)";
                 }
                 enum "character-string" {
                   description "Character string";
                 }
               }
             }
             leaf mip-half-function {
               description "Half function to be implemented by MIP";
               default "none";
               type enumeration {
                 enum "none" {
                   description "No MHFs should be created";
                 }
                 enum "default" {
                   description "Create MHF as per IEEE 802.1ag specifications for defMHFDefault";
                 }
                 enum "explicit" {
                   description "Create MHF as per IEEE 802.1ag specifications for defMHFExplicit";
                 }
               }
             }
             list maintenance-association {
               key name;
               description "Maintenance association configuration";
               leaf name {
                 description "Name of maintenance association in IEEE compliant format";
                 type string {
                   length "1 .. 45";
                 }
               }
               uses apply-advanced;
               leaf debug-session {
                 description "Debug the CFM session";
                 type empty;
               }
               leaf short-name-format {
                 description "Format of Maintenance Association Name";
                 type enumeration {
                   enum "2octet" {
                     description "An integer in the range 0..65535";
                   }
                   enum "rfc-2685-vpn-id" {
                     description "VPN identifier that complies with RFC 2685";
                   }
                   enum "vlan" {
                     description "Primary VLAN identifier";
                   }
                   enum "character-string" {
                     description "Character string";
                   }
                   enum "icc" {
                     description "ITU Carrier Code";
                   }
                 }
               }
               leaf primary-vid {
                 description "VLAN id";
                 type string;
               }
               container continuity-check {
                 presence "enable continuity-check";
                 description "Continuity check configuration";
                 uses apply-advanced;
                 leaf interval {
                   description "Interval between continuity-check messages";
                   default "1m";
                   type enumeration {
                     enum "10ms" {
                     }
                     enum "100ms" {
                     }
                     enum "1s" {
                     }
                     enum "10s" {
                     }
                     enum "1m" {
                     }
                     enum "10m" {
                     }
                     enum "3.3ms" {
                     }
                   }
                 }
                 leaf loss-threshold {
                   description "Number of continuity-check messages lost before marking endpoint as down";
                   default "3";
                   type union {
                     type string {
                       pattern "<.*>|$.*";
                     }
                     type uint32 {
                       range "3 .. 256";
                     }
                   }
                 }
                 leaf hold-interval {
                   description "Time before flushing MEP database if no updates occur";
                   default "10";
                   units "minutes";
                   type union {
                     type string {
                       pattern "<.*>|$.*";
                     }
                     type uint32 {
                       range "1 .. 30240";
                     }
                   }
                 }
                 leaf port-status-tlv {
                   description "Include port status TLV in CCM";
                   type empty;
                 }
                 leaf interface-status-tlv {
                   description "Include interface status TLV in CCM";
                   type empty;
                 }
                 leaf connection-protection-tlv {
                   description "Include connection protection OUI TLV in CCM";
                   type empty;
                 }
                 leaf convey-loss-threshold {
                   description "Include Loss Threshold OUI TLV in CCM";
                   type empty;
                 }
                 leaf interface-status-send-rdi {
                   description "Send RDI on interface operation status down in CCM";
                   type empty;
                 }
                 leaf ignore-cfm-interface-status-ap {
                   description "Ignore AP cfm interface status";
                   type empty;
                 }
                 container sendid-tlv {
                   description "Include sendid-tlv in CCM/LBM/LTM";
                   uses apply-advanced;
                   leaf send-chassis-tlv {
                     description "Attach Chassis ID & Mgmt Addr to CCM/LBM/LTM";
                     type empty;
                   }
                 }
               }
               leaf mip-half-function {
                 description "Half function to be implemented by MIP";
                 default "defer";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                   enum "defer" {
                     description "Create MHF as per IEEE 802.1ag specifications for defMHFDefer";
                   }
                 }
               }
               list mep {
                 key name;
                 ordered-by user;
                 description "Maintenance association endpoint configuration";
                 leaf name {
                   description "Identifier for maintenance association endpoint";
                   type union {
                     type string {
                       pattern "<.*>|$.*";
                     }
                     type uint16 {
                       range "1 .. 8191";
                     }
                   }
                 }
                 uses apply-advanced;
                 container interface {
                   presence "enable interface";
                   description "Name of interface";
                   leaf interface-name {
                     type union {
                       type jt:interface-unit;
                       type string {
                         pattern "<.*>|$.*";
                       }
                     }
                     mandatory true;
                   }
                   leaf vlan {
                     description "Trunk port interface VLAN identifier";
                     type union {
                       type string {
                         pattern "<.*>|$.*";
                       }
                       type uint32 {
                         range "1 .. 4094";
                       }
                     }
                   }
                   choice connection-type {
                     case case_1 {
                       leaf working {
                         description "Monitory the primary path";
                         type empty;
                       }
                     }
                     case case_2 {
                       leaf protect {
                         description "Monitory the protect path";
                         type empty;
                       }
                     }
                   }
                 }
                 leaf direction {
                   description "Direction of maintenance endpoint";
                   default "down";
                   type enumeration {
                     enum "up" {
                     }
                     enum "down" {
                     }
                   }
                 }
                 leaf priority {
                   description "802.1p priority of continuity-check and link-trace packet";
                   default "0";
                   type union {
                     type string {
                       pattern "<.*>|$.*";
                     }
                     type uint32 {
                       range "0 .. 7";
                     }
                   }
                 }
                 leaf auto-discovery {
                   description "Accept continuity-check messages from all remote MEPs";
                   type empty;
                 }
                 leaf action-profile {
                   description "Name of the action profile";
                   type string;
                 }
                 list remote-mep {
                   key name;
                   ordered-by user;
                   description "Remote maintenance association endpoint configuration";
                   leaf name {
                     description "Identifier for remote maintenance association endpoint";
                     type union {
                       type string {
                         pattern "<.*>|$.*";
                       }
                       type uint16 {
                         range "1 .. 8191";
                       }
                     }
                   }
                   uses apply-advanced;
                   leaf action-profile {
                     description "Name of the action profile";
                     type string;
                   }
                   container interface-group {
                     presence "enable interface-group";
                     description "Mark this interface group down Profile configured with action interface-group-down";
                     uses apply-advanced;
                     leaf interface-device-name {
                       description "Interface device name";
                       type union {
                         type jt:interface-device;
                         type string {
                           pattern "<.*>|$.*";
                         }
                       }
                     }
                     leaf-list unit-list {
                       description "One or more logical interface unit numbers";
                       type jt:range;
                     }
                   }
                   list sla-iterator-profile {
                     key name;
                     ordered-by user;
                     description "Name of the iterator profile";
                     leaf name {
                       type string;
                     }
                     uses apply-advanced;
                     leaf iteration-count {
                       description "Iterations to partake for acquiring SLA measurements";
                       units "frames";
                       type union {
                         type string {
                           pattern "<.*>|$.*";
                         }
                         type uint32 {
                           range "1 .. 65535";
                         }
                       }
                     }
                     leaf priority {
                       description "The vlan pcp value to be sent in the Y.1731 frame";
                       type union {
                         type string {
                           pattern "<.*>|$.*";
                         }
                         type uint32 {
                           range "0 .. 7";
                         }
                       }
                     }
                     leaf data-tlv-size {
                       description "Size of the data-tlv portion of Y.1731 frame";
                       units "bytes";
                       type union {
                         type string {
                           pattern "<.*>|$.*";
                         }
                         type uint32 {
                           range "1 .. 1400";
                         }
                       }
                     }
                   }
                   leaf detect-loc {
                     description "Detects initial loss of connectivity with remote mep";
                     type empty;
                   }
                 }
                 leaf lowest-priority-defect {
                   description "Lowest priority defect that is allowed to generate a fault alarm";
                   type enumeration {
                     enum "all-defects" {
                       description "Allows all defects";
                     }
                     enum "mac-rem-err-xcon" {
                       description "Allows only MAC, not receiving CCM, erroneous CCM and cross connect defects";
                     }
                     enum "rem-err-xcon" {
                       description "Allows only not receiving CCM, erroneous CCM and cross connect CCM defects";
                     }
                     enum "err-xcon" {
                       description "Allows only erroneous CCM and cross connect CCM defects";
                     }
                     enum "xcon" {
                       description "Allows only cross connect CCM defect";
                     }
                     enum "no-defect" {
                       description "Allows no defect";
                     }
                   }
                 }
               }
               container policer {
                 description "Rate limit Ethernet OAM packets for this session";
                 uses apply-advanced;
                 leaf continuity-check {
                   description "Policer to rate limit Continuity Check Ethernet OAM messages";
                   type string;
                 }
                 leaf other {
                   description "Policer to rate limit non Continuity Check Ethernet OAM messages";
                   type string;
                 }
                 leaf all {
                   description "Policer to rate limit all Ethernet OAM messages";
                   type string;
                 }
               }
             }
           }
           container sendid-tlv {
             description "Include sendid-tlv in CCM/LBM/LTM";
             uses apply-advanced;
             leaf send-chassis-tlv {
               description "Attach Chassis ID & Mgmt Addr to CCM/LBM/LTM";
               type empty;
             }
           }
         }
         list evcs {
           key name;
           description "Ethernet virtual circuits configuration";
           leaf name {
             description "EVC id";
             type string {
               length "1 .. 100";
             }
           }
           uses apply-advanced;
           container evc-protocol {
             description "Signaling protocol to monitor EVC status";
             choice protocol {
               case case_1 {
                 container cfm {
                   presence "enable cfm";
                   description "Connectivity fault management";
                   leaf maintenance-domain {
                     description "Maintenance domain name";
                     type string;
                     mandatory true;
                   }
                   leaf maintenance-association {
                     description "Maintenance association name";
                     type string;
                     mandatory true;
                   }
                   leaf mep {
                     description "Identifier for maintenance association endpoint";
                     type union {
                       type string {
                         pattern "<.*>|$.*";
                       }
                       type uint16 {
                         range "1 .. 8191";
                       }
                     }
                     mandatory true;
                   }
                 }
               }
               case case_2 {
                 container vpls {
                   presence "enable vpls";
                   description "Virtual private LAN service (BGP/LDP)";
                   leaf routing-instance {
                     description "Routing instance name";
                     type string;
                     mandatory true;
                   }
                 }
               }
               case case_3 {
               }
               case case_4 {
               }
             }
           }
           leaf remote-uni-count {
             description "Number of remote UNIs in the EVC";
             default "1";
             type union {
               type string {
                 pattern "<.*>|$.*";
               }
               type uint8 {
                 range "1 .. 255";
               }
             }
           }
           leaf multipoint-to-multipoint {
             description "Multipoint to Multipoint EVC";
             type empty;
           }
         }
         container lmi {
           presence "enable lmi";
           description "Ethernet local management interface configuration";
           uses apply-advanced;
           container traceoptions {
             description "Trace options for ethernet local management interface";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 units "bytes";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "init" {
                     description "Trace events related to protocol daemon start-up";
                   }
                   enum "error" {
                     description "Trace events related to catestrophic errors in daemon";
                   }
                   enum "packet" {
                     description "Trace events related to packet flow";
                   }
                   enum "all" {
                     description "Trace everything";
                   }
                 }
               }
             }
           }
           leaf status-counter {
             description "E-LMI status counter (N393)";
             default "4";
             type union {
               type string {
                 pattern "<.*>|$.*";
               }
               type uint8 {
                 range "2 .. 10";
               }
             }
           }
           leaf polling-verification-timer {
             description "Polling verification timer (T392)";
             default "15";
             units "seconds";
             type union {
               type string {
                 pattern "<.*>|$.*";
               }
               type uint8 {
                 range "5 .. 30";
               }
             }
           }
           list interface {
             key name;
             description "Interface options";
             leaf name {
               type union {
                 type jt:interface-device;
                 type string {
                   pattern "<.*>|$.*";
                 }
               }
             }
             uses apply-advanced;
             leaf uni-id {
               description "UNI identifier";
               type string {
                 length "1 .. 64";
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             leaf evc-map-type {
               description "CE-VLAN ID/EVC map type";
               default "bundling";
               type enumeration {
                 enum "all-to-one-bundling" {
                   description "All to one bundling";
                 }
                 enum "service-multiplexing" {
                   description "Service multiplexing with no bundling";
                 }
                 enum "bundling" {
                   description "Bundling with service multiplexing";
                 }
               }
             }
             list evc {
               key name;
               description "EVC configuration";
               leaf name {
                 description "EVC identifier";
                 type string {
                   length "1 .. 100";
                 }
               }
               uses apply-advanced;
               leaf default-evc {
                 description "Default EVC";
                 type empty;
               }
               leaf-list vlan-list {
                 description "Vlans mapped to this EVC";
                 type jt:vlan-range;
               }
             }
           }
         }
         container fnp {
           presence "enable fnp";
           description "Failure notification protocol configuration";
           uses apply-advanced;
           container traceoptions {
             description "Tracing options for FNP";
             uses apply-advanced;
             container file {
               description "Trace file options";
               leaf filename {
                 description "Name of file in which to write trace information";
                 type string {
                   length "1 .. 1024";
                 }
                 mandatory true;
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "events" {
                     description "Trace protocol events";
                   }
                   enum "pdu" {
                     description "Trace PDU reception and transmission";
                   }
                   enum "timers" {
                     description "Trace protocol timers";
                   }
                   enum "error" {
                     description "Trace all failure conditions";
                   }
                   enum "all" {
                     description "Trace all";
                   }
                 }
               }
             }
           }
           leaf interval {
             description "Interval between FNP messages";
             default "1s";
             type enumeration {
               enum "100ms" {
               }
               enum "1s" {
               }
               enum "10s" {
               }
               enum "1m" {
               }
               enum "10m" {
               }
             }
           }
           leaf loss-threshold {
             description "Number of FNP messages lost before clearing FNP state";
             default "4";
             type union {
               type string {
                 pattern "<.*>|$.*";
               }
               type uint8 {
                 range "3 .. 255";
               }
             }
           }
           list interface {
             key name;
             ordered-by user;
             description "Interface configuration";
             leaf name {
               type union {
                 type jt:interface-name;
                 type string {
                   pattern "<.*>|$.*";
                 }
               }
             }
             uses apply-advanced;
             leaf domain-id {
               description "Ethernet domain identifier";
               default "0";
               type union {
                 type uint32;
                 type string {
                   pattern "<.*>|$.*";
                 }
               }
             }
           }
         }
       }
     }
     container vrrp {
       description "VRRP options";
       uses apply-advanced;
       container traceoptions {
         description "Trace options for VRRP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "0 .. 4294967295";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
           leaf microsecond-stamp {
             description "Timestamp with microsecond granularity";
             type empty;
           }
         }
         list flag {
           key name;
           ordered-by user;
           description "Tracing parameters";
           leaf name {
             type enumeration {
               enum "database" {
                 description "Trace database";
               }
               enum "general" {
                 description "Trace general events";
               }
               enum "interfaces" {
                 description "Trace interface messages";
               }
               enum "normal" {
                 description "Trace normal events";
               }
               enum "packets" {
                 description "Trace packets";
               }
               enum "state" {
                 description "Trace state transitions";
               }
               enum "timer" {
                 description "Trace timer events";
               }
               enum "ppm" {
                 description "VRRP PPM related messages";
               }
               enum "all" {
                 description "Trace all events";
               }
             }
           }
         }
       }
       leaf failover-delay {
         description "Additional failover delay timer";
         units "milliseconds";
         type union {
           type string {
             pattern "<.*>|$.*";
           }
           type uint32 {
             range "50 .. 100000";
           }
         }
       }
       container context-history {
         presence "enable context-history";
         description "VRRP Context history for debugging purpose";
         uses apply-advanced;
         leaf max-limit {
           description "Change limit for maximum number of entries for context history";
           default "20000";
           type union {
             type string {
               pattern "<.*>|$.*";
             }
             type uint32 {
               range "0 .. 100000";
             }
           }
         }
       }
       leaf startup-silent-period {
         description "Period for ignoring master down timer at device startup";
         units "seconds";
         type union {
           type string {
             pattern "<.*>|$.*";
           }
           type uint32 {
             range "1 .. 2000";
           }
         }
       }
       leaf asymmetric-hold-time {
         description "Priority hold time asymmetric behaviour";
         type empty;
       }
       container delegate-processing {
         presence "enable delegate-processing";
         description "Switch to distributed PPMD";
         uses apply-advanced;
       }
       leaf skew-timer-disable {
         description "Disable the skew timer";
         type empty;
       }
       leaf global-advertisements-threshold {
         description "Number of vrrp advertisements missed before declaring master down";
         default "3";
         type union {
           type string {
             pattern "<.*>|$.*";
           }
           type uint32 {
             range "1 .. 15";
           }
         }
       }
       leaf inherit-advertisement-interval {
         description "Advertisement interval for inherit sessions";
         default "120";
         type union {
           type string {
             pattern "<.*>|$.*";
           }
           type uint32 {
             range "5 .. 120";
           }
         }
       }
       leaf version-3 {
         description "VRRPv3 conformance";
         type empty;
       }
     }
     container pgm {
       description "PGM options";
       presence "enable pgm";
       status deprecated;
       uses juniper-protocols-pgm;
     }
     container bgpmcast {
       description "BGP multicast options";
       presence "enable bgpmcast";
       uses juniper-protocols-bgpmcast;
     }
     container connections {
       description "Circuit cross-connect configuration";
       uses apply-advanced;
       list interface-switch {
         key name;
         ordered-by user;
         description "Bidirectional switch between interfaces";
         leaf name {
           description "Name of interface switch";
           type string {
           }
         }
         uses apply-advanced;
         list interface {
           key name;
           ordered-by user;
           description "Interface to be switched";
           leaf name {
             description "Interface name";
             type union {
               type jt:interface-name;
               type string {
                 pattern "<.*>|$.*";
               }
             }
           }
           uses apply-advanced;
         }
       }
       list remote-interface-switch {
         key name;
         ordered-by user;
         description "Bidirectional switch between a local and a remote interface";
         leaf name {
           description "Name of remote interface switch";
           type string {
           }
         }
         uses apply-advanced;
         leaf interface {
           description "Local interface name";
           type union {
             type jt:interface-name;
             type string {
               pattern "<.*>|$.*";
             }
           }
           mandatory true;
         }
         leaf transmit-lsp {
           description "Name of outgoing label-switched path";
           type string;
           mandatory true;
         }
         leaf receive-lsp {
           description "Name of incoming label-switched path";
           type string;
           mandatory true;
         }
       }
       list lsp-switch {
         key name;
         ordered-by user;
         description "Unidirectional switch between two label-switched paths";
         leaf name {
           description "Name of label-switched path switch";
           type string {
           }
         }
         uses apply-advanced;
         leaf transmit-lsp {
           description "Name of outgoing label-switched path";
           type string;
           mandatory true;
         }
         leaf receive-lsp {
           description "Name of incoming label-switched path";
           type string;
           mandatory true;
         }
       }
       list p2mp-transmit-switch {
         key name;
         ordered-by user;
         description "Local interface to point-to-multipoint LSP switch";
         leaf name {
           description "Point-to-multipoint switch name on which to transmit";
           type string {
           }
         }
         uses apply-advanced;
         leaf input-interface {
           description "Input interface name";
           type union {
             type jt:interface-name;
             type string {
               pattern "<.*>|$.*";
             }
           }
           mandatory true;
         }
         leaf transmit-p2mp-lsp {
           description "Point-to-multipoint LSP name on which to transmit";
           type string;
           mandatory true;
         }
         leaf-list output-interface {
           ordered-by user;
           description "Outgoing interface name";
           type union {
             type jt:interface-name;
             type string {
               pattern "<.*>|$.*";
             }
           }
           max-elements 16;
         }
       }
       list p2mp-receive-switch {
         key name;
         ordered-by user;
         description "Point-to-multipoint LSP to local interfaces switch";
         leaf name {
           description "Point-to-multipoint switch name on which to receive";
           type string {
           }
         }
         uses apply-advanced;
         leaf receive-p2mp-lsp {
           description "Point-to-multipoint LSP name on which to receive";
           type string;
           mandatory true;
         }
         leaf-list output-interface {
           ordered-by user;
           description "Next outgoing interface name";
           type union {
             type jt:interface-name;
             type string {
               pattern "<.*>|$.*";
             }
           }
         }
       }
     }
     container dvmrp {
       presence "enable dvmrp";
       description "DVMRP options";
       status deprecated;
       uses apply-advanced;
       choice enable-disable {
         case case_1 {
           leaf disable {
             description "Disable DVMRP";
             type empty;
           }
         }
       }
       container traceoptions {
         description "Trace options for DVMRP";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "poison" {
                 description "Trace poison-route-reverse packets";
               }
               enum "packets" {
                 description "Trace all DVMRP packets";
               }
               enum "probe" {
                 description "Trace probe packets";
               }
               enum "report" {
                 description "Trace DVMRP route report packets";
               }
               enum "neighbor" {
                 description "Trace neighbor probe packets";
               }
               enum "prune" {
                 description "Trace prune messages";
               }
               enum "graft" {
                 description "Trace graft messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container rib-group {
         description "Routing table group";
         uses rib_group_inet_type;
       }
       leaf-list import {
         ordered-by user;
         description "Import policy";
         type jt:policy-algebra;
       }
       leaf-list export {
         ordered-by user;
         description "Export policy";
         type jt:policy-algebra;
       }
       list interface {
         key name;
         ordered-by user;
         description "DVMRP interface options";
         leaf name {
           description "Interface name";
           type union {
             type jt:interface-name;
             type string {
               pattern "<.*>|$.*";
             }
           }
         }
         uses apply-advanced;
         choice enable-disable {
           case case_1 {
             leaf disable {
               description "Disable DVMRP on this interface";
               type empty;
             }
           }
         }
         leaf mode {
           description "Mode of interface";
           type enumeration {
             enum "forwarding" {
               description "Use DVMRP for multicast forwarding";
             }
             enum "unicast-routing" {
               description "Use DVMRP for unicast routing only";
             }
           }
         }
         leaf metric {
           description "DVMRP metric value";
           type union {
             type string {
               pattern "<.*>|$.*";
             }
             type uint32 {
               range "1 .. 32";
             }
           }
         }
         leaf hold-time {
           description "When neighbors think the interface is down";
           units "seconds";
           type union {
             type string {
               pattern "<.*>|$.*";
             }
             type uint32 {
               range "1 .. 255";
             }
           }
         }
       }
     }
     container evpn {
       description "Configuration EVPN default routing instance";
       uses apply-advanced;
       container traceoptions {
         description "Trace options for Layer 2 VPNs";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 VPN, VPLS and EVPN topology changes";
               }
               enum "nlri" {
                 description "Trace Layer 2 VPN, VPLS and EVPN remote site advertisements";
               }
               enum "connections" {
                 description "Trace Layer 2 VPN and VPLS connections";
               }
               enum "automatic-site" {
                 description "Trace VPLS automatic site state";
               }
               enum "oam" {
                 description "Trace OAM messages";
               }
               enum "mac-database" {
                 description "Trace MAC route database in a EVPN instance";
               }
               enum "nsr" {
                 description "Trace NSR in a EVPN instance";
               }
               enum "egress-protection" {
                 description "Trace Edge Protection messages";
               }
               enum "instance" {
                 description "Evpn instance related messages";
               }
               enum "interface" {
                 description "Interface related messages";
               }
               enum "l2aldsync" {
                 description "Messages related to EVPN-L2ALD communication";
               }
               enum "p2mp" {
                 description "P2MP messages";
               }
               enum "esi" {
                 description "Evpn ethernet segment related messages";
               }
               enum "mcsn" {
                 description "Evpn multicast snooping related messages";
               }
               enum "vpws" {
                 description "VPWS messages";
               }
               enum "irb" {
                 description "Integrated routing bridging messages";
               }
               enum "ar" {
                 description "Assisted-replication messages";
               }
               enum "etree" {
                 description "Evpn etree messages";
               }
               enum "kernel" {
                 description "Messages related to rpd-kernel communication";
               }
               enum "bd" {
                 description "Evpn bridge domain messages";
               }
               enum "pbb" {
                 description "Evpn provider backbone bridging messages";
               }
               enum "infra" {
                 description "Messages related to infrastructure in evpn";
               }
               enum "pfxdb" {
                 description "Type-5 related messages";
               }
               enum "peg-df" {
                 description "PIM EVPN Gateway DF-Election related messages";
               }
               enum "gbptagdb" {
                 description "Trace message related to gbptagdb";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf mac-history {
         description "Number of history entries to be maitained per mac";
         type union {
           type string {
             pattern "<.*>|$.*";
           }
           type uint16 {
             range "0 .. 255";
           }
         }
       }
       leaf peg-df-election-history {
         description "Number of DF Election history entries to be maintained per PEG BD";
         type union {
           type string {
             pattern "<.*>|$.*";
           }
           type uint16 {
             range "0 .. 255";
           }
         }
       }
       leaf oism-core-route-history {
         description "Number of history entries to be maintained per OISM Core Route";
         type union {
           type string {
             pattern "<.*>|$.*";
           }
           type uint16 {
             range "0 .. 255";
           }
         }
       }
       leaf interface-history {
         description "Number of history entries to be maintained per EVPN interface";
         type union {
           type string {
             pattern "<.*>|$.*";
           }
           type uint16 {
             range "0 .. 255";
           }
         }
       }
       leaf core-isolation-delay-response {
         description "Delay core-isolation response (seconds)";
         type union {
           type string {
             pattern "<.*>|$.*";
           }
           type uint32 {
             range "0 .. 255";
           }
         }
       }
       leaf mac-ip-limit {
         description "Maximum number of IPs that can be learned on a MAC, default is 200";
         type union {
           type string {
             pattern "<.*>|$.*";
           }
           type uint32 {
             range "1 .. 5000";
           }
         }
       }
       leaf interconnect-esi-bringup-delay {
         description "Delay interconnect esi bringup (seconds)";
         type union {
           type string {
             pattern "<.*>|$.*";
           }
           type uint32 {
             range "1 .. 600";
           }
         }
       }
       list mac-list {
         key name;
         description "Configure MAC lists";
         leaf name {
           description "List name";
           type string {
             length "1 .. 128";
           }
         }
         uses apply-advanced;
         leaf description {
           description "MAC list description";
           type string {
             length "1 .. 128";
           }
         }
         list mac-address {
           key name;
           description "MAC address";
           leaf name {
             description "MAC address";
             type jt:mac-addr-prefix;
           }
           uses apply-advanced;
         }
       }
       container mac-mobility {
         description "MAC mobility settings";
         uses apply-advanced;
         leaf no-sequence-numbers {
           description "Don't use sequence numbers for MAC mobility";
           type empty;
         }
       }
       leaf no-core-isolation {
         description "Disable EVPN Core isolation";
         type empty;
       }
       leaf leave-sync-route-oldstyle {
         description "Originate leave sync route oldstyle";
         type empty;
       }
       leaf-list interconnect-multihoming-peer-gateways {
         description "Configure multihoming peer gateway VTEP IPv4 addresses";
         type jt:ipaddr;
         max-elements 64;
       }
       leaf-list interconnect-multihoming-peer-v6-gateways {
         description "Configure multihoming peer gateway VTEP IPv6 addresses";
         type jt:ipv6addr;
         max-elements 64;
       }
       leaf advertise-evpn-esi-routes {
         description "Advertise AD/ES routes considering instance ifl status";
         type empty;
       }
       leaf-list static-multihoming-peer {
         description "Configure static multihoming peer VTEP IPv4 addresses";
         type jt:ipaddr;
         max-elements 64;
       }
       leaf-list static-multihoming-peer-v6 {
         description "Configure static multihoming peer VTEP IPv6 addresses";
         type jt:ipv6addr;
         max-elements 64;
       }
       container node-detection {
         presence "enable node-detection";
         description "Node detection";
         uses apply-advanced;
         leaf next-hop {
           description "Next-hop identifier to which to map";
           type union {
             type jt:interface-unit;
             type string {
               pattern "<.*>|$.*";
             }
           }
         }
         leaf action {
           description "Isolation action";
           type enumeration {
             enum "laser-off" {
               description "Will trigger laser-off on core-isolation";
             }
             enum "trigger-node-isolation" {
               description "Will trigger link-down on core-isolation";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           leaf neighbor {
             description "BFD neighbor address";
             type jt:ipaddr;
           }
         }
       }
       container maintenance-mode {
         description "EVPN maintenance mode";
         uses apply-advanced;
         container erb-leaf {
           description "Will trigger evpn maintenance mode for evpn erb-leaf";
           uses apply-advanced;
           leaf action-type {
             description "Define maintenance mode action type";
             type enumeration {
               enum "validate-only" {
                 description "Validate maintenance-mode pre-checks, no action is taken";
               }
               enum "validate-and-set" {
                 description "Trigger maintenance-mode after pre-check validation";
               }
               enum "force" {
                 description "Trigger maintenance-mode, ignores pre-check validations";
               }
             }
           }
           leaf schedule-start-at {
             description "Time at which to start maintenance-actions. Format is [yyyy-mm-dd.]hh:mm";
             type string {
               length "4 .. 16";
             }
           }
           leaf schedule-end-at {
             description "Time at which to end maintenance-actions. Format is [yyyy-mm-dd.]hh:mm";
             type string {
               length "4 .. 16";
             }
           }
         }
         container collapsed-core {
           description "Will trigger evpn maintenance mode for evpn collapsed-core";
           uses apply-advanced;
           leaf action-type {
             description "Define maintenance mode action type";
             type enumeration {
               enum "validate-only" {
                 description "Validate maintenance-mode pre-checks, no action is taken";
               }
               enum "validate-and-set" {
                 description "Trigger maintenance-mode after pre-check validation";
               }
               enum "force" {
                 description "Trigger maintenance-mode, ignores pre-check validations";
               }
             }
           }
           leaf schedule-start-at {
             description "Time at which to start maintenance-actions. Format is [yyyy-mm-dd.]hh:mm";
             type string {
               length "4 .. 16";
             }
           }
           leaf schedule-end-at {
             description "Time at which to end maintenance-actions. Format is [yyyy-mm-dd.]hh:mm";
             type string {
               length "4 .. 16";
             }
           }
         }
         container core-distribution {
           description "Will trigger evpn maintenance mode for evpn core-distribution";
           uses apply-advanced;
           leaf action-type {
             description "Define maintenance mode action type";
             type enumeration {
               enum "validate-only" {
                 description "Validate maintenance-mode pre-checks, no action is taken";
               }
               enum "validate-and-set" {
                 description "Trigger maintenance-mode after pre-check validation";
               }
               enum "force" {
                 description "Trigger maintenance-mode, ignores pre-check validations";
               }
             }
           }
           leaf schedule-start-at {
             description "Time at which to start maintenance-actions. Format is [yyyy-mm-dd.]hh:mm";
             type string {
               length "4 .. 16";
             }
           }
           leaf schedule-end-at {
             description "Time at which to end maintenance-actions. Format is [yyyy-mm-dd.]hh:mm";
             type string {
               length "4 .. 16";
             }
           }
         }
         container ip-clos {
           description "Will trigger evpn maintenance mode for evpn ip-clos";
           uses apply-advanced;
           leaf action-type {
             description "Define maintenance mode action type";
             type enumeration {
               enum "validate-only" {
                 description "Validate maintenance-mode pre-checks, no action is taken";
               }
               enum "validate-and-set" {
                 description "Trigger maintenance-mode after pre-check validation";
               }
               enum "force" {
                 description "Trigger maintenance-mode, ignores pre-check validations";
               }
             }
           }
           leaf schedule-start-at {
             description "Time at which to start maintenance-actions. Format is [yyyy-mm-dd.]hh:mm";
             type string {
               length "4 .. 16";
             }
           }
           leaf schedule-end-at {
             description "Time at which to end maintenance-actions. Format is [yyyy-mm-dd.]hh:mm";
             type string {
               length "4 .. 16";
             }
           }
         }
       }
       leaf es-import-oldstyle {
         description "Enable noncompliant ES import route-target computation";
         type empty;
       }
       leaf es-label-oldstyle {
         description "Enable noncompliant ESI 24 bit label";
         type empty;
       }
       leaf encapsulation {
         description "Encapsulation type for EVPN";
         default "mpls";
         type enumeration {
           enum "mpls" {
             description "MPLS encapsulation";
           }
           enum "vxlan" {
             description "VXLAN encapsulation";
           }
           enum "mpls-inet6" {
             description "MPLS over IPv6 encapsulation";
           }
           enum "srv6" {
             description "SRv6 encapsulation";
           }
         }
       }
       container assisted-replication {
         description "Option to enable Assisted Replication";
         uses apply-advanced;
         choice AR {
           case case_1 {
             container leaf {
               presence "enable leaf";
               description "Assisted Replicator Leaf";
               uses apply-advanced;
               leaf replicator-activation-delay {
                 description "Dealy interval in starting replication";
                 default "10";
                 units "seconds";
                 type union {
                   type string {
                     pattern "<.*>|$.*";
                   }
                   type uint32 {
                     range "0 .. 180";
                   }
                 }
               }
               leaf-list deterministic-ar-policy {
                 ordered-by user;
                 description "Deterministic mapping of multicast flow to replicator";
                 type jt:policy-algebra;
               }
             }
           }
           case case_2 {
           }
         }
       }
       leaf designated-forwarder-election-hold-time {
         description "Time to wait before electing a DF(seconds)";
         units "seconds";
         type union {
           type string {
             pattern "<.*>|$.*";
           }
           type uint32 {
             range "1 .. 1800";
           }
         }
       }
       leaf df-election-ntp {
         description "NTP based absolute time DF election";
         type empty;
       }
       choice df-preference-alg {
         case case_1 {
           leaf designated-forwarder-preference-least {
             description "Use least preference in DF election";
             type empty;
           }
         }
         case case_2 {
           leaf designated-forwarder-preference-highest {
             description "Use highest preference in DF election-1";
             type empty;
           }
         }
       }
       container duplicate-mac-detection {
         description "Duplicate MAC detection settings";
         uses apply-advanced;
         leaf auto-recovery-time {
           description "Automatically unblock duplicate MACs after a time delay";
           units "minutes";
           type union {
             type string {
               pattern "<.*>|$.*";
             }
             type uint32 {
               range "1 .. 360";
             }
           }
         }
         leaf auto-recovery-time-seconds {
           description "Automatically unblock duplicate MACs after a time delay";
           units "seconds";
           type union {
             type string {
               pattern "<.*>|$.*";
             }
             type uint32 {
               range "1 .. 21600";
             }
           }
         }
       }
       container remote-ip-host-routes {
         presence "enable remote-ip-host-routes";
         description "Virtual machine traffic optimization(VMTO) for EVPN";
         uses apply-advanced;
         leaf-list import {
           ordered-by user;
           description "Policy to control the creation of remote IP host routes";
           type jt:policy-algebra;
         }
         leaf no-advertise-community {
           description "Don't advertise Type 2 route's community";
           type empty;
         }
       }
       leaf pmsi-tunnel-endpoint {
         description "IM IR PMSI tunnel Endpoint for remote PE";
         type jt:ipv4addr;
       }
       leaf label-allocation {
         description "Label allocation policy";
         type enumeration {
           enum "per-bridge-domain" {
             description "Allocate one label for each bridge-domain";
           }
         }
       }
       leaf esi-resolution-per-bridge-domain {
         description "Enable ESI Resolution Per BD";
         type empty;
       }
       leaf riot-loopback {
         description "Track loopback irb interface state on RIOT platform";
         type empty;
       }
       container anycast-multihoming {
         presence "enable anycast-multihoming";
         description "Enable anycast multi-homing";
         uses apply-advanced;
         leaf mlag-interop-mode {
           description "Enable interop mode";
           type empty;
         }
         choice family {
           case case_1 {
             container inet {
               description "IPv4 source";
               uses apply-advanced;
               leaf address {
                 description "Anycast source vtep IPv4 address";
                 type jt:ipv4addr;
                 mandatory true;
               }
             }
           }
           case case_2 {
             container inet6 {
               description "IPv6 source";
               uses apply-advanced;
               leaf address {
                 description "Anycast source vtep IPv6 address";
                 type jt:ipv6addr;
                 mandatory true;
               }
             }
           }
         }
         leaf router-mac {
           description "Router mac address";
           type jt:mac-addr;
         }
         leaf loopback-interface {
           description "Name of loopback interface";
           default "lo0.0";
           type union {
             type jt:interface-name;
             type string {
               pattern "<.*>|$.*";
             }
           }
         }
       }
       leaf suppress-remote-host-routes-on-vlan-down {
         description "Suppress host routes matching irb subnet ip on vlan down";
         type empty;
       }
       container interconnect {
         description "Interconnect";
         uses juniper-protocols-evpn-interconnect;
       }
       container mark-local-ip-host-routes {
         description "Mark local ip host routes";
         uses apply-advanced;
         leaf-list export {
           ordered-by user;
           description "Policy to mark local IP host routes";
           type jt:policy-algebra;
         }
       }
       leaf igmp-snooping-join-withdraw-hold-time {
         description "Time to hold state on receiving igmp withdraw(seconds)";
         units "seconds";
         type union {
           type string {
             pattern "<.*>|$.*";
           }
           type uint32 {
             range "1 .. 60";
           }
         }
       }
       leaf igmp-snooping-join-state-retain-time {
         description "Time to retain state after join withdraw timer expires (seconds)";
         units "seconds";
         type union {
           type string {
             pattern "<.*>|$.*";
           }
           type uint32 {
             range "1 .. 1800";
           }
         }
       }
       leaf mld-snooping-join-withdraw-hold-time {
         description "Time to hold state on receiving mld withdraw(seconds)";
         units "seconds";
         type union {
           type string {
             pattern "<.*>|$.*";
           }
           type uint32 {
             range "1 .. 60";
           }
         }
       }
       leaf mld-snooping-join-state-retain-time {
         description "Time to retain state after mld join withdraw timer expires (seconds)";
         units "seconds";
         type union {
           type string {
             pattern "<.*>|$.*";
           }
           type uint32 {
             range "1 .. 1800";
           }
         }
       }
       container oism {
         description "EVPN Multicast master OISM features";
         uses apply-advanced;
         leaf supplemental-bridge-domain-irb {
           description "OISM SBD irb interface address";
           type union {
             type jt:interface-unit;
             type string {
               pattern "<.*>|$.*";
             }
           }
         }
         leaf originate-smet-on-revenue-vlan-too {
           description "Originate smet route on revenue vlan too";
           type empty;
         }
         container pim-evpn-gateway {
           presence "enable pim-evpn-gateway";
           description "Configure PIM EVPN Gateway PEG parameters";
           uses apply-advanced;
           list external-irb {
             key name;
             ordered-by user;
             description "List of IRBs for external connectivity";
             leaf name {
               description "External vlan interface name";
               type union {
                 type jt:interface-name;
                 type string {
                   pattern "<.*>|$.*";
                 }
               }
             }
             uses apply-advanced;
           }
           container peg-df-election {
             presence "enable peg-df-election";
             description "PEG DF Election Options";
             uses apply-advanced;
             choice pref_choice {
               case case_1 {
                 container preference {
                   presence "enable preference";
                   description "Preference based DF election";
                   uses apply-advanced;
                   leaf value {
                     description "Preference value for EVPN OISM PEG DF election";
                     default "32767";
                     type union {
                       type string {
                         pattern "<.*>|$.*";
                       }
                       type uint32 {
                         range "0 .. 65535";
                       }
                     }
                   }
                   leaf use-least {
                     description "Use least preference in OISM PEG DF election";
                     type empty;
                   }
                 }
               }
             }
             choice mod_choice {
               case case_1 {
                 container mod {
                   presence "enable mod";
                   description "MOD based DF election";
                 }
               }
             }
             leaf delay-time {
               description "Time to wait before electing a DF(seconds)";
               units "seconds";
               type union {
                 type string {
                   pattern "<.*>|$.*";
                 }
                 type uint32 {
                   range "1 .. 1800";
                 }
               }
             }
           }
         }
         container enhanced {
           description "Enhanced-OISM suboptions";
           uses apply-advanced;
           container forward-on-source-bridge-domain {
             description "Forward applicable streams on source bridge-domain";
             uses apply-advanced;
             leaf-list forward-policy {
               ordered-by user;
               description "Force traffic matching source, group on source BD when enhanced-oism is in use";
               type jt:policy-algebra;
             }
           }
         }
       }
       container vni-options {
         description "Vni options";
         uses juniper-protocols-vni-options;
       }
     }
     container express-segments {
       description "Configuration for Express Segments";
       uses apply-advanced;
       list segment-template {
         key name;
         ordered-by user;
         description "Express Segments Template Definition";
         max-elements 64;
         leaf name {
           description "Express Segment Template Name";
           type string {
           }
         }
         uses apply-advanced;
         leaf-list admin-group {
           ordered-by user;
           description "Administrative groups";
           type string;
           max-elements 16;
         }
         leaf-list admin-group-extended {
           ordered-by user;
           description "Extended administrative groups";
           type string;
           max-elements 16;
         }
         leaf-list srlg {
           ordered-by user;
           description "SRLG Name";
           type string;
           max-elements 16;
         }
         container metric {
           description "Metric values for Express Segment Template";
           uses apply-advanced;
           leaf te {
             description "TE metric value";
             type union {
               type string {
                 pattern "<.*>|$.*";
               }
               type uint32 {
                 range "1 .. 4294967295";
               }
             }
           }
           leaf igp {
             description "IGP metric value";
             type union {
               type string {
                 pattern "<.*>|$.*";
               }
               type uint32 {
                 range "1 .. 16777215";
               }
             }
           }
           leaf delay {
             description "Delay metric value";
             units "microseconds";
             type union {
               type string {
                 pattern "<.*>|$.*";
               }
               type uint32 {
                 range "1 .. 16777215";
               }
             }
           }
         }
       }
       list segment-set {
         key name;
         ordered-by user;
         description "Express Segments Set Definition";
         max-elements 64;
         leaf name {
           description "Express Segment Set Name";
           type string {
           }
         }
         uses apply-advanced;
         leaf-list membership-policy {
           ordered-by user;
           description "Policy for matching specific LSPs to this express segment";
           type jt:policy-algebra;
         }
         container template {
           description "Template for Express Segment Attribute Selection";
           uses apply-advanced;
           leaf template-name {
             description "Name of Express Segment template";
             type string {
             }
           }
         }
       }
       container traffic-engineering {
         presence "enable traffic-engineering";
         description "Enable Import of all Express Segments into TED";
         uses apply-advanced;
       }
       container traceoptions {
         description "Trace options for Express Segment";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace everything";
               }
               enum "error" {
                 description "Trace errors";
               }
               enum "route" {
                 description "Trace route-related changes";
               }
               enum "state" {
                 description "Trace state transitions";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container igmp {
       presence "enable igmp";
       description "IGMP options";
       uses apply-advanced;
       leaf protocol-instance-name {
         description "Name of protocol instance under routing instance";
         type string;
       }
       container traceoptions {
         description "Trace options for IGMP";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "mtrace" {
                 description "Trace mtrace packets";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf maximum-transmit-rate {
         description "Maximum transmission rate (packets per second)";
         type union {
           type string {
             pattern "<.*>|$.*";
           }
           type uint32 {
             range "1 .. 10000";
           }
         }
       }
       leaf accounting {
         description "Enable join and leave event notification";
         type empty;
       }
       list interface {
         key name;
         ordered-by user;
         description "Interface options for IGMP";
         leaf name {
           type string;
         }
         uses apply-advanced;
         choice enable-disable {
           case case_1 {
             leaf disable {
               description "Disable IGMP on this interface";
               type empty;
             }
           }
         }
         leaf version {
           description "Set IGMP version number on this interface";
           type union {
             type string {
               pattern "<.*>|$.*";
             }
             type uint8 {
               range "1 .. 3";
             }
           }
         }
         container static {
           description "Static group or source membership";
           uses apply-advanced;
           list group {
             key name;
             ordered-by user;
             description "IP multicast group address";
             leaf name {
               description "IP multicast group address";
               type jt:ipv4addr;
             }
             uses apply-advanced;
             leaf group-increment {
               description "Mask for the incrementing group IP address";
               type jt:ipv4addr;
             }
             leaf group-count {
               description "Number of groups";
               type union {
                 type string {
                   pattern "<.*>|$.*";
                 }
                 type uint32 {
                   range "1 .. 512";
                 }
               }
             }
             leaf exclude {
               description "Exclude sources";
               type empty;
             }
             list source {
               key name;
               ordered-by user;
               description "IP multicast source address";
               leaf name {
                 description "Source address of IP multicast data";
                 type jt:ipv4addr;
               }
               uses apply-advanced;
               leaf source-increment {
                 description "Mask for the incrementing source IP address";
                 type jt:ipv4addr;
               }
               leaf source-count {
                 description "Number of sources";
                 type union {
                   type string {
                     pattern "<.*>|$.*";
                   }
                   type uint32 {
                     range "1 .. 1024";
                   }
                 }
               }
             }
           }
         }
         leaf ssm-map {
           description "Map for SSM translation of IGMPv1 or IGMPv2 messages";
           type string;
         }
         leaf-list ssm-map-policy {
           ordered-by user;
           description "SSM map policy name";
           type jt:policy-algebra;
         }
         leaf immediate-leave {
           description "Group removed immediately, last membership query not sent";
           type empty;
         }
         leaf promiscuous-mode {
           description "Accept igmp messages coming from different subnet";
           type empty;
         }
         choice accounting-choice {
           leaf accounting {
             description "Enable join and leave event notification";
             type empty;
           }
           leaf no-accounting {
             description "Don't enable join and leave event notification";
             type empty;
           }
         }
         leaf-list group-policy {
           ordered-by user;
           description "Group filter applied to incoming IGMP report messages";
           type jt:policy-algebra;
         }
         leaf group-limit {
           description "Maximum number of (source,group) per interface";
           type union {
             type string {
               pattern "<.*>|$.*";
             }
             type uint16 {
               range "1 .. 32767";
             }
           }
         }
         leaf group-threshold {
           description "Percentage of limit at which to generate warnings";
           type union {
             type string {
               pattern "<.*>|$.*";
             }
             type uint32 {
               range "1 .. 100";
             }
           }
         }
         leaf log-interval {
           description "Time between consecutive log messages";
           type union {
             type string {
               pattern "<.*>|$.*";
             }
             type uint32 {
               range "6 .. 32767";
             }
           }
         }
         container passive {
           presence "enable passive";
           description "Suppress sending and receiving IGMP messages";
           leaf allow-receive {
             description "Allow receiving IGMP messages";
             type empty;
           }
           leaf send-general-query {
             description "Send IGMP general query messages";
             type empty;
           }
           leaf send-group-query {
             description "Send IGMP group query messages";
             type empty;
           }
         }
         leaf-list oif-map {
           ordered-by user;
           description "Output interface map";
           type jt:policy-algebra;
         }
         leaf distributed {
           description "Distributed IGMP interface";
           type empty;
         }
       }
       container amt {
         description "Automatic Multicast Tunnel options for IGMP";
         uses apply-advanced;
         container relay {
           description "AMT relay options for IGMP";
           uses apply-advanced;
           container defaults {
             presence "enable defaults";
             description "Default AMT relay options for IGMP";
             uses apply-advanced;
             leaf version {
               description "Set IGMP version number on AMT interfaces";
               type union {
                 type string {
                   pattern "<.*>|$.*";
                 }
                 type uint8 {
                   range "1 .. 3";
                 }
               }
             }
             leaf ssm-map {
               description "Map for SSM translation of IGMPv1 or IGMPv2 messages";
               type string;
             }
             leaf-list ssm-map-policy {
               ordered-by user;
               description "SSM map policy name";
               type jt:policy-algebra;
             }
             choice accounting-choice {
               leaf accounting {
                 description "Enable join and leave event notification";
                 type empty;
               }
               leaf no-accounting {
                 description "Don't enable join and leave event notification";
                 type empty;
               }
             }
             leaf-list group-policy {
               ordered-by user;
               description "Group filter applied to incoming IGMP report messages";
               type jt:policy-algebra;
             }
             leaf group-limit {
               description "Maximum number of (source,group) per interface";
               type union {
                 type string {
                   pattern "<.*>|$.*";
                 }
                 type uint16 {
                   range "1 .. 32767";
                 }
               }
             }
             leaf group-threshold {
               description "Percentage of limit at which to generate warnings";
               type union {
                 type string {
                   pattern "<.*>|$.*";
                 }
                 type uint32 {
                   range "1 .. 100";
                 }
               }
             }
             leaf log-interval {
               description "Time between consecutive log messages";
               type union {
                 type string {
                   pattern "<.*>|$.*";
                 }
                 type uint32 {
                   range "6 .. 32767";
                 }
               }
             }
             leaf robust-count {
               description "Expected packet loss on a subnet";
               type union {
                 type string {
                   pattern "<.*>|$.*";
                 }
                 type uint32 {
                   range "2 .. 10";
                 }
               }
             }
             leaf query-interval {
               description "When to send host query messages";
               units "seconds";
               type union {
                 type string {
                   pattern "<.*>|$.*";
                 }
                 type uint32 {
                   range "1 .. 1024";
                 }
               }
             }
             leaf query-response-interval {
               description "How long to wait for a host query response";
               units "seconds";
               type string {
               }
             }
           }
         }
       }
     }
     container router-discovery {
       description "ICMP router discovery options";
       uses juniper-protocols-router-discovery;
     }
     container isis {
       description "IS-IS options";
       uses juniper-protocols-isis;
     }
     list isis-instance {
       key name;
       ordered-by user;
       description "Multi-instance IS-IS configuration";
       leaf name {
         description "IS-IS instance name";
         type string;
       }
       leaf link-state-instance-id {
         description "Link State Instance Identifier";
         type union {
           type string {
             pattern "<.*>|$.*";
           }
           type uint64 {
             range "1 .. 65535";
           }
         }
       }
       container instance-id {
         description "Instance Identifier attributes";
         leaf instance-id-value {
           description "Instance Identifier";
           type union {
             type string {
               pattern "<.*>|$.*";
             }
             type uint16 {
               range "1 .. 65535";
             }
           }
           mandatory true;
         }
         leaf itid-disable {
           description "Disable transmission of ITID in IID TLV and its receive validation";
           type empty;
         }
       }
       uses apply-advanced;
       list interface {
         key name;
         description "Interface configuration";
         leaf name {
           description "Interface name";
           type union {
             type jt:interface-name;
             type string {
               pattern "<.*>|$.*";
             }
           }
         }
         uses apply-advanced;
         container ldp-synchronization {
           description "Advertise maximum metric until LDP is operational";
           presence "enable ldp-synchronization";
           uses ldp-sync-obj;
         }
         list level {
           key name;
           ordered-by user;
           description "Configure levels on this interface";
           leaf name {
             description "IS-IS level number";
             type union {
               type string {
                 pattern "<.*>|$.*";
               }
               type uint32 {
                 range "1 .. 2";
               }
             }
           }
           uses apply-advanced;
           leaf te-metric {
             description "Traffic engineering metric";
             type union {
               type string {
                 pattern "<.*>|$.*";
               }
               type uint32 {
                 range "0 .. 16777215";
               }
             }
           }
           leaf no-advertise-adjacency-segment {
             description "Do not advertise an adjacency segment for this level";
             type empty;
           }
           container ipv4-adjacency-segment {
             description "Configure ipv4 adjacency segment";
             uses apply-advanced;
             container protected {
               description "Adjacency SID is eligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
                 mandatory true;
               }
             }
           }
           container srv6-adjacency-segment {
             description "Configure srv6 adjacency segment";
             uses apply-advanced;
             container unprotected {
               presence "enable unprotected";
               description "SRv6 Adjacency segment is uneligible for protection";
               uses apply-advanced;
               list locator {
                 key name;
                 ordered-by user;
                 description "Locator to bind SRv6 adjacency segment";
                 leaf name {
                   description "Locator name";
                   type string;
                   mandatory true;
                 }
                 uses apply-advanced;
                 list end-x-sid {
                   key name;
                   ordered-by user;
                   description "Endpoint 128 bit address";
                   leaf name {
                     type jt:ipv6addr;
                   }
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
                 container micro-adjacency-sid {
                   presence "enable micro-adjacency-sid";
                   description "Micro-adjacency-SID";
                   uses apply-advanced;
                   leaf static-sid {
                     description "Static micro-adjacency-SID";
                     type union {
                       type uint32;
                       type string {
                         pattern "<.*>|$.*";
                       }
                     }
                   }
                 }
                 container dynamic-end-x-sid {
                   presence "enable dynamic-end-x-sid";
                   description "Allocate end-x-SID dynamically";
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
           list lan-neighbor {
             key name;
             ordered-by user;
             description "Configuration specific to a LAN neighbor";
             leaf name {
               description "Neighbor's sysid";
               type jt:sysid;
             }
             uses apply-advanced;
             container ipv4-adjacency-segment {
               description "Configure ipv4 adjacency segment";
               uses apply-advanced;
               container protected {
                 description "Adjacency SID is eligible for protection";
                 uses apply-advanced;
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 uses apply-advanced;
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container ipv6-adjacency-segment {
               description "Configure ipv6 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 1048575";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container srm6-adjacency-segment {
               description "Configure srm6 adjacency segment";
               uses apply-advanced;
               container unprotected {
                 description "Adjacency SID uneligible for protection";
                 leaf sid {
                   description "Set Adjacency SID Value";
                   type union {
                     type string {
                       pattern "<.*>|$.*";
                     }
                     type uint32 {
                       range "1 .. 65535";
                     }
                   }
                   mandatory true;
                 }
               }
             }
             container srv6-adjacency-segment {
               description "Configure srv6 adjacency segment";
               uses apply-advanced;
               container unprotected {
                 presence "enable unprotected";
                 description "SRv6 Adjacency segment is uneligible for protection";
                 uses apply-advanced;
                 list locator {
                   key name;
                   ordered-by user;
                   description "Locator to bind SRv6 adjacency segment";
                   leaf name {
                     description "Locator name";
                     type string;
                     mandatory true;
                   }
                   uses apply-advanced;
                   list end-x-sid {
                     key name;
                     ordered-by user;
                     description "Endpoint 128 bit address";
                     leaf name {
                       type jt:ipv6addr;
                     }
                     uses apply-advanced;
                     container flavor {
                       presence "enable flavor";
                       description "Configure end-x-SID flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                   container micro-adjacency-sid {
                     presence "enable micro-adjacency-sid";
                     description "Micro-adjacency-SID";
                     uses apply-advanced;
                     leaf static-sid {
                       description "Static micro-adjacency-SID";
                       type union {
                         type uint32;
                         type string {
                           pattern "<.*>|$.*";
                         }
                       }
                     }
                   }
                   container dynamic-end-x-sid {
                     presence "enable dynamic-end-x-sid";
                     description "Allocate end-x-SID dynamically";
                     uses apply-advanced;
                     container flavor {
                       presence "enable flavor";
                       description "Configure end-x-SID flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                 }
               }
             }
           }
           container post-convergence-lfa {
             presence "enable post-convergence-lfa";
             description "Configure backup along post convergence on this interface";
             uses apply-advanced;
             container node-protection {
               presence "enable node-protection";
               description "Enable node protection";
               uses apply-advanced;
               leaf cost {
                 description "Cost for node protection";
                 type union {
                   type string {
                     pattern "<.*>|$.*";
                   }
                   type uint32 {
                     range "0 .. 16777215";
                   }
                 }
               }
             }
             leaf srlg-protection {
               description "Enable srlg protection";
               type empty;
             }
             leaf fate-sharing-protection {
               description "Enable fate-sharing protection";
               type empty;
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf advertise-delay-metric {
                 description "Advertise delay metric as per interface config";
                 type empty;
               }
               leaf te-metric {
                 description "Traffic engineering metric for this attribute group";
                 type union {
                   type string {
                     pattern "<.*>|$.*";
                   }
                   type uint32 {
                     range "0 .. 16777215";
                   }
                 }
               }
               leaf-list admin-group {
                 ordered-by user;
                 description "Administrative groups for this attribute-group";
                 type string;
                 max-elements 16;
               }
               leaf-list srlg {
                 ordered-by user;
                 description "SRLG Name";
                 type string;
                 max-elements 16;
               }
               container application {
                 description "Standard Applications part of this attribute-group";
                 uses apply-advanced;
                 leaf flex-algorithm {
                   description "Set X flag in standard application bit mask";
                   type empty;
                 }
               }
             }
           }
           choice enable-disable {
             case case_1 {
               leaf disable {
                 description "Disable IS-IS for this level";
                 type empty;
               }
             }
           }
           leaf metric {
             description "Metric for this level";
             type union {
               type string {
                 pattern "<.*>|$.*";
               }
               type uint32 {
                 range "0 .. 16777215";
               }
             }
           }
           leaf ipv4-multicast-metric {
             description "IPv4 multicast metric for this level";
             type union {
               type string {
                 pattern "<.*>|$.*";
               }
               type uint32 {
                 range "0 .. 16777215";
               }
             }
           }
           leaf ipv6-unicast-metric {
             description "IPv6 unicast metric for this level";
             type union {
               type string {
                 pattern "<.*>|$.*";
               }
               type uint32 {
                 range "0 .. 16777215";
               }
             }
           }
           leaf ipv6-multicast-metric {
             description "IPv6 multicast metric for this level";
             type union {
               type string {
                 pattern "<.*>|$.*";
               }
               type uint32 {
                 range "0 .. 16777215";
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                   mandatory true;
                 }
               }
             }
           }
           leaf authentication-key {
             description "Authentication key (password)";
             status deprecated;
             type jt:unreadable;
           }
           leaf authentication-type {
             description "Authentication type";
             status deprecated;
             type enumeration {
               enum "md5" {
                 description "MD5 authentication";
                 status deprecated;
               }
               enum "simple" {
                 description "Simple password authentication";
                 status deprecated;
               }
             }
           }
           leaf hello-authentication-key {
             description "Authentication key (password) for hello packets";
             type jt:unreadable;
           }
           leaf hello-authentication-type {
             description "Authentication type for hello packets";
             type enumeration {
               enum "md5" {
                 description "MD5 authentication";
               }
               enum "simple" {
                 description "Simple password authentication";
               }
             }
           }
           leaf hello-authentication-key-chain {
             description "Key chain name";
             type string {
               length "1 .. 128";
             }
           }
           leaf hello-interval {
             description "Interval between hello packet transmissions";
             units "seconds";
             type union {
               type string {
                 pattern "<.*>|$.*";
               }
               type uint32 {
                 range "1 .. 21845";
               }
             }
           }
           leaf hold-time {
             description "Time after which neighbors think the interface is down";
             units "seconds";
             type union {
               type string {
                 pattern "<.*>|$.*";
               }
               type uint32 {
                 range "1 .. 65535";
               }
             }
           }
           leaf priority {
             description "Designated router election priority";
             type union {
               type string {
                 pattern "<.*>|$.*";
               }
               type uint32 {
                 range "0 .. 127";
               }
             }
           }
           container flood-reflector {
             presence "enable flood-reflector";
             description "Configure interface as flood-reflector";
             uses apply-advanced;
             leaf cluster-id {
               description "Cluster-ID";
               type union {
                 type string {
                   pattern "<.*>|$.*";
                 }
                 type uint32 {
                   range "1 .. 4294967295";
                 }
               }
             }
           }
           container passive {
             presence "enable passive";
             description "Do not run IS-IS at this level, but advertise it";
             uses apply-advanced;
             leaf remote-node-iso {
               description "ISO System-ID of the remote node";
               type jt:sysid;
             }
             leaf remote-node-id {
               description "Remote address of the link";
               type jt:ipv4addr;
             }
           }
           leaf strict-bfd-old {
             description "Enable strict bfd over this interface";
             type empty;
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container normalize {
             description "Normalize Measured Link Delay";
             leaf interval {
               description "The value of the normalized interval in microseconds.";
               units "microseconds";
               type union {
                 type string {
                   pattern "<.*>|$.*";
                 }
                 type uint32 {
                   range "1 .. 5000000";
                 }
               }
               mandatory true;
             }
             leaf offset {
               description "The value of the normalized offset in microseconds (Must be < normalized interval).";
               units "microseconds";
               type union {
                 type string {
                   pattern "<.*>|$.*";
                 }
                 type uint32 {
                   range "1 .. 5000000";
                 }
               }
               mandatory true;
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         leaf no-advertise-adjacency-segment {
           description "Do not advertise an adjacency segment for this interface";
           type empty;
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible for backup traffic from protected interfaces";
           type empty;
         }
         leaf no-eligible-remote-backup {
           description "Not eligible for Remote-LFA backup traffic from protected interfaces";
           type empty;
         }
         container link-degradation-threshold {
           presence "enable link-degradation-threshold";
           description "Link up and down thresholds (in %) for proactive link protection";
           leaf link-down {
             description "Signal degradation threshold above which link marked down";
             type union {
               type string {
                 pattern "<.*>|$.*";
               }
               type uint32 {
                 range "0 .. 100";
               }
             }
             mandatory true;
           }
           leaf link-up {
             description "Signal degradation threshold below which link is marked up.";
             type union {
               type string {
                 pattern "<.*>|$.*";
               }
               type uint32 {
                 range "0 .. 100";
               }
             }
             mandatory true;
           }
         }
         container auto-bandwidth {
           description "Auto bandwidth configuration";
           uses apply-advanced;
           leaf template-name {
             description "Auto bandwidth template name";
             type string;
           }
           choice enable-disable {
             case case_1 {
               leaf disable {
                 description "Disable Auto bandwidth on this interface";
                 type empty;
               }
             }
           }
         }
         choice enable-disable {
           case case_1 {
             leaf disable {
               description "Disable IS-IS on this interface";
               type empty;
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf flood-group {
           description "ISO Area that this interface should send LSPs to";
           type string {
           }
         }
         leaf hello-authentication-key {
           description "Authentication key (password) for hello packets";
           status deprecated;
           type jt:unreadable;
         }
         leaf hello-authentication-type {
           description "Authentication type for hello packets";
           status deprecated;
           type enumeration {
             enum "md5" {
               description "MD5 authentication";
               status deprecated;
             }
             enum "simple" {
               description "Simple password authentication";
               status deprecated;
             }
           }
         }
         leaf hello-padding-type {
           description "Type of padding for hello packets";
           default "loose";
           type enumeration {
             enum "strict" {
               description "Padding for all adjacency states";
             }
             enum "adaptive" {
               description "Padding until state of neighbor adjacency is 'up'";
             }
             enum "loose" {
               description "Padding until state of adjacency is 'initializing'";
             }
             enum "disable" {
               description "Do not add any padding for hello packets";
             }
           }
         }
         leaf interface-group-holddown-delay {
           description "Time to wait before including in BBM calculation";
           units "seconds";
           type union {
             type string {
               pattern "<.*>|$.*";
             }
             type uint32 {
               range "0 .. 60";
             }
           }
         }
         choice layer2-map-choice {
           leaf layer2-map {
             description "Kernel ARP/ND creation for nexthops";
             type empty;
           }
           leaf no-layer2-map {
             description "Don't kernel ARP/ND creation for nexthops";
             type empty;
           }
         }
         leaf max-hello-size {
           description "Maximum size allowed for ISIS Hello PDUs";
           type union {
             type string {
               pattern "<.*>|$.*";
             }
             type uint32 {
               range "512 .. 16000";
             }
           }
         }
         leaf lsp-interval {
           description "Interval between LSP transmissions";
           default "100";
           units "milliseconds";
           type union {
             type string {
               pattern "<.*>|$.*";
             }
             type uint32 {
               range "1 .. 1000";
             }
           }
         }
         container csnp-interval {
           description "Rate of CSN packets (for LAN interfaces only)";
           choice csnp_interval_option {
             case case_1 {
               leaf csnp-interval-number {
                 description "Interval between CSN packets";
                 units "seconds";
                 type union {
                   type string {
                     pattern "<.*>|$.*";
                   }
                   type uint32 {
                     range "1 .. 65535";
                   }
                 }
               }
             }
             case case_2 {
               leaf disable {
                 description "Do not send CSN packets on this interface";
                 type empty;
               }
             }
           }
         }
         container strict-dual-isis {
           presence "enable strict-dual-isis";
           description "Enable dual isis if spf computation is required for both ipv4 and ipv6 family";
           uses apply-advanced;
           leaf holdown {
             description "Time to wait for ipv4 and ipv6 connectivity";
             status deprecated;
             default "12";
             type union {
               type string {
                 pattern "<.*>|$.*";
               }
               type uint32 {
                 range "1 .. 65535";
               }
             }
           }
           leaf holddown {
             description "Time to wait for ipv4 and ipv6 connectivity";
             default "12";
             type union {
               type string {
                 pattern "<.*>|$.*";
               }
               type uint32 {
                 range "1 .. 65535";
               }
             }
           }
         }
         container mesh-group {
           description "Add the interface to a mesh group";
           choice mesh_group_option {
             case case_1 {
               leaf mesh-group-number {
                 description "Mesh group number for this interface";
                 type union {
                   type uint32;
                   type string {
                     pattern "<.*>|$.*";
                   }
                 }
               }
             }
             case case_2 {
               leaf blocked {
                 description "Do not flood new LSPs on this interface";
                 type empty;
               }
             }
           }
         }
         leaf point-to-point {
           description "Treat interface as point to point";
           type empty;
         }
         container passive {
           presence "enable passive";
           description "Do not run IS-IS, but advertise it";
           uses apply-advanced;
           leaf remote-node-iso {
             description "ISO System-ID of the remote node";
             type jt:sysid;
           }
           leaf remote-node-id {
             description "Remote address of the link";
             type jt:ipv4addr;
           }
         }
         leaf checksum {
           description "Enable checksum for packets on this interface";
           type empty;
         }
         leaf no-unicast-topology {
           description "Do not include this interface in the unicast topology";
           type empty;
         }
         leaf no-ipv4-multicast {
           description "Do not include this interface in the IPv4 multicast topology";
           type empty;
         }
         leaf no-ipv6-unicast {
           description "Do not include this interface in the IPv6 unicast topology";
           type empty;
         }
         leaf no-ipv6-multicast {
           description "Do not include this interface in the IPv6 multicast topology";
           type empty;
         }
         leaf no-adjacency-down-notification {
           description "Do not inform other protocols about adjacency down events";
           type empty;
         }
         container bfd-liveness-detection {
           description "Bidirectional Forwarding Detection options";
           status deprecated;
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
         list family {
           key name;
           ordered-by user;
           description "Address family specific interface attributes";
           leaf name {
             type enumeration {
               enum "inet" {
                 description "IPv4 family";
               }
               enum "inet6" {
                 description "IPv6 family";
               }
             }
           }
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "1 .. 255000";
                   }
                 }
                 mandatory true;
               }
             }
             leaf holddown-interval {
               description "Time to hold the session-UP notification to the client";
               units "milliseconds";
               type union {
                 type string {
                   pattern "<.*>|$.*";
                 }
                 type uint32 {
                   range "0 .. 255000";
                 }
               }
             }
           }
         }
         leaf strict-bfd {
           description "Enable strict bfd over this interface";
           type empty;
         }
         leaf-list srlg {
           ordered-by user;
           description "SRLG Name";
           type string;
           max-elements 16;
         }
       }
       list bier-sub-domain {
         key name;
         description "Configuration of bier subdomain";
         leaf name {
           description "Enable bier subdomain id";
           type union {
             type uint8;
             type string {
               pattern "<.*>|$.*";
             }
           }
         }
       }
       container prefix-unreachable {
         presence "enable prefix-unreachable";
         description "Configure unreachable prefix advertisement parameters";
         uses apply-advanced;
         container originator {
           description "Parameters for originating unreachable prefix advertisements";
           uses apply-advanced;
           leaf unplanned-lifetime {
             description "Lifetime of unplanned UPA";
             units "seconds";
             type union {
               type string {
                 pattern "<.*>|$.*";
               }
               type uint32 {
                 range "30 .. 65535";
               }
             }
           }
           leaf metric {
             description "Metric value of unplanned UPA";
             type union {
               type string {
                 pattern "<.*>|$.*";
               }
               type uint32 {
                 range "4261412865 .. 4294967295";
               }
             }
           }
           leaf max-advertisements {
             description "Maximum UPAs that can be originated at any point of time";
             type union {
               type string {
                 pattern "<.*>|$.*";
               }
               type uint32 {
                 range "1 .. 10000";
               }
             }
           }
         }
         leaf use-only-for-leaking {
           description "Do not use this UPA route for resolution";
           type empty;
         }
       }
       container source-packet-routing {
         presence "enable source-packet-routing";
         description "Enable Source Packet Routing (SPRING)";
         uses apply-advanced;
         container adjacency-segment {
           description "Configure attributes for Adjacency Segments in SPRING";
           uses apply-advanced;
           leaf hold-time {
             description "Duration(ms) for which adjacency segments will be retained after isolating from an interface";
             type union {
               type string {
                 pattern "<.*>|$.*";
               }
               type uint32 {
                 range "180000 .. 900000";
               }
             }
           }
         }
         container udp-tunneling {
           description "Enable SR over UDP feature";
           uses apply-advanced;
           leaf encapsulation {
             description "Enable UDP Tunnel Encapsulation";
             type empty;
           }
           leaf decapsulation {
             description "Enable UDP Tunnel decapsulation";
             type empty;
           }
         }
         container srgb {
           description "Set the SRGB global block in SPRING";
           leaf start-label {
             description "Start range for SRGB label block";
             type union {
               type string {
                 pattern "<.*>|$.*";
               }
               type uint32;
             }
             mandatory true;
           }
           leaf index-range {
             description "Index to the SRGB start label block";
             type union {
               type string {
                 pattern "<.*>|$.*";
               }
               type uint32;
             }
             mandatory true;
           }
         }
         container node-segment {
           description "Enable support for Node segments in SPRING";
           uses apply-advanced;
           leaf ipv4-index {
             description "Set IPv4 Node Segment index";
             type union {
               type string {
                 pattern "<.*>|$.*";
               }
               type uint32 {
                 range "0 .. 1048575";
               }
             }
           }
           leaf ipv6-index {
             description "Set IPv6 Node Segment index";
             type union {
               type string {
                 pattern "<.*>|$.*";
               }
               type uint32 {
                 range "0 .. 1048575";
               }
             }
           }
           leaf index-range {
             description "Set Range of Node Segment indices allowed";
             type union {
               type string {
                 pattern "<.*>|$.*";
               }
               type uint32 {
                 range "32 .. 16385";
               }
             }
           }
         }
         leaf-list flex-algorithm {
           description "Flex-algorithms we would like to participate in";
           type union {
             type string {
               pattern "<.*>|$.*";
             }
             type uint32 {
               range "128 .. 255";
             }
           }
           max-elements 16;
         }
         leaf use-flex-algorithm-metric-always {
           description "Use flex-algo prefix metric whenever available";
           type empty;
         }
         leaf strict-asla-based-flex-algorithm {
           description "Flex-Algorithm to ignore links not having ASLA sub-TLVs";
           type empty;
         }
         leaf new-capability-subtlv {
           description "Advertise all ranges in single spring capability subtlv";
           type empty;
         }
         leaf explicit-null {
           description "Set E and P bits in all Prefix SID advertisements";
           type empty;
         }
         leaf ultimate-hop-popping {
           description "Set P bit for no-php in all Prefix SID advertisements";
           type empty;
         }
         leaf mapping-server {
           description "Mapping server name";
           type string;
         }
         leaf no-strict-spf {
           description " Disable strict spf algo 1 advertisement";
           type empty;
         }
         leaf no-binding-sid-leaking {
           description " Disable SRMS binding sid leaking";
           type empty;
         }
         leaf ldp-stitching {
           description "Enable SR to LDP stitching";
           type empty;
         }
         leaf entropy-label {
           description " Enable entropy label";
           type empty;
         }
         container srv6 {
           presence "enable srv6";
           description "Enable IPv6 Segment Routing (SRv6)";
           uses apply-advanced;
           list locator {
             key name;
             ordered-by user;
             description "SRv6 Locator";
             leaf name {
               description "Locator name";
               type string;
               mandatory true;
             }
             uses apply-advanced;
             leaf anycast {
               description "Set A flag in the Prefix-Attribute sub-TLV";
               type empty;
             }
             list end-sid {
               key name;
               ordered-by user;
               leaf name {
                 type jt:ipv6addr;
               }
               uses apply-advanced;
               container flavor {
                 presence "enable flavor";
                 description "Configure end-SID flavor";
                 uses apply-advanced;
                 leaf psp {
                   description "Penultimate segment pop of the SRH";
                   type empty;
                 }
                 leaf usp {
                   description "Ultimate segment pop of the SRH";
                   type empty;
                 }
                 leaf usd {
                   description "Ultimate segment decapsulation";
                   type empty;
                 }
               }
             }
             container dynamic-end-sid {
               presence "enable dynamic-end-sid";
               description "Allocate end SID dynamically";
               uses apply-advanced;
               container flavor {
                 presence "enable flavor";
                 description "Configure end-SID flavor";
                 uses apply-advanced;
                 leaf psp {
                   description "Penultimate segment pop of the SRH";
                   type empty;
                 }
                 leaf usp {
                   description "Ultimate segment pop of the SRH";
                   type empty;
                 }
                 leaf usd {
                   description "Ultimate segment decapsulation";
                   type empty;
                 }
               }
             }
             leaf micro-node-sid {
               description "Program and advertise micro-node-SID";
               type empty;
             }
           }
           container sensor-based-stats {
             description "Configure sensor based stats in SRv6";
             uses apply-advanced;
             leaf remote-locator-ingress {
               description "Enable sensor based stats for remote locator ingress accounting";
               type empty;
             }
             leaf remote-locator-egress {
               description "Enable sensor based stats for remote locator egress accounting";
               type empty;
             }
           }
         }
         container sensor-based-stats {
           description "Configure sensor based stats in SPRING";
           uses apply-advanced;
           container per-interface-per-member-link {
             description "Configure sensor based stats per nexthop";
             leaf ingress {
               description "Enable sensor based stats on ingress interface";
               type empty;
             }
             leaf egress {
               description "Enable sensor based stats on egress interface";
               type empty;
             }
           }
           container per-sid {
             description "Configure sensor based stats per spring route";
             leaf ingress {
               description "Enable sensor based stats for per-sid ingress accounting";
               type empty;
             }
             leaf egress {
               description "Enable sensor based stats for IP-MPLS egress accounting";
               type empty;
             }
           }
         }
         container traffic-statistics {
           description "Enable support for traffic statistics in SPRING";
           uses apply-advanced;
           container statistics-granularity {
             description "Granularity for traffic statistics in SPRING";
             uses apply-advanced;
             leaf per-interface {
               description "Interface Based traffic statistics in SPRING";
               type empty;
             }
           }
           leaf congestion-protection {
             description "Enable tactical traffic engineering";
             type empty;
           }
           leaf auto-bandwidth {
             description "Auto bandwidth name";
             type string;
           }
         }
       }
       container srm6 {
         presence "enable srm6";
         description "Enable SRm6";
         uses apply-advanced;
         container sid {
           description "Configure attributes for SID in srm6";
           uses apply-advanced;
           leaf node-sid {
             description "Set Node SID Value";
             type union {
               type string {
                 pattern "<.*>|$.*";
               }
               type uint32 {
                 range "1 .. 65535";
               }
             }
             mandatory true;
           }
           leaf address {
             description "IPv6 address corresponding to SID";
             type jt:ipv6addr;
             mandatory true;
           }
         }
       }
       list level {
         key name;
         ordered-by user;
         description "Configure global level attributes";
         leaf name {
           description "IS-IS level number";
           type union {
             type string {
               pattern "<.*>|$.*";
             }
             type uint32 {
               range "1 .. 2";
             }
           }
         }
         uses apply-advanced;
         leaf labeled-preference {
           description "Preference of labeled IS-IS routes";
           type union {
             type uint32;
             type string {
               pattern "<.*>|$.*";
             }
           }
         }
         leaf srv6-preference {
           description "Preference of SRV6 IS-IS routes";
           type union {
             type uint32;
             type string {
               pattern "<.*>|$.*";
             }
           }
         }
         leaf flex-algorithm-preference {
           description "Preference of flex-algorithm routes";
           type union {
             type uint32;
             type string {
               pattern "<.*>|$.*";
             }
           }
         }
         container source-packet-routing {
           presence "enable source-packet-routing";
           description "Enable Source Packet Routing (SPRING)";
           uses apply-advanced;
           choice enable-disable {
             case case_1 {
               leaf disable {
                 description "Disable Source Packet Routing on this level";
                 type empty;
               }
             }
           }
           leaf srms-preference {
             description "Set SRMS preference value";
             type union {
               type string {
                 pattern "<.*>|$.*";
               }
               type uint32 {
                 range "0 .. 255";
               }
             }
           }
         }
         choice enable-disable {
           case case_1 {
             leaf disable {
               description "Disable IS-IS on this level";
               type empty;
             }
           }
         }
         leaf authentication-key {
           description "Authentication key (password)";
           type jt:unreadable;
         }
         leaf authentication-type {
           description "Authentication type";
           type enumeration {
             enum "md5" {
               description "MD5 authentication";
             }
             enum "simple" {
               description "Simple password authentication";
             }
           }
         }
         leaf purge-originator {
           description "Add Purge Originator information";
           type enumeration {
             enum "self" {
               description "Add POI only for self-originated purge LSPs";
             }
             enum "empty" {
               description "Add POI for purge LSPs who do not have POI information";
             }
           }
         }
         leaf no-hello-authentication {
           description "Disable authentication for hello packets";
           type empty;
         }
         leaf no-csnp-authentication {
           description "Disable authentication for CSN packets";
           type empty;
         }
         leaf no-psnp-authentication {
           description "Disable authentication for PSN packets";
           type empty;
         }
         leaf no-lsp-authentication {
           description "Disable authentication for LSP packets";
           type empty;
         }
         leaf authentication-key-chain {
           description "Key chain name";
           type string {
             length "1 .. 128";
           }
         }
         leaf wide-metrics-only {
           description "Generate wide metrics only";
           type empty;
         }
         leaf preference {
           description "Preference of internal routes";
           type union {
             type uint32;
             type string {
               pattern "<.*>|$.*";
             }
           }
         }
         leaf external-preference {
           description "Preference of external routes";
           type union {
             type uint32;
             type string {
               pattern "<.*>|$.*";
             }
           }
         }
         leaf prefix-export-limit {
           description "Maximum number of external prefixes that can be exported";
           type union {
             type string {
               pattern "<.*>|$.*";
             }
             type uint32 {
               range "0 .. 4294967295";
             }
           }
         }
         leaf max-lsp-size {
           description "Maximum size allowed for LSPs";
           type union {
             type string {
               pattern "<.*>|$.*";
             }
             type uint32 {
               range "512 .. 9192";
             }
           }
         }
         container flood-reflector {
           description "Enable flood-reflector";
           uses apply-advanced;
           choice flood-reflector-choice {
             case case_1 {
               container reflector {
                 description "Configure this as a flood-reflector";
                 uses apply-advanced;
                 leaf cluster-id {
                   description "Cluster-ID";
                   type union {
                     type string {
                       pattern "<.*>|$.*";
                     }
                     type uint32 {
                       range "1 .. 4294967295";
                     }
                   }
                   mandatory true;
                 }
               }
             }
             case case_2 {
               leaf client {
                 description "Configure interface as flood-reflector client";
                 type empty;
               }
             }
           }
         }
       }
       list interface-group {
         key name;
         description "Interface grouping configuration";
         leaf name {
           description "Interface group name";
           type string;
         }
         uses apply-advanced;
         list level {
           key name;
           ordered-by user;
           description "Configure levels on this interface-group";
           leaf name {
             description "IS-IS level number";
             type union {
               type string {
                 pattern "<.*>|$.*";
               }
               type uint32 {
                 range "1 .. 2";
               }
             }
           }
           uses apply-advanced;
           container ipv4-adjacency-segment {
             description "Configure ipv4 adjacency segment";
             uses apply-advanced;
             container protected {
               description "Adjacency SID is eligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
                 mandatory true;
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                   mandatory true;
                 }
               }
             }
           }
         }
         container link-group-protection {
           description "Configure link group protection";
           uses apply-advanced;
           leaf minimum-bandwidth {
             description "Minimum bandwidth to carry traffic";
             type string;
           }
           leaf revert-bandwidth {
             description "Revert bandwidth to carry traffic";
             type string;
           }
         }
         list interface {
           key name;
           description "List interfaces for this group";
           leaf name {
             description "Interface name";
             type union {
               type jt:interface-name;
               type string {
                 pattern "<.*>|$.*";
               }
             }
           }
           uses apply-advanced;
           leaf weight {
             description "Interface weight for adjacency set";
             type union {
               type string {
                 pattern "<.*>|$.*";
               }
               type uint32 {
                 range "1 .. 255";
               }
             }
           }
         }
       }
       container spf-options {
         description "Configure SPF attributes";
         uses apply-advanced;
         container microloop-avoidance {
           description "Configure microloop avoidance mechanisms";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Set maximum number of label supported for Micro-Loop-Avoidance calculations";
               type union {
                 type string {
                   pattern "<.*>|$.*";
                 }
                 type uint32 {
                   range "2 .. 8";
                 }
               }
             }
             leaf maximum-srv6-sids {
               description "Set maximum number of SRV6 SIDs supported for Micro-Loop-Avoidance calculations";
               type union {
                 type string {
                   pattern "<.*>|$.*";
                 }
                 type uint32 {
                   range "2 .. 12";
                 }
               }
             }
           }
         }
         leaf delay {
           description "Time to wait before running an SPF";
           units "milliseconds";
           type union {
             type string {
               pattern "<.*>|$.*";
             }
             type uint32 {
               range "50 .. 1000";
             }
           }
         }
         leaf holddown {
           description "Time to hold down before running an SPF";
           units "milliseconds";
           type union {
             type string {
               pattern "<.*>|$.*";
             }
             type uint32 {
               range "1000 .. 10000";
             }
           }
         }
         leaf rapid-runs {
           description "Number of rapid SPF runs before SPF holddown";
           type union {
             type string {
               pattern "<.*>|$.*";
             }
             type uint32 {
               range "1 .. 5";
             }
           }
         }
         container multipath {
           description "Configure multipath options";
           uses apply-advanced;
           container weighted {
             description "Weighted multipath options";
             uses apply-advanced;
             leaf one-hop {
               description "Enable load balancing on onehop multipath based on interface bandwidth";
               type empty;
             }
           }
         }
       }
       container traceoptions {
         description "Trace options for IS-IS";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "post-convergence-lfa" {
                 description "Trace post-convergence-lfa related events";
               }
               enum "traffic-statistics" {
                 description "Trace traffic-statistics related events";
               }
               enum "error" {
                 description "Trace errored packets";
               }
               enum "spf" {
                 description "Trace SPF events";
               }
               enum "packets" {
                 description "Trace IS-IS packets";
               }
               enum "hello" {
                 description "Trace hello packets";
               }
               enum "lsp" {
                 description "Trace link-state packets";
               }
               enum "psn" {
                 description "Trace partial sequence number (PSN) packets";
               }
               enum "csn" {
                 description "Trace complete sequence number (CSN) packets";
               }
               enum "layer2-map" {
                 description "Trace ARP/ND kernel state manipulation";
               }
               enum "lsp-generation" {
                 description "Trace LSP generation";
               }
               enum "graceful-restart" {
                 description "Trace graceful restart events";
               }
               enum "ldp-synchronization" {
                 description "Trace synchronization between IS-IS and LDP";
               }
               enum "nsr-synchronization" {
                 description "Trace NSR synchronization events";
               }
               enum "spring" {
                 description "Trace source packet routing";
               }
               enum "prefix-sid" {
                 description "Trace source packet routing, prefix-sids";
               }
               enum "flex-algorithm" {
                 description "Trace flex-algorithm related events";
               }
               enum "adj-sid" {
                 description "Trace adj-sid related events";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "srv6" {
                 description "Trace srv6 related events";
               }
               enum "rmopd" {
                 description "Trace rmopd interactions";
               }
               enum "mapping-server" {
                 description "Trace mapping server related events";
               }
               enum "prefix-unreachable" {
                 description "Trace unreachable prefix advertisement related events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container backup-spf-options {
         description "Configure backup SPF attributes";
         uses apply-advanced;
         container remote-backup-calculation {
           presence "enable remote-backup-calculation";
           description "Calculate Remote LFA backup nexthops";
           uses apply-advanced;
         }
         container use-post-convergence-lfa {
           presence "enable use-post-convergence-lfa";
           description "Calculate Post Convergence Backup Nexthops";
           uses apply-advanced;
           leaf maximum-labels {
             description "Set maximum number of label supported for post convergence path calculations";
             type union {
               type string {
                 pattern "<.*>|$.*";
               }
               type uint32 {
                 range "2 .. 8";
               }
             }
           }
           leaf maximum-srv6-sids {
             description "Set maximum number of SRV6 SIDs for post convergence path calculations";
             type union {
               type string {
                 pattern "<.*>|$.*";
               }
               type uint32 {
                 range "2 .. 12";
               }
             }
           }
           leaf maximum-backup-paths {
             description "Set maximum equal cost backup post convergence paths";
             type union {
               type string {
                 pattern "<.*>|$.*";
               }
               type uint32 {
                 range "1 .. 8";
               }
             }
           }
         }
         container use-source-packet-routing {
           presence "enable use-source-packet-routing";
           description "Use SPRING routed paths for protection";
           uses apply-advanced;
         }
         leaf per-prefix-calculation {
           description "Calculate backup nexthops for non-best prefix originators";
           type empty;
         }
         leaf node-link-degradation {
           description "Degrade to link protection when nodelink protection not available";
           type empty;
         }
       }
       list context-identifier {
         key name;
         ordered-by user;
         description "Configuration for advertisement of a context-identifier ";
         leaf name {
           description "Context identifier range";
           type jt:ipprefix;
         }
         uses apply-advanced;
         list level {
           key name;
           ordered-by user;
           description "Configure global level attributes";
           leaf name {
             description "IS-IS level number";
             type union {
               type string {
                 pattern "<.*>|$.*";
               }
               type uint32 {
                 range "1 .. 2";
               }
             }
           }
           uses apply-advanced;
           choice enable-disable {
             case case_1 {
               leaf disable {
                 description "Disable advertisements to this level";
                 type empty;
               }
             }
           }
         }
       }
       container traffic-engineering {
         description "Configure traffic engineering attributes";
         uses apply-advanced;
         choice enable-disable {
           case case_1 {
             leaf disable {
               description "Disable traffic engineering";
               type empty;
             }
           }
         }
         leaf l3-unicast-topology {
           description "Download IGP topology into TED";
           type empty;
         }
         leaf ipv6 {
           description "Enable TEDv6";
           type empty;
         }
         leaf credibility-protocol-preference {
           description "Follow IGP protocol preference for TED protocol credibility";
           type empty;
         }
         leaf ipv4-multicast-rpf-routes {
           description "Install IPv4 routes for multicast RPF checks into inet.2";
           status deprecated;
           type empty;
         }
         leaf ignore-lsp-metrics {
           description "Ignore label-switched path metrics when doing shortcuts";
           type empty;
         }
         container tunnel-source-protocol {
           description "Protocols from which to pick label-switched paths";
           uses apply-advanced;
           container rsvp {
             presence "enable rsvp";
             description "Pick label-switched paths from rsvp";
             uses apply-advanced;
             leaf preference {
               description "Preference for label-switched paths from this protocol";
               type union {
                 type string {
                   pattern "<.*>|$.*";
                 }
                 type uint32 {
                   range "1 .. 255";
                 }
               }
             }
           }
           container spring-te {
             presence "enable spring-te";
             description "Pick label-switched paths from spring-te";
             uses apply-advanced;
             leaf preference {
               description "Preference for label-switched paths from this protocol";
               type union {
                 type string {
                   pattern "<.*>|$.*";
                 }
                 type uint32 {
                   range "1 .. 255";
                 }
               }
             }
           }
         }
         list family {
           key name;
           ordered-by user;
           description "Address family specific traffic-engineering attributes";
           leaf name {
             type enumeration {
               enum "inet" {
                 description "IPv4 family";
               }
               enum "inet6" {
                 description "IPv6 family";
               }
               enum "inet-mpls" {
                 description "IPv4-MPLS family";
               }
               enum "inet6-mpls" {
                 description "IPv6-MPLS family";
               }
             }
           }
           uses apply-advanced;
           container shortcuts {
             presence "enable shortcuts";
             description "Use label-switched paths as next hops, if possible";
             uses apply-advanced;
             leaf multicast-rpf-routes {
               description "Install routes for multicast RPF checks into multicast RIB";
               type empty;
             }
             leaf-list import {
               ordered-by user;
               description "Import policy for shortcut";
               type jt:policy-algebra;
             }
           }
         }
         container shortcuts {
           presence "enable shortcuts";
           description "Use label-switched paths as next hops, if possible";
           status deprecated;
           uses apply-advanced;
           leaf ignore-lsp-metrics {
             description "Ignore label-switched path metrics when doing shortcuts";
             status deprecated;
             type empty;
           }
         }
         container multipath {
           description "Configure label-switched-path multipath behavior";
           uses apply-advanced;
           leaf lsp-equal-cost {
             description "Include equal cost label-switched-paths";
             type empty;
           }
         }
         container advertisement {
           description "Configure traffic engineering attribute advertisements";
           uses apply-advanced;
           leaf always {
             description "Advertise applicable legacy TE attributes always";
             type empty;
           }
           container application-specific {
             description "Advertise application-specific TE attributes";
             uses apply-advanced;
             container all-applications {
               presence "enable all-applications";
               description "Advertise common application-specific link attributes";
               uses apply-advanced;
               leaf legacy {
                 description "Use legacy TE attributes for this application";
                 type empty;
               }
             }
           }
         }
       }
       list label-switched-path {
         key name;
         ordered-by user;
         description "Configuration for advertisement of a label-switched path";
         leaf name {
           description "Name of label-switched path to be advertised";
           type string {
             length "1 .. 64";
           }
         }
         uses apply-advanced;
         list level {
           key name;
           ordered-by user;
           description "Configure global level attributes";
           leaf name {
             description "IS-IS level number";
             type union {
               type string {
                 pattern "<.*>|$.*";
               }
               type uint32 {
                 range "1 .. 2";
               }
             }
           }
           uses apply-advanced;
           choice enable-disable {
             case case_1 {
               leaf disable {
                 description "Disable advertisements to this level";
                 type empty;
               }
             }
           }
           leaf metric {
             description "SPF metric for this level";
             type union {
               type string {
                 pattern "<.*>|$.*";
               }
               type uint32 {
                 range "0 .. 16777215";
               }
             }
           }
         }
       }
       choice enable-disable {
         case case_1 {
           leaf disable {
             description "Disable IS-IS";
             type empty;
           }
         }
       }
       leaf-list export {
         ordered-by user;
         description "Export policy";
         type jt:policy-algebra;
       }
       leaf-list import {
         ordered-by user;
         description "Import policy";
         type jt:policy-algebra;
       }
       leaf reference-bandwidth {
         description "Bandwidth for calculating metric defaults";
         type string;
       }
       choice layer2-map-choice {
         leaf layer2-map {
           description "Kernel ARP/ND creation for nexthops";
           type empty;
         }
         leaf no-layer2-map {
           description "Don't kernel ARP/ND creation for nexthops";
           type empty;
         }
       }
       leaf job-stats {
         description "Collect job statistics";
         type empty;
       }
       leaf lsp-lifetime {
         description "Lifetime of LSPs";
         units "seconds";
         type union {
           type string {
             pattern "<.*>|$.*";
           }
           type uint32 {
             range "350 .. 65535";
           }
         }
       }
       leaf max-lsp-size {
         description "Maximum size allowed for LSPs";
         default "1492";
         type union {
           type string {
             pattern "<.*>|$.*";
           }
           type uint32 {
             range "512 .. 9192";
           }
         }
       }
       leaf max-hello-size {
         description "Maximum size allowed for ISIS Hello PDUs";
         default "1492";
         type union {
           type string {
             pattern "<.*>|$.*";
           }
           type uint32 {
             range "512 .. 16000";
           }
         }
       }
       leaf max-snp-size {
         description "Maximum size allowed for Sequence Number (Complete/Partial) PDUs";
         default "1400";
         type union {
           type string {
             pattern "<.*>|$.*";
           }
           type uint32 {
             range "512 .. 1400";
           }
         }
       }
       leaf spf-delay {
         description "Time to wait before running an SPF";
         status deprecated;
         units "milliseconds";
         type union {
           type string {
             pattern "<.*>|$.*";
           }
           type uint32 {
             range "50 .. 120000";
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf loose-authentication-check {
         description "Verify authentication only if PDU has authentication TLV";
         type empty;
       }
       leaf max-areas {
         description "Maximum number of advertised Areas";
         default "3";
         type union {
           type string {
             pattern "<.*>|$.*";
           }
           type uint32 {
             range "3 .. 64";
           }
         }
       }
       leaf no-authentication-check {
         description "Disable authentication checking";
         type empty;
       }
       leaf no-ipv4-routing {
         description "Disable IPv4 routing";
         type empty;
       }
       leaf no-ipv6-routing {
         description "Disable IPv6 routing";
         type empty;
       }
       leaf no-adjacency-holddown {
         description "Disable adjacency hold down";
         type empty;
       }
       leaf multicast-topology {
         description "Enable multicast topology";
         status deprecated;
         type empty;
       }
       leaf ignore-attached-bit {
         description "Ignore the attached bit in Level 1 LSPs";
         type empty;
       }
       container rib-group {
         description "Routing table group for importing IS-IS routes";
         uses rib_group_type;
       }
       container no-external-export {
         description "No external export";
         uses apply-advanced;
         list protocol {
           key name;
           ordered-by user;
           description "Protocol parameters";
           leaf name {
             type enumeration {
               enum "bgp" {
                 description "BGP";
               }
               enum "ospf" {
                 description "OSPF";
               }
               enum "isis" {
                 description "ISIS";
               }
               enum "l-isis" {
                 description "Labelled ISIS";
               }
               enum "l-ospf" {
                 description "Labelled OSPF";
               }
               enum "static" {
                 description "Static";
               }
             }
           }
         }
       }
       container strict-dual-isis {
         presence "enable strict-dual-isis";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container topologies {
         description "Enable topologies";
         uses apply-advanced;
         leaf ipv4-multicast {
           description "Enable IPv4-multicast topology";
           type empty;
         }
         leaf ipv6-unicast {
           description "Enable IPv6-unicast topology";
           type empty;
         }
         leaf ipv6-multicast {
           description "Enable IPv6-multicast topology";
           type empty;
         }
       }
       container overload {
         presence "enable overload";
         description "Set the overload bit (no transit traffic)";
         uses apply-advanced;
         leaf timeout {
           description "Time after which overload bit is reset";
           units "seconds";
           type union {
             type string {
               pattern "<.*>|$.*";
             }
             type uint32 {
               range "60 .. 3600";
             }
           }
         }
         leaf advertise-high-metrics {
           description "Advertise high metrics instead of setting the overload bit";
           type empty;
         }
         leaf allow-route-leaking {
           description "Allow routes to be leaked when overload is configured";
           type empty;
         }
         leaf internal-prefixes {
           description "Allow internal prefixes to be advertised with high metric";
           type empty;
         }
         leaf external-prefixes {
           description "Allow external prefixes to be advertised with high metric";
           type empty;
         }
       }
       container dynamic-overload {
         description "Set the dynamic overload options";
         uses apply-advanced;
         leaf no-overload-on-prefix-export-limit {
           description "Do not set overload bit when prefix export limit is reached";
           type empty;
         }
         leaf auto-recovery {
           description "Enable Auto recovery to recover from dynamic overload state";
           type empty;
         }
       }
       container graceful-restart {
         description "IS-IS graceful restart options";
         choice enable-disable {
           case case_1 {
             leaf disable {
               description "Disable graceful restart";
               type empty;
             }
           }
         }
         leaf helper-disable {
           description "Disable graceful restart helper capability";
           type empty;
         }
         leaf restart-duration {
           description "Maximum time for graceful restart to finish";
           units "seconds";
           type union {
             type string {
               pattern "<.*>|$.*";
             }
             type uint32 {
               range "30 .. 300";
             }
           }
         }
       }
       list net {
         key name;
         description "Assign Network Entity Title (NET) configuration";
         leaf name {
           description "Assign Network Entity Title (NET) address to an IS-IS router";
           type jt:isoaddr;
         }
       }
       leaf rfc7775-compliance {
         description "RFC 7775 compliance for up/down bit and prefix attribute sub-tlv";
         type empty;
       }
       container pixel-tracing {
         description "Pixel-tracing for IS-IS";
         uses apply-advanced;
         choice enable-disable {
           case case_1 {
             leaf disable {
               description "Disable pixel-tracing for IS-IS";
               type empty;
             }
           }
         }
       }
     }
     container l2iw {
       presence "enable l2iw";
       description "Configuration for Layer 2 interworking";
       uses apply-advanced;
       container traceoptions {
         description "Trace options for Layer 2 circuits";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf dynamic-peer-discovery {
         description "Create l2iw peers dynamically based on local site-id";
         type empty;
       }
     }
     container l2circuit {
       description "Configuration for Layer 2 circuits over MPLS";
       uses apply-advanced;
       container traceoptions {
         description "Trace options for Layer 2 circuits";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 circuit topology changes";
               }
               enum "fec" {
                 description "Trace Layer 2 circuit VC FEC advertisements";
               }
               enum "connections" {
                 description "Trace Layer 2 circuit connections";
               }
               enum "oam" {
                 description "Trace Layer 2 circuit OAM messages";
               }
               enum "egress-protection" {
                 description "Trace Layer 2 circuit egress protection messages";
               }
               enum "auto-sensing" {
                 description "Trace Layer 2 circuit PW auto-sensing";
               }
               enum "sdb" {
                 description "Trace SDB";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list neighbor {
         key name;
         ordered-by user;
         description "List of Layer 2 circuits to this neighbor";
         leaf name {
           description "Neighbor ID";
           type jt:ipv4addr;
         }
         uses apply-advanced;
         list interface {
           key name;
           ordered-by user;
           description "Interface forming the Layer 2 circuit";
           leaf name {
             description "Interface name";
             type union {
               type jt:interface-name;
               type string {
                 pattern "<.*>|$.*";
               }
             }
           }
           uses apply-advanced;
           container static {
             presence "enable static";
             description "Configuration of static Pseudowire";
             uses apply-advanced;
             leaf incoming-label {
               description "Layer 2 circuit incoming static label";
               type union {
                 type string {
                   pattern "<.*>|$.*";
                 }
                 type uint32 {
                   range "16 .. 1048575";
                 }
               }
               mandatory true;
             }
             leaf outgoing-label {
               description "Layer 2 circuit outgoing static label";
               type union {
                 type string {
                   pattern "<.*>|$.*";
                 }
                 type uint32 {
                   range "16 .. 1048575";
                 }
               }
               mandatory true;
             }
             leaf send-oam {
               description "Turn on sending of l2ckt ping";
               type empty;
             }
           }
           leaf psn-tunnel-endpoint {
             description "Endpoint of the transport tunnel on the remote PE";
             type jt:ipv4addr;
           }
           leaf protect-interface {
             description "Name of protect interface";
             type union {
               type jt:interface-name;
               type string {
                 pattern "<.*>|$.*";
               }
             }
           }
           leaf virtual-circuit-id {
             description "Identifier for this Layer 2 circuit";
             type union {
               type string {
                 pattern "<.*>|$.*";
               }
               type uint32 {
                 range "1 .. 4294967295";
               }
             }
             mandatory true;
           }
           leaf description {
             description "Text description of Layer 2 circuit";
             type string;
           }
           choice control-word-choice {
             leaf control-word {
               description "Add control word to the Layer 2 encapsulation";
               type empty;
             }
             leaf no-control-word {
               description "Don't add control word to the Layer 2 encapsulation";
               type empty;
             }
           }
           leaf flow-label-transmit {
             description "Advertise capability to push Flow Label in transmit direction to remote PE";
             type empty;
           }
           leaf flow-label-transmit-static {
             description "Push Flow Label on PW packets sent to remote PE";
             type empty;
           }
           leaf flow-label-receive {
             description "Advertise capability to pop Flow Label in receive direction to remote PE";
             type empty;
           }
           leaf flow-label-receive-static {
             description "Pop Flow Label from PW packets received from remote PE";
             type empty;
           }
           leaf community {
             description "Community associated with this Layer 2 circuit";
             type string;
           }
           leaf mtu {
             description "MTU to be advertised for this Layer 2 circuit";
             type union {
               type string {
                 pattern "<.*>|$.*";
               }
               type uint32 {
                 range "512 .. 65535";
               }
             }
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
           leaf no-revert {
             description "Don't revert to primary-interface";
             type empty;
           }
           container bandwidth {
             description "Bandwidth to reserve (bps)";
             uses bandwidth-type;
           }
           leaf send-ip-addr-list-tlv {
             description "Send IP ADDR LIST TLV to remote side";
             type empty;
           }
           container pseudowire-status-tlv {
             presence "enable pseudowire-status-tlv";
             description "Send pseudowire status TLV";
             uses apply-advanced;
             leaf hot-standby-vc-on {
               description "Activate pseudowire upon arrival of 'hot-standby' status TLV message";
               type empty;
             }
           }
           leaf switchover-delay {
             description "Layer 2 circuit switchover delay";
             default "10000";
             units "milliseconds";
             type union {
               type string {
                 pattern "<.*>|$.*";
               }
               type uint32 {
                 range "0 .. 180000";
               }
             }
           }
           container revert-time {
             presence "enable revert-time";
             description "Enable pseudowire redundancy reversion";
             leaf delay {
               description "Reversion timer (seconds)";
               units "seconds";
               type union {
                 type string {
                   pattern "<.*>|$.*";
                 }
                 type uint32 {
                   range "0 .. 3600";
                 }
               }
               mandatory true;
             }
             leaf maximum {
               description "Maximum reversion interval to add over revert-time delay";
               units "seconds";
               type union {
                 type string {
                   pattern "<.*>|$.*";
                 }
                 type uint32 {
                   range "0 .. 7200";
                 }
               }
             }
           }
           leaf connection-protection {
             description "End-2-end protection via OAM failure detection";
             type empty;
           }
           list backup-neighbor {
             key name;
             ordered-by user;
             description "Configuration of redundant l2circuit";
             leaf name {
               description "Neighbor ID";
               type jt:ipv4addr;
             }
             uses apply-advanced;
             container static {
               presence "enable static";
               description "Configuration of static Pseudowire";
               uses apply-advanced;
               leaf incoming-label {
                 description "Layer 2 circuit incoming static label";
                 type union {
                   type string {
                     pattern "<.*>|$.*";
                   }
                   type uint32 {
                     range "16 .. 1048575";
                   }
                 }
                 mandatory true;
               }
               leaf outgoing-label {
                 description "Layer 2 circuit outgoing static label";
                 type union {
                   type string {
                     pattern "<.*>|$.*";
                   }
                   type uint32 {
                     range "16 .. 1048575";
                   }
                 }
                 mandatory true;
               }
             }
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               type string;
             }
             leaf psn-tunnel-endpoint {
               description "Endpoint of the transport tunnel on the remote PE";
               type jt:ipv4addr;
             }
             leaf standby {
               description "Keep backup pseudowire in continuous standby";
               type empty;
             }
             leaf hot-standby {
               description "Keep backup pseudowire in continuous standby mode and ready for traffic forwarding";
               type empty;
             }
           }
           container oam {
             description "OAM Configuration for Layer 2 circuit";
             uses apply-advanced;
             leaf ping-interval {
               description "Time interval between ping messages";
               default "60";
               units "seconds";
               type union {
                 type string {
                   pattern "<.*>|$.*";
                 }
                 type uint16 {
                   range "30 .. 3600";
                 }
               }
             }
             leaf ping-multiplier {
               description "Number of ping reply missed before declaring BFD down";
               type union {
                 type string {
                   pattern "<.*>|$.*";
                 }
                 type uint8 {
                   range "1 .. 5";
                 }
               }
             }
           }
           container egress-protection {
             description "Egress protection for Layer 2 circuit";
             uses apply-advanced;
             choice protection-type {
               case case_1 {
                 leaf protector-interface {
                   description "Name of the protector interface for local protection";
                   type union {
                     type jt:interface-name;
                     type string {
                       pattern "<.*>|$.*";
                     }
                   }
                 }
               }
               case case_2 {
                 container protector-pe {
                   description "Address of the protector PE";
                   leaf address {
                     description "Address of the protector PE";
                     type jt:ipv4addr;
                     mandatory true;
                   }
                   leaf context-identifier {
                     description "Identifier of the context used for this protection";
                     type jt:ipv4addr;
                     mandatory true;
                   }
                   leaf lsp {
                     description "Name of the label-switched path used for the protection";
                     type string {
                     }
                   }
                 }
               }
             }
             container protected-l2circuit {
               description "Primary Layer 2 circuit to be protected";
               leaf l2circuit-name {
                 description "Name of the protected Layer 2 circuit";
                 type string {
                 }
                 mandatory true;
               }
               leaf ingress-pe {
                 description "Ingress PE address of the protected Layer 2 circuit";
                 type jt:ipv4addr;
                 mandatory true;
               }
               leaf egress-pe {
                 description "Egress PE address of the protected Layer 2 circuit";
                 type jt:ipv4addr;
                 mandatory true;
               }
               leaf virtual-circuit-id {
                 description "Identifier of the protected Layer 2 circuit";
                 type union {
                   type string {
                     pattern "<.*>|$.*";
                   }
                   type uint32 {
                     range "1 .. 4294967295";
                   }
                 }
                 mandatory true;
               }
             }
           }
         }
       }
       container local-switching {
         description "Configuration of Layer 2 circuits local switching";
         uses apply-advanced;
         list interface {
           key name;
           ordered-by user;
           description "Interface forming the local Layer 2 circuit";
           leaf name {
             description "Interface name";
             type union {
               type jt:interface-name;
               type string {
                 pattern "<.*>|$.*";
               }
             }
           }
           uses apply-advanced;
           leaf no-revert {
             description "Do not revert to primary-interface";
             type empty;
           }
           leaf protect-interface {
             description "Name of protect interface";
             type union {
               type jt:interface-name;
               type string {
                 pattern "<.*>|$.*";
               }
             }
           }
           leaf connection-protection {
             description "End-2-end protection via OAM failure detection";
             type empty;
           }
           list neighbor {
             key name;
             ordered-by user;
             description "Configuration of Layer 2 circuit";
             leaf name {
               description "Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
               mandatory true;
             }
             leaf community {
               description "Community associated with this Layer 2 circuit";
               type string;
             }
             leaf psn-tunnel-endpoint {
               description "Endpoint of the transport tunnel on the neighbor PE";
               type jt:ipv4addr;
             }
             leaf mtu {
               description "MTU to be advertised for this Layer 2 circuit";
               type union {
                 type string {
                   pattern "<.*>|$.*";
                 }
                 type uint32 {
                   range "512 .. 65535";
                 }
               }
             }
           }
           list backup-neighbor {
             key name;
             ordered-by user;
             description "Configuration of redundant l2circuit";
             leaf name {
               description "Backup Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
               mandatory true;
             }
             leaf psn-tunnel-endpoint {
               description "Endpoint of the transport tunnel on the backup neighbor PE";
               type jt:ipv4addr;
             }
             leaf community {
               description "Community associated with this Layer 2 circuit";
               type string;
             }
             leaf mtu {
               description "MTU to be advertised for this Layer 2 circuit";
               type union {
                 type string {
                   pattern "<.*>|$.*";
                 }
                 type uint32 {
                   range "512 .. 65535";
                 }
               }
             }
           }
           container end-interface {
             description "Interface name of the other end point";
             uses apply-advanced;
             leaf interface {
               description "Interface name";
               type union {
                 type jt:interface-name;
                 type string {
                   pattern "<.*>|$.*";
                 }
               }
             }
             leaf no-revert {
               description "Do not revert to primary-interface";
               type empty;
             }
             leaf protect-interface {
               description "Name of protect interface";
               type union {
                 type jt:interface-name;
                 type string {
                   pattern "<.*>|$.*";
                 }
               }
             }
             leaf backup-interface {
               description "Name of backup interface";
               type union {
                 type jt:interface-name;
                 type string {
                   pattern "<.*>|$.*";
                 }
               }
             }
           }
           leaf description {
             description "Text description of Layer 2 circuit";
             type string;
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
         }
       }
       container auto-sensing {
         presence "enable auto-sensing";
         description "Configuration of PW auto-sensing";
         uses apply-advanced;
         leaf password {
           description "Password for authentication with Radius server; 15 characters maximum";
           type string {
             length "0 .. 15";
           }
           mandatory true;
         }
       }
       container resolution {
         description "Configuration of PW nexthop resolution";
         uses apply-advanced;
         leaf preserve-nexthop-hierarchy {
           description "Install expanded hierarchy";
           type empty;
         }
       }
     }
     container l2vpn {
       description "Configuration for Layer 2 VPN circuits over MPLS";
       uses apply-advanced;
       container resolution {
         description "Configuration of PW nexthop resolution";
         uses apply-advanced;
         leaf preserve-nexthop-hierarchy {
           description "Install expanded hierarchy";
           type empty;
         }
       }
     }
     container link-management {
       description "LMP options";
       uses juniper-protocols-lmp;
     }
     container msdp {
       description "MSDP configuration";
       uses juniper-protocols-msdp;
     }
     container mvpn {
       description "BGP-MVPN configuration";
       uses juniper-protocols-mvpn;
     }
     container ospf {
       description "OSPF configuration";
       uses juniper-protocols-ospf;
     }
     list ospf-instance {
       key name;
       ordered-by user;
       description "Multi-instance OSPF configuration";
       leaf name {
         description "OSPF instance name";
         type string;
       }
       uses apply-advanced;
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           type string;
         }
         container spf-options {
           description "Configure options for SPF";
           uses apply-advanced;
           container microloop-avoidance {
             description "Configure microloop avoidance mechanism";
             uses apply-advanced;
             container post-convergence-path {
               presence "enable post-convergence-path";
               description "Temporarily install post-convergence path for routes potentially affected by microloops";
               uses apply-advanced;
               leaf delay {
                 description "Time after which temporary post-convergence paths are removed";
                 units "milliseconds";
                 type union {
                   type string {
                     pattern "<.*>|$.*";
                   }
                   type uint32 {
                     range "500 .. 60000";
                   }
                 }
               }
               leaf maximum-labels {
                 description "Maximum number of labels installed for post-convergence paths";
                 type union {
                   type string {
                     pattern "<.*>|$.*";
                   }
                   type uint32 {
                     range "2 .. 8";
                   }
                 }
               }
             }
           }
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
           container multipath {
             description "Configure multipath options";
             uses apply-advanced;
             container weighted {
               description "Weighted multipath options";
               uses apply-advanced;
               leaf one-hop {
                 description "Enable load balancing on onehop multipath based on interface bandwidth";
                 type empty;
               }
             }
           }
         }
         container backup-spf-options {
           description "Configure options for backup SPF";
           uses apply-advanced;
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 8";
                 }
               }
             }
             leaf maximum-backup-paths {
               description "Maximum number of equal-cost post-convergence paths installed";
               type union {
                 type string {
                   pattern "<.*>|$.*";
                 }
                 type uint32 {
                   range "1 .. 8";
                 }
               }
             }
           }
           leaf use-source-packet-routing {
             description "Use spring backup paths for inet.0 routes";
             type empty;
           }
           leaf disable {
             description "Do not run backup SPF";
             type empty;
           }
           leaf no-install {
             description "Do not install backup nexthops into the RIB";
             type empty;
           }
           leaf downstream-paths-only {
             description "Use only downstream backup paths";
             type empty;
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
         }
         leaf prefix-export-limit {
           description "Maximum number of prefixes that can be exported";
           type union {
             type string {
               pattern "<.*>|$.*";
             }
             type uint32 {
               range "0 .. 4294967295";
             }
           }
         }
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       container traffic-engineering {
         presence "enable traffic-engineering";
         description "Configure traffic engineering attributes";
         uses apply-advanced;
         leaf no-topology {
           description "Disable dissemination of TE link-state topology information";
           type empty;
         }
         leaf multicast-rpf-routes {
           description "Install routes for multicast RPF checks into inet.2";
           type empty;
         }
         leaf l3-unicast-topology {
           description "Download IGP topology into TED";
           type empty;
         }
         container ignore-lsp-metrics {
           presence "enable ignore-lsp-metrics";
           description "Ignore label-switched path metrics when doing shortcuts";
           uses apply-advanced;
           leaf unconfigured-only {
             description "Ignore lsp metrics for unconfigured only";
             type empty;
           }
         }
         container shortcuts {
           presence "enable shortcuts";
           description "Use label-switched paths as next hops, if possible";
           uses apply-advanced;
           leaf ignore-lsp-metrics {
             description "Ignore label-switched path metrics when doing shortcuts";
             status deprecated;
             type empty;
           }
           leaf lsp-metric-into-summary {
             description "Advertise LSP metric into summary LSAs";
             type empty;
           }
           list family {
             key name;
             ordered-by user;
             description "Address family specific traffic-engineering attributes";
             leaf name {
               type enumeration {
                 enum "inet" {
                   description "IPv4 family";
                 }
                 enum "inet-mpls" {
                   description "IPv4-MPLS family";
                 }
               }
             }
             uses apply-advanced;
           }
         }
         leaf advertise-unnumbered-interfaces {
           description "Advertise unnumbered interfaces";
           type empty;
         }
         leaf credibility-protocol-preference {
           description "TED protocol credibility follows protocol preference";
           type empty;
         }
         container advertisement {
           description "Advertise TE parameters even if RSVP is not turned on";
           uses apply-advanced;
           leaf always {
             description "Advertise TE parameters in TE LSAs";
             type empty;
           }
         }
         container tunnel-source-protocol {
           description "Protocols from which to pick label-switched paths";
           uses apply-advanced;
           container rsvp {
             presence "enable rsvp";
             description "Pick label-switched paths from rsvp";
             uses apply-advanced;
             leaf preference {
               description "Preference for label-switched paths from this protocol";
               type union {
                 type string {
                   pattern "<.*>|$.*";
                 }
                 type uint32 {
                   range "1 .. 255";
                 }
               }
             }
           }
           container spring-te {
             presence "enable spring-te";
             description "Pick label-switched paths from spring-te";
             uses apply-advanced;
             leaf preference {
               description "Preference for label-switched paths from this protocol";
               type union {
                 type string {
                   pattern "<.*>|$.*";
                 }
                 type uint32 {
                   range "1 .. 255";
                 }
               }
             }
           }
         }
       }
       leaf flex-algorithm-preference {
         description "Preference of flex-algorithm L-OSPF routes";
         type union {
           type uint32;
           type string {
             pattern "<.*>|$.*";
           }
         }
       }
       container source-packet-routing {
         presence "enable source-packet-routing";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 199999";
               }
             }
           }
           leaf index-range {
             description "Set range of node segment indices allowed";
             type union {
               type string {
                 pattern "<.*>|$.*";
               }
               type uint32 {
                 range "32 .. 16385";
               }
             }
           }
         }
         container srgb {
           description "Set the SRGB global block in SPRING";
           leaf start-label {
             description "Start range for SRGB label block";
             type union {
               type string {
                 pattern "<.*>|$.*";
               }
               type uint32;
             }
             mandatory true;
           }
           leaf index-range {
             description "Index to the SRGB start label block";
             type union {
               type string {
                 pattern "<.*>|$.*";
               }
               type uint32;
             }
             mandatory true;
           }
         }
         leaf mapping-server {
           description "Mapping server name";
           type string;
         }
         leaf install-prefix-sid-for-best-route {
           description "For best route install a exact prefix sid route";
           type empty;
         }
         leaf ldp-stitching {
           description "Enable SR to LDP stitching";
           type empty;
         }
         leaf-list flex-algorithm {
           description "Flex-algorithms we would like to participate in";
           type union {
             type string {
               pattern "<.*>|$.*";
             }
             type uint32 {
               range "128 .. 255";
             }
           }
           max-elements 16;
         }
         leaf strict-asla-based-flex-algorithm {
           description "Flex-Algorithm to ignore links not having ASLA sub-TLVs";
           type empty;
         }
         container sensor-based-stats {
           description "Configure sensor based stats in SPRING";
           uses apply-advanced;
           container per-interface-per-member-link {
             description "Configure sensor based stats per nexthop";
             leaf ingress {
               description "Enable sensor based stats on ingress interface";
               type empty;
             }
             leaf egress {
               description "Enable sensor based stats on egress interface";
               type empty;
             }
           }
           container per-sid {
             description "Configure sensor based stats per spring route";
             leaf ingress {
               description "Enable sensor based stats for per-sid ingress accounting";
               type empty;
             }
             leaf egress {
               description "Enable sensor based stats for IP-MPLS egress accounting";
               type empty;
             }
           }
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                     mandatory true;
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
         }
         list sham-link-remote {
           key name;
           ordered-by user;
           description "Configure parameters for remote sham link endpoint";
           leaf name {
             description "Remote sham link endpoint address";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf keychain {
             description "Key chain name";
             type string {
               length "1 .. 128";
             }
           }
         }
         list interface {
           key name;
           ordered-by user;
           description "Include an interface in this area";
           leaf name {
             description "Interface name";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           choice protection-type {
             case case_1 {
               leaf link-protection {
                 description "Protect interface from link faults only";
                 type empty;
               }
             }
             case case_2 {
               leaf node-link-protection {
                 description "Protect interface from both link and node faults";
                 type empty;
               }
             }
           }
           leaf no-eligible-backup {
             description "Not eligible to backup traffic from protected interfaces";
             type empty;
           }
           leaf no-eligible-remote-backup {
             description "Not eligible for Remote-LFA backup traffic from protected interfaces";
             type empty;
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 type jt:ipv4addr;
               }
             }
           }
           leaf secondary {
             description "Treat interface as secondary";
             type empty;
           }
           leaf own-router-lsa {
             description "Generate a separate router LSA for this interface";
             type empty;
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
           leaf metric {
             description "Interface metric";
             type union {
               type string {
                 pattern "<.*>|$.*";
               }
               type uint16 {
                 range "1 .. 65535";
               }
             }
           }
           leaf priority {
             description "Designated router priority";
             type union {
               type string {
                 pattern "<.*>|$.*";
               }
               type uint32 {
                 range "0 .. 255";
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "1 .. 255000";
                   }
                 }
                 mandatory true;
               }
             }
             leaf full-neighbors-only {
               description "Setup BFD sessions only to Full neighbors";
               type empty;
             }
             leaf holddown-interval {
               description "Time to hold the session-UP notification to the client";
               units "milliseconds";
               type union {
                 type string {
                   pattern "<.*>|$.*";
                 }
                 type uint32 {
                   range "0 .. 255000";
                 }
               }
             }
           }
           leaf dynamic-neighbors {
             description "Learn neighbors dynamically on a p2mp interface";
             type empty;
           }
           leaf no-advertise-adjacency-segment {
             description "Do not advertise an adjacency segment for this interface";
             type empty;
           }
           list neighbor {
             key name;
             ordered-by user;
             description "NBMA neighbor";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
           leaf strict-bfd {
             description "Enable strict bfd over this interface";
             type empty;
           }
           container post-convergence-lfa {
             presence "enable post-convergence-lfa";
             description "Protect interface using post-convergence backup path";
             uses apply-advanced;
             container node-protection {
               presence "enable node-protection";
               description "Compute backup path assuming node failure";
               uses apply-advanced;
               leaf cost {
                 description "Cost for node protection";
                 type union {
                   type string {
                     pattern "<.*>|$.*";
                   }
                   type uint16 {
                     range "1 .. 65535";
                   }
                 }
               }
             }
             leaf srlg-protection {
               description "Compute backup path assuming SRLG failure";
               type empty;
             }
             leaf fate-sharing-protection {
               description "Compute backup path assuming fate-sharing group failure";
               type empty;
             }
           }
           leaf te-metric {
             description "Traffic engineering metric";
             type union {
               type string {
                 pattern "<.*>|$.*";
               }
               type uint32 {
                 range "1 .. 4294967295";
               }
             }
           }
           container ldp-synchronization {
             description "Advertise maximum metric until LDP is operational";
             presence "enable ldp-synchronization";
             uses ldp-sync-obj;
           }
           container ipv4-adjacency-segment {
             description "Configure ipv4 adjacency segment";
             uses apply-advanced;
             container protected {
               description "Adjacency SID is eligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list lan-neighbor {
             key name;
             ordered-by user;
             description "Configuration specific to a LAN neighbor";
             leaf name {
               description "Address of neighbor";
               type jt:ipaddr;
             }
             uses apply-advanced;
             container ipv4-adjacency-segment {
               description "Configure ipv4 adjacency segment";
               uses apply-advanced;
               container protected {
                 description "Adjacency SID is eligible for protection";
                 uses apply-advanced;
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 uses apply-advanced;
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
           }
           leaf delay-metric {
             description "Delay metric";
             units "microseconds";
             type union {
               type string {
                 pattern "<.*>|$.*";
               }
               type uint32 {
                 range "0 .. 16777215";
               }
             }
           }
           container delay-measurement {
             presence "enable delay-measurement";
             description "Enable delay measurement";
             uses apply-advanced;
             leaf probe-interval {
               description "Probe interval";
               units "seconds";
               type union {
                 type string {
                   pattern "<.*>|$.*";
                 }
                 type uint32 {
                   range "1 .. 255";
                 }
               }
             }
             leaf probe-count {
               description "Probe count";
               type union {
                 type string {
                   pattern "<.*>|$.*";
                 }
                 type uint32 {
                   range "1 .. 15";
                 }
               }
             }
             container normalize {
               description "Normalize Measured Link Delay";
               leaf interval {
                 description "The value of the normalized interval in microseconds.";
                 units "microseconds";
                 type union {
                   type string {
                     pattern "<.*>|$.*";
                   }
                   type uint32 {
                     range "1 .. 5000000";
                   }
                 }
                 mandatory true;
               }
               leaf offset {
                 description "The value of the normalized offset in microseconds (Must be < normalized interval).";
                 units "microseconds";
                 type union {
                   type string {
                     pattern "<.*>|$.*";
                   }
                   type uint32 {
                     range "1 .. 5000000";
                   }
                 }
                 mandatory true;
               }
             }
             container advertisement {
               description "Delay advertisement";
               uses apply-advanced;
               container periodic {
                 description "Periodic advertisement parameters";
                 uses apply-advanced;
                 leaf threshold {
                   description "Threshold";
                   units "percentage";
                   type union {
                     type string {
                       pattern "<.*>|$.*";
                     }
                     type uint32 {
                       range "0 .. 100";
                     }
                   }
                 }
                 leaf interval {
                   description "Interval";
                   units "seconds";
                   type union {
                     type string {
                       pattern "<.*>|$.*";
                     }
                     type uint32 {
                       range "30 .. 3600";
                     }
                   }
                 }
               }
               container accelerated {
                 presence "enable accelerated";
                 description "Accelerated advertisement parameters";
                 uses apply-advanced;
                 leaf threshold {
                   description "Threshold";
                   units "percentage";
                   type union {
                     type string {
                       pattern "<.*>|$.*";
                     }
                     type uint32 {
                       range "0 .. 100";
                     }
                   }
                 }
               }
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf te-metric {
                 description "Traffic engineering metric for this attribute group";
                 type union {
                   type string {
                     pattern "<.*>|$.*";
                   }
                   type uint32 {
                     range "1 .. 4294967295";
                   }
                 }
               }
               leaf-list admin-group {
                 ordered-by user;
                 description "Administrative groups for this attribute-group";
                 type string;
                 max-elements 16;
               }
               leaf delay-metric {
                 description "Delay metric for this attribute-group";
                 units "microseconds";
                 type union {
                   type string {
                     pattern "<.*>|$.*";
                   }
                   type uint32 {
                     range "0 .. 16777215";
                   }
                 }
               }
               leaf advertise-interface-delay {
                 description "Use interface specific static/dynamic delay values as applicable in ASLA Sub-TLVs";
                 type empty;
               }
               container application {
                 description "Standard Applications part of this attribute-group";
                 uses apply-advanced;
                 leaf flex-algorithm {
                   description "Set X flag in standard application bit mask";
                   type empty;
                 }
               }
             }
           }
         }
         leaf no-context-identifier-advertisement {
           description "Disable context identifier advertisments in this area";
           type empty;
         }
         list peer-interface {
           key name;
           ordered-by user;
           description "Configuration for peer interface";
           leaf name {
             description "Name of peer interface";
             type string;
           }
           uses apply-advanced;
           choice enable-disable {
             case case_1 {
               leaf disable {
                 description "Disable OSPF on this control peer";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                   mandatory true;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
         }
         leaf no-source-packet-routing {
           description "Disable SPRING in this area";
           type empty;
         }
         list context-identifier {
           key name;
           ordered-by user;
           description "Configure context identifier in support of edge protection";
           leaf name {
             description "Context identifier";
             type jt:ipv4addr;
           }
           uses apply-advanced;
         }
         list label-switched-path {
           key name;
           ordered-by user;
           description "Configuration for advertisement of a label-switched path";
           leaf name {
             description "Name of label-switched path to be advertised";
             type string {
               length "1 .. 64";
             }
           }
           uses apply-advanced;
           choice enable-disable {
             case case_1 {
               leaf disable {
                 description "Disable OSPF on this label-switched path";
                 type empty;
               }
             }
           }
           leaf metric {
             description "Interface metric";
             type union {
               type string {
                 pattern "<.*>|$.*";
               }
               type uint16 {
                 range "1 .. 65535";
               }
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                   mandatory true;
                 }
               }
             }
           }
         }
       }
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "traffic-statistics" {
                 description "Trace Segment Routing Traffic Statistics";
               }
               enum "backup-spf" {
                 description "Trace backup SPF (LFA) specific events";
               }
               enum "source-packet-routing" {
                 description "Trace source packet routing (SPRING) events";
               }
               enum "post-convergence-lfa" {
                 description "Trace post-convergence-lfa related events";
               }
               enum "flex-algorithm" {
                 description "Trace flex-algorithm related events";
               }
               enum "rmopd" {
                 description "Trace rmopd interactions";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           type string;
         }
         leaf inet3 {
           description "Name of the IPv4/v6 inet.3 routing table group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 3600";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
           mandatory true;
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         type union {
           type string {
             pattern "<.*>|$.*";
           }
           type uint32 {
             range "50 .. 8000";
           }
         }
       }
       leaf no-rfc-1583 {
         description "Disable RFC1583 compatibility";
         type empty;
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
     }
     container pim {
       description "PIM configuration";
       uses juniper-protocols-pim;
     }
     container rip {
       description "RIP options";
       uses juniper-protocols-rip;
     }
     container rsvp {
       description "RSVP options";
       uses juniper-protocols-rsvp;
     }
     container sap {
       presence "enable sap";
       description "Session Advertisement Protocol options";
       uses apply-advanced;
       choice enable-disable {
         case case_1 {
           leaf disable {
             description "Disable SAP";
             type empty;
           }
         }
       }
       list listen {
         key name;
         ordered-by user;
         description "Address for SAP and SDP to listen on";
         leaf name {
           description "IP address";
           type jt:ipv4addr;
         }
         leaf port {
           description "Port to listen for session advertisements";
           type union {
             type uint16;
             type string {
               pattern "<.*>|$.*";
             }
           }
         }
       }
     }
     container l2-learning {
       description "Layer 2 forwarding configuration";
       uses juniper-protocols-bridge;
     }
     container network-isolation {
       description "Network isolation configuration";
       uses apply-advanced;
       list group {
         key name;
         description "Network isolation group";
         max-elements 64;
         leaf name {
           description "Group name";
           type string {
             length "1 .. 63";
           }
         }
         uses apply-advanced;
         container detection {
           presence "enable detection";
           description "Network isolation detection";
           uses apply-advanced;
           container hold-time {
             description "Hold time for network core isolation ";
             leaf up {
               description "Hold time in milliseconds for declaring network reachable";
               units "milliseconds";
               type union {
                 type string {
                   pattern "<.*>|$.*";
                 }
                 type uint32 {
                   range "0 .. 3600000";
                 }
               }
             }
             leaf down {
               description "Hold time in milliseconds for declaring network not reachable";
               units "milliseconds";
               type union {
                 type string {
                   pattern "<.*>|$.*";
                 }
                 type uint32 {
                   range "0 .. 3600000";
                 }
               }
             }
           }
           container link-tracking {
             presence "enable link-tracking";
             description "Network isolation detection via link tracking";
             uses apply-advanced;
             leaf minimum-links {
               description "Minimum link count in up state to consider network not isolated";
               type union {
                 type string {
                   pattern "<.*>|$.*";
                 }
                 type uint32 {
                   range "1 .. 10";
                 }
               }
             }
             leaf failure-type {
               description "Type of Failure";
               default "link";
               type enumeration {
                 enum "link" {
                   description "Failure type link";
                 }
               }
             }
             choice uplink {
               case case_1 {
                 list interface {
                   key name;
                   description "Name of logical Interface (IFL)  or list of interfaces (IFL) ";
                   leaf name {
                     description "Logical Interface name";
                     type union {
                       type jt:interface-name;
                       type string {
                         pattern "<.*>|$.*";
                       }
                     }
                   }
                   uses apply-advanced;
                 }
               }
               case case_2 {
                 list link-to-monitor {
                   key name;
                   description "Name of physical Interface (IFD)  or list of interfaces (IFD)";
                   leaf name {
                     description "Physical Interface name";
                     type union {
                       type jt:interface-device;
                       type string {
                         pattern "<.*>|$.*";
                       }
                     }
                   }
                   uses apply-advanced;
                 }
               }
             }
           }
           container service-tracking {
             presence "enable service-tracking";
             description "Network isolation service tracking";
             uses apply-advanced;
             leaf core-isolation {
               description "Network isolation via core-isolation";
               type empty;
             }
           }
         }
         container service-tracking-action {
           choice actions {
             case case_1 {
               leaf link-down {
                 description "Bring down associated interfaces";
                 type empty;
               }
             }
             case case_2 {
               leaf lacp-out-of-sync {
                 description "Put ESI LAG in lacp out of sync state";
                 type empty;
               }
             }
           }
         }
       }
     }
     container dcbx {
       presence "enable dcbx";
     }
     container lldp {
       description "Link Layer Detection Protocol";
       uses apply-advanced;
       choice enable-disable {
         case case_1 {
           leaf disable {
             description "Disable LLDP";
             type empty;
           }
         }
       }
       container traceoptions {
         description "Trace options for LLDP";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "all" {
                 description "Trace configuration events";
               }
               enum "configuration" {
                 description "Log configuration events";
               }
               enum "rtsock" {
                 description "Trace rtsock message events";
               }
               enum "packet" {
                 description "Trace packet information";
               }
               enum "protocol" {
                 description "Trace protocol information";
               }
               enum "interface" {
                 description "Trace interface update events";
               }
               enum "vlan" {
                 description "Trace VLAN update events";
               }
               enum "snmp" {
                 description "Trace SNMP events";
               }
               enum "jvision" {
                 description "Trace Jvision events";
               }
             }
           }
           leaf disable {
             description "Disable this trace flag";
             type empty;
           }
         }
       }
       leaf management-address {
         description "LLDP management address";
         type jt:ipaddr;
       }
       leaf advertisement-interval {
         description "Transmit interval for LLDP messages";
         default "30";
         units "seconds";
         type union {
           type string {
             pattern "<.*>|$.*";
           }
           type uint32 {
             range "5 .. 32768";
           }
         }
       }
       leaf transmit-delay {
         description "Transmit delay time interval for LLDP messages";
         units "seconds";
         type union {
           type string {
             pattern "<.*>|$.*";
           }
           type uint32 {
             range "1 .. 8192";
           }
         }
       }
       leaf hold-multiplier {
         description "Hold timer interval for LLDP messages";
         default "4";
         type union {
           type string {
             pattern "<.*>|$.*";
           }
           type uint32 {
             range "2 .. 10";
           }
         }
       }
       leaf ptopo-configuration-trap-interval {
         description "Interval for physical topology configuration change trap";
         default "0";
         units "seconds";
         type union {
           type string {
             pattern "<.*>|$.*";
           }
           type uint32 {
             range "0 .. 3600";
           }
         }
       }
       leaf ptopo-configuration-maximum-hold-time {
         description "Hold time for physical topology connection entries";
         default "300";
         units "seconds";
         type union {
           type string {
             pattern "<.*>|$.*";
           }
           type uint32 {
             range "1 .. 2147483647";
           }
         }
       }
       leaf lldp-configuration-notification-interval {
         description "Time interval for LLDP notification";
         default "5";
         units "seconds";
         type union {
           type string {
             pattern "<.*>|$.*";
           }
           type uint32 {
             range "5 .. 3600";
           }
         }
       }
       leaf port-id-subtype {
         description "Sub-type to be used for Port ID TLV generation";
         default "locally-assigned";
         type enumeration {
           enum "locally-assigned" {
             description "Locally assigned value (SNMP index of the interface)";
           }
           enum "interface-name" {
             description "Interface name on which LLDPDU is sent";
           }
         }
       }
       container chassis-id {
         description "Chassis-id to be used for Chassis ID TLV generation";
         uses apply-advanced;
         leaf chassis-id-type {
           description "Chassis-id-type to be used for Chassis ID TLV generation";
           type enumeration {
             enum "chassis-component" {
               description "User define chassis component name.";
             }
             enum "interface-alias" {
               description "Interface description or name on which LLDPDU is sent";
             }
             enum "port-component" {
               description "User define port component name";
             }
             enum "mac-address" {
               description "MAC Address of Interface on which LLDPDU is sent";
             }
             enum "network-address" {
               description "Netwok Address of Interface on which LLDPDU is sent";
             }
             enum "interface-name" {
               description "Interface name on which LLDPDU is sent";
             }
             enum "locally-assigned" {
               description "Locally assigned value (SNMP index of the interface)";
             }
           }
           mandatory true;
         }
         leaf chassis-id-value {
           description "Chassis-id value as per chassis id type";
           type string {
             length "1 .. 256";
           }
           mandatory true;
         }
       }
       leaf port-description-type {
         description "The Interfaces Group MIB object to be used for Port Description TLV generation";
         default "interface-alias";
         type enumeration {
           enum "interface-alias" {
             description "Use object ifAlias value for TLV generation";
           }
           enum "interface-description" {
             description "Use object ifDescr value for TLV generation";
           }
         }
       }
       leaf neighbour-port-info-display {
         description "Show lldp neighbors to display port-id or port-description ";
         type enumeration {
           enum "port-id" {
             description "Display port-id information of neighbor in port info";
           }
           enum "port-description" {
             description "Display port description of neighbor in port info";
           }
         }
       }
       leaf mau-type {
         description "Populate mau-type in lldp PDU";
         type empty;
       }
       leaf vlan-name-tlv-option {
         description "Vlan tlv options to transmit vlan name or vlan-id";
         default "vlan-id";
         type enumeration {
           enum "vlan-id" {
             description "Use vlan-id for tlv";
           }
           enum "name" {
             description "Use vlan-name for tlv";
           }
         }
       }
       leaf lldp-tx-fast-init {
         description "Transmission count in fast transmission mode";
         type union {
           type string {
             pattern "<.*>|$.*";
           }
           type uint32 {
             range "1 .. 8";
           }
         }
       }
       leaf fast-rx-processing {
         description "Start optimised processing of received pdu";
         type empty;
       }
       leaf-list tlv-select {
         ordered-by user;
         description "Select TLVs to be sent";
         type enumeration {
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 link-aggregation";
           }
           enum "dcbx-ets-configuration" {
             description "OUI IEEE 802.1 dcbx ets configuration";
           }
           enum "dcbx-ets-recommendation" {
             description "OUI IEEE 802.1 dcbx ets recommendation";
           }
           enum "dcbx-priority-flow-control" {
             description "OUI IEEE 802.1 dcbx pfc";
           }
           enum "dcbx-version-101" {
             description "OUI IEEE 802.1 dcbx version 1.01";
           }
           enum "evb" {
             description "OUI IEEE 82.1QBG evb";
           }
           enum "power-via-mdi-measurements" {
             description "OUI IEEE 802.3 power-via-mdi-measurements";
           }
           enum "cloud-reach-event" {
             description "Cloud reachability event";
           }
           enum "phone-home-active" {
             description "Phone-home active configuration";
           }
           enum "cloud-connect-event" {
             description "Cloud-connectivity configuration";
           }
           enum "juniper-poe-capability" {
             description "OUI Juniper PoE Capability";
           }
         }
       }
       leaf-list tlv-filter {
         ordered-by user;
         description "Filter TLVs to be sent";
         type enumeration {
           enum "all" {
             description "Filter all non mandatory TLVs";
           }
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 Link Aggregation";
           }
           enum "dcbx-priority-flow-control" {
             description "OUI IEEE 802.1 dcbx pfc";
           }
           enum "dcbx-ets-configuration" {
             description "OUI IEEE 802.1 dcbx ets configuration";
           }
           enum "dcbx-ets-recommendation" {
             description "OUI IEEE 802.1 dcbx ets recommendation";
           }
           enum "dcbx-version-101" {
             description "OUI IEEE 802.1 dcbx version 1.01";
           }
           enum "evb" {
             description "OUI IEEE 802.1QBG evb";
           }
           enum "power-via-mdi-measurements" {
             description "OUI IEEE 802.3 power-via-mdi-measurements";
           }
           enum "cloud-reach-event" {
             description "Cloud reachability event";
           }
           enum "phone-home-active" {
             description "Phone-home active configuration";
           }
           enum "cloud-connect-event" {
             description "Cloud-connectivity configuration";
           }
           enum "juniper-poe-capability" {
             description "OUI Juniper PoE Capability";
           }
         }
       }
       leaf dest-mac-type {
         description "Destination address to be used";
         type enumeration {
           enum "nearest-bridge" {
             description "To set destination mac as 01:80:C2:00:00:0E";
           }
           enum "nearest-non-tpmr-bridge" {
             description "To set destination mac as 01:80:C2:00:00:03";
           }
           enum "nearest-customer-bridge" {
             description "To set destination mac as 01:80:C2:00:00:00";
           }
         }
       }
       leaf management-interface {
         description "Management interface to be used in LLDP PDUs";
         type union {
           type jt:interface-name;
           type string {
             pattern "<.*>|$.*";
           }
         }
       }
       list interface {
         key name;
         ordered-by user;
         description "Interface configuration";
         leaf name {
           type string;
         }
         uses apply-advanced;
         choice enable-disable {
           case case_1 {
             leaf disable {
               description "Disable LLDP";
               type empty;
             }
           }
         }
         container power-negotiation {
           presence "enable power-negotiation";
           description "LLDP power negotiation";
           uses apply-advanced;
           choice enable-disable {
             case case_1 {
               leaf disable {
                 description "Disable power negotiation";
                 type empty;
               }
             }
           }
         }
         leaf-list tlv-select {
           ordered-by user;
           description "Select TLV(s) to be sent";
           type enumeration {
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 link-aggregation";
             }
             enum "dcbx-ets-configuration" {
               description "OUI IEEE 802.1 dcbx ets configuration";
             }
             enum "dcbx-ets-recommendation" {
               description "OUI IEEE 802.1 dcbx ets recommendation";
             }
             enum "dcbx-priority-flow-control" {
               description "OUI IEEE 802.1 dcbx pfc";
             }
             enum "dcbx-version-101" {
               description "OUI IEEE 802.1 dcbx version 1.01";
             }
             enum "evb" {
               description "OUI IEEE 82.1QBG evb";
             }
             enum "power-via-mdi-measurements" {
               description "OUI IEEE 802.3 power-via-mdi-measurements";
             }
             enum "cloud-reach-event" {
               description "Cloud reachability event";
             }
             enum "phone-home-active" {
               description "Phone-home active configuration";
             }
             enum "cloud-connect-event" {
               description "Cloud-connectivity configuration";
             }
             enum "juniper-poe-capability" {
               description "OUI Juniper PoE Capability";
             }
           }
         }
         leaf-list tlv-filter {
           ordered-by user;
           description "Filter TLV(s) to be sent";
           type enumeration {
             enum "all" {
               description "Filter all non mandatory TLVs";
             }
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 Link Aggregation";
             }
             enum "dcbx-priority-flow-control" {
               description "OUI IEEE 802.1 dcbx pfc";
             }
             enum "dcbx-ets-configuration" {
               description "OUI IEEE 802.1 dcbx ets configuration";
             }
             enum "dcbx-ets-recommendation" {
               description "OUI IEEE 802.1 dcbx ets recommendation";
             }
             enum "dcbx-version-101" {
               description "OUI IEEE 802.1 dcbx version 1.01";
             }
             enum "evb" {
               description "OUI IEEE 802.1QBG evb";
             }
             enum "power-via-mdi-measurements" {
               description "OUI IEEE 802.3 power-via-mdi-measurements";
             }
             enum "cloud-reach-event" {
               description "Cloud reachability event";
             }
             enum "phone-home-active" {
               description "Phone-home active configuration";
             }
             enum "cloud-connect-event" {
               description "Cloud-connectivity configuration";
             }
             enum "juniper-poe-capability" {
               description "OUI Juniper PoE Capability";
             }
           }
         }
         leaf trap-notification {
           description "To enable or disable for lldp-trap notification";
           default "enable";
           type enumeration {
             enum "enable" {
               description "Enable trap notification";
             }
             enum "disable" {
               description "Disable trap notification";
             }
           }
         }
         leaf dest-mac-type {
           description "Destination address to be used";
           type enumeration {
             enum "nearest-bridge" {
               description "To set destination mac as 01:80:C2:00:00:0E";
             }
             enum "nearest-non-tpmr-bridge" {
               description "To set destination mac as 01:80:C2:00:00:03";
             }
             enum "nearest-customer-bridge" {
               description "To set destination mac as 01:80:C2:00:00:00";
             }
           }
         }
         leaf transmit-max-vlan-tlv {
           description "Enable to Transmit max Vlan Name TLVs";
           type empty;
         }
       }
       leaf system-name {
         description "System name to be used in system-name TLV";
         type string {
           length "1 .. 255";
         }
       }
       leaf system-description {
         description "System description to be used in system-description TLV";
         type string {
           length "1 .. 255";
         }
       }
     }
     container lldp-med {
       presence "enable lldp-med";
       description "LLDP Media Endpoint Discovery";
       uses apply-advanced;
       leaf fast-start {
         description "Discovery count for MED";
         type union {
           type string {
             pattern "<.*>|$.*";
           }
           type uint32 {
             range "1 .. 10";
           }
         }
       }
       list interface {
         key name;
         ordered-by user;
         description "Interface configuration";
         leaf name {
           type string;
         }
         uses apply-advanced;
         choice enable-disable {
           case case_1 {
             leaf disable {
               description "Disable LLDP";
               type empty;
             }
           }
         }
         container location {
           presence "enable location";
           uses apply-advanced;
           choice location-type {
             case case_1 {
               container civic-based {
                 description "Postal address";
                 presence "enable civic-based";
                 uses civic-address-elements;
               }
             }
             case case_2 {
               leaf elin {
                 description "Emergency line identification (ELIN) string";
                 type string;
               }
             }
             case case_3 {
             }
           }
         }
         leaf-list tlv-select {
           ordered-by user;
           description "Select TLV(s) to be sent";
           type enumeration {
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
         leaf-list tlv-filter {
           ordered-by user;
           description "Filter TLV(s) to be sent";
           type enumeration {
             enum "all" {
               description "Filter all non mandatory TLVs";
             }
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
       }
       leaf-list tlv-select {
         ordered-by user;
         description "Select MED TLVs to be sent";
         type enumeration {
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
       leaf-list tlv-filter {
         ordered-by user;
         description "Filter MED TLVs to be sent";
         type enumeration {
           enum "all" {
             description "Filter all non mandatory TLVs";
           }
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
     }
     container unified-access-policy {
       description "Unified Access Policy for deployment with MIST AP.";
       uses apply-advanced;
       leaf mac {
         description "Destination multicast mac of key-cache packets sent by Access Point.";
         default "5d:5b:35:ff:ff:01";
         type jt:mac-multicast;
       }
       leaf source-mac {
         description "Source mac of key-cache packets sent by the device.";
         type jt:mac-unicast;
       }
       leaf key {
         description "Hex key which will be converted to ASCII key for ENC/DEC KeyCache Packets.";
         type jt:unreadable;
         mandatory true;
       }
       leaf robust-count {
         description "Max number of retries for key-cache packets.";
         default "3";
         type union {
           type string {
             pattern "<.*>|$.*";
           }
           type int32 {
             range "1 .. 10";
           }
         }
       }
       list interface {
         key name;
         description "Configure ports as AP/ISL links";
         leaf name {
           type string;
         }
         uses apply-advanced;
         choice role {
           case case_1 {
             leaf auto-detect {
               description "Auto detect roles via LLDP";
               type empty;
             }
           }
           case case_2 {
             leaf access-point {
               description "Assign access point port role";
               type empty;
             }
           }
           case case_3 {
             leaf inter-switch-link {
               description "Assign inter-switch-link role";
               type empty;
             }
           }
         }
       }
     }
     container igmp-snooping {
       description "IGMP snooping configuration";
       uses juniper-default-ri-protocols-igmp-snooping;
     }
     container mld-snooping {
       description "MLD snooping configuration";
       uses juniper-default-ri-protocols-mld-snooping;
     }
     container sflow {
       presence "enable sflow";
       description "SFLOW protocol";
       uses apply-advanced;
       container traceoptions {
         description "Trace options for SFLOW";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "configuration" {
                 description "Trace sflow configuration";
               }
               enum "rtsock" {
                 description "Trace rtsock events";
               }
               enum "interface" {
                 description "Trace interface events";
               }
               enum "client-server" {
                 description "Trace sflow client-server events";
               }
               enum "all" {
                 description "Trace all sflow events";
               }
             }
           }
           leaf disable {
             description "Disable this trace flag";
             type empty;
           }
         }
       }
       container agent-id {
         description "Sflow agent id configuration";
         leaf inet {
           description "Sflow agent ipv4 address";
           type jt:ipv4addr;
         }
       }
       leaf polling-interval {
         description "Interval between port statistics";
         default "20";
         units "seconds";
         type union {
           type string {
             pattern "<.*>|$.*";
           }
           type uint32 {
             range "0 .. 3600";
           }
         }
       }
       container adaptive-sample-rate {
         description "Trigger adaptive sampling";
         leaf fallback {
           description "Enable fallback to previous adapted sample rates";
           type empty;
         }
         leaf sample-limit-threshold {
           description "Per FPC Sample limits in pps ";
           type union {
             type string {
               pattern "<.*>|$.*";
             }
             type uint32;
           }
         }
       }
       leaf inline-sampling {
         description "Enable inline sampling of packets";
         type empty;
       }
       container sample-rate {
         description "Sampling rate";
         uses apply-advanced;
       }
       container source-ip {
         description "Sflow source ip configuration";
         leaf inet {
           description "Sflow datagram source ipv4 address";
           type jt:ipv4addr;
         }
       }
       container scale-mode {
         presence "enable scale-mode";
         description "Recommended on more than 4 member VC with scale";
         uses apply-advanced;
         choice enable-disable {
           case case_1 {
             leaf disable {
               description "Disable scale mode";
               type empty;
             }
           }
         }
         leaf adaptive-interval {
           description "Interval for adaptive sampling";
           type string;
         }
       }
       list collector {
         key name;
         ordered-by user;
         description "SFLOW collector configuration";
         max-elements 4;
         leaf name {
           description "Collector IP v4/v6 address";
           type jt:ipaddr;
         }
         uses apply-advanced;
         leaf udp-port {
           description "Collector UDP port";
           default "6343";
           type union {
             type uint16;
             type string {
               pattern "<.*>|$.*";
             }
           }
         }
       }
       list interfaces {
         key name;
         description "Enable SFLOW on this interface";
         leaf name {
           description "Interface name";
           type union {
             type jt:interface-name;
             type string {
               pattern "<.*>|$.*";
             }
           }
         }
         uses apply-advanced;
         leaf polling-interval {
           description "Interval between port statistics";
           units "seconds";
           type union {
             type string {
               pattern "<.*>|$.*";
             }
             type uint32 {
               range "0 .. 3600";
             }
           }
         }
         container sample-rate {
           description "Sampling rate";
           uses apply-advanced;
         }
       }
       leaf disable-sw-rate-limiter {
         description "Disable sw rate limiter";
         type empty;
       }
     }
     container layer2-control {
       description "Global options for layer 2 protocols";
       uses juniper-protocols-l2control;
     }
     container rstp {
       description "Rapid Spanning Tree Protocol options";
       uses juniper-protocols-stp;
     }
     container mstp {
       description "Multiple Spanning Tree Protocol options";
       uses juniper-protocols-mstp;
     }
     container vstp {
       description "VLAN Spanning Tree Protocol options";
       uses juniper-protocols-vstp;
     }
     container loop-detect {
       presence "enable loop-detect";
       description "Layer2 Loop Detect on interface with non-IP L2 Multicast mac as destination mac";
       uses apply-advanced;
       list interface {
         key name;
         ordered-by user;
         description "Interface name to block Loop Detect PDUs on";
         leaf name {
           type string;
         }
         uses apply-advanced;
         leaf disable {
           description "Disable loop detect feature on a port";
           type empty;
         }
       }
       container enhanced {
         description "Enhanced loop detect configuration";
         uses apply-advanced;
         list interface {
           key name;
           ordered-by user;
           description "Name of interface";
           leaf name {
             type string;
           }
           uses apply-advanced;
           leaf vlan-id {
             description "VLAN identifier for trunk interface or all";
             type string;
           }
           leaf loop-detect-action {
             description "Action that needs to be taken";
             default "interface-down";
             type enumeration {
               enum "interface-down" {
                 description "Interface down action";
               }
               enum "laser-off" {
                 description "Laser off action";
               }
             }
           }
           leaf transmit-interval {
             description "Interval between loop-detect messages";
             default "1s";
             type enumeration {
               enum "1s" {
               }
               enum "10s" {
               }
               enum "1m" {
               }
               enum "10m" {
               }
             }
           }
           leaf revert-interval {
             description "Interval after which action will be reverted";
             default "0";
             units "seconds";
             type union {
               type string {
                 pattern "<.*>|$.*";
               }
               type uint32 {
                 range "0 .. 300";
               }
             }
           }
         }
       }
       leaf destination-mac {
         description "Destination non-IP L2 multicast mac to be used for transmitting Loop Detect PDUs";
         type jt:mac-multicast;
       }
       leaf transmit-interval {
         description "Loop Detect PDU TX interval in sec --default 30s";
         units "seconds";
         type union {
           type string {
             pattern "<.*>|$.*";
           }
           type uint16 {
             range "5 .. 3600";
           }
         }
       }
     }
     container protection-group {
       description "Protection group";
       presence "enable protection-group";
       uses juniper-protocols-protection-group;
     }
     container mvrp {
       description "MVRP configuration";
       uses juniper-protocols-mvrp;
     }
     container uplink-failure-detection {
       description "Uplink failure detection configuration";
       uses apply-advanced;
       container group {
         description "Uplink failure detection group";
         uses apply-advanced;
         list ufd-group-name {
           key name;
           description "Uplink failure detection group name";
           uses ufd-group-type;
         }
       }
       container traceoptions {
         description "Trace options for uplink failure detection";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "interface" {
                 description "Trace interface notifcation handlers of ufd";
               }
               enum "dcd" {
                 description "Trace ufdd interaction with dcd";
               }
               enum "groups" {
                 description "Trace uplink failure detection group handling";
               }
               enum "all" {
                 description "Trace everything";
               }
             }
           }
         }
       }
       container action {
         description "Define action on ufd group state change";
         uses apply-advanced;
         leaf log {
           description "Log a message";
           type empty;
         }
       }
     }
   }
   grouping bandwidth-type {
     uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping civic-address-elements {
     uses apply-advanced;
     leaf what {
       description "Type of address";
       default "1";
       type union {
         type string {
           pattern "<.*>|$.*";
         }
         type uint16 {
           range "0 .. 2";
         }
       }
     }
     leaf country-code {
       description "Two-letter country code";
       type string {
         length 2;
       }
       mandatory true;
     }
     list ca-type {
       key name;
       ordered-by user;
       leaf name {
         description "Address element type";
         type union {
           type string {
             pattern "<.*>|$.*";
           }
           type uint16 {
             range "0 .. 255";
           }
         }
       }
       uses apply-advanced;
       leaf ca-value {
         description "Address element value";
         type string {
           length "1 .. 248";
         }
       }
     }
   }
   grouping juniper-default-ri-protocols-igmp-snooping {
     description "IGMP snooping options";
     uses apply-advanced;
     list vlan {
       key name;
       ordered-by user;
       description "VLAN options";
       leaf name {
         description "VLAN name";
         type string;
       }
       uses apply-advanced;
       container traceoptions {
         description "Trace options for IGMP Snooping";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "group" {
                 description "Trace group operations";
               }
               enum "client-notification" {
                 description "Trace notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IP address to use for L2 querier";
           type jt:ipv4addr;
           mandatory true;
         }
       }
       leaf query-response-interval {
         description "How long to wait for a host query response";
         default "10";
         units "seconds";
         type string {
         }
       }
       leaf query-last-member-interval {
         description "When to send group query messages";
         default "1";
         units "seconds";
         type string {
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       leaf evpn-ssm-reports-only {
         description "Accept and process only <s,g> reports of SSM groups";
         type empty;
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interface";
           type empty;
         }
         leaf host-only-interface {
           description "Enable interface to be treated as host-side interface";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           description "Enable L2 querier mode";
           uses apply-advanced;
           leaf source-address {
             description "Source IP address to use for L2 querier";
             type jt:ipv4addr;
             mandatory true;
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         leaf evpn-ssm-reports-only {
           description "Accept and process only <s,g> reports of SSM groups";
           type empty;
         }
         list interface {
           key name;
           ordered-by user;
           description "Interface options for IGMP";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interface";
             type empty;
           }
           leaf host-only-interface {
             description "Enable interface to be treated as host-side interface";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
       }
       leaf version {
         description "Set IGMP version number on interface_help_string";
         type union {
           type string {
             pattern "<.*>|$.*";
           }
           type uint8 {
             range "2 .. 3";
           }
         }
       }
       leaf no-flood-to-multicast-router-interfaces {
         description "Don't flood multicast traffic to router interfaces";
         type empty;
       }
       leaf flood-reports-to-inter-switch-interface {
         description "Flood reports to inter switch link";
         type empty;
       }
       leaf immediate-leave-on-host-interface {
         description "Immediate leave on host interfaces";
         type empty;
       }
       leaf evpn-query-relay-stop {
         description "Stop relaying query on EVPN VLAN or BD";
         type empty;
       }
     }
     leaf version {
       description "Set IGMP snooping version number";
       type union {
         type string {
           pattern "<.*>|$.*";
         }
         type uint8 {
           range "2 .. 3";
         }
       }
     }
   }
   grouping juniper-default-ri-protocols-mld-snooping {
     description "MLD snooping options";
     uses apply-advanced;
     list vlan {
       key name;
       ordered-by user;
       description "VLAN options";
       leaf name {
         description "VLAN name";
         type string;
       }
       uses apply-advanced;
       container traceoptions {
         description "Trace options for MLD Snooping";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv1 only)";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IPv6 link local address to use for L2 querier";
           type jt:ipv6addr;
           mandatory true;
         }
       }
       leaf query-response-interval {
         description "How long to wait for a host query response";
         default "10";
         units "seconds";
         type string {
         }
       }
       leaf query-last-member-interval {
         description "When to send group query messages";
         default "1";
         units "seconds";
         type string {
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       container proxy {
         description "Enable proxy mode";
         uses apply-advanced;
         leaf source-address {
           description "Source IPv6 link local address to use for proxy";
           type jt:ipv6addr;
           mandatory true;
         }
       }
       leaf evpn-ssm-reports-only {
         description "Accept and process only <s,g> reports of SSM groups";
         type empty;
       }
       leaf version {
         description "Set MLD snooping version number";
         type union {
           type string {
             pattern "<.*>|$.*";
           }
           type uint8 {
             range "1 .. 2";
           }
         }
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           uses apply-advanced;
           leaf source-address {
             description "Source IPv6 link local address to use for L2 querier";
             type jt:ipv6addr;
             mandatory true;
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           description "Enable proxy mode";
           uses apply-advanced;
           leaf source-address {
             description "Source IPv6 link local address to use for proxy";
             type jt:ipv6addr;
             mandatory true;
           }
         }
         leaf evpn-ssm-reports-only {
           description "Accept and process only <s,g> reports of SSM groups";
           type empty;
         }
         list interface {
           key name;
           ordered-by user;
           description "Interface options for MLD";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
       }
       leaf no-flood-to-multicast-router-interfaces {
         description "Don't flood multicast traffic to router interfaces";
         type empty;
       }
       leaf flood-reports-to-inter-switch-interface {
         description "Flood reports to inter switch link";
         type empty;
       }
       leaf immediate-leave-on-host-interface {
         description "Immediate leave on host interfaces";
         type empty;
       }
     }
     container traceoptions {
       description "Trace options for MLD Snooping";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     leaf version {
       description "Set MLD snooping version number";
       type union {
         type string {
           pattern "<.*>|$.*";
         }
         type uint8 {
           range "1 .. 2";
         }
       }
     }
     container proxy {
       description "Enable proxy mode";
       uses apply-advanced;
       leaf source-address {
         description "Source IPv6 link local address to use for proxy";
         type jt:ipv6addr;
         mandatory true;
       }
       leaf irb {
         description "Proxy IGMP reports to IRB";
         type empty;
       }
     }
     list interface {
       key name;
       ordered-by user;
       description "Interface options for MLD";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
   }
   grouping juniper-ospf-authentication {
     description "Authentication information";
     uses apply-advanced;
     choice authentication-type {
       case case_1 {
         leaf simple-password {
           description "Authentication key";
           type jt:unreadable;
         }
       }
       case case_2 {
         list md5 {
           key name;
           ordered-by user;
           description "MD5 authentication key";
           leaf name {
             description "Key ID for MD5 authentication";
             type union {
               type string {
                 pattern "<.*>|$.*";
               }
               type uint32 {
                 range "0 .. 255";
               }
             }
           }
           leaf key {
             description "MD5 authentication key value";
             type jt:unreadable;
             mandatory true;
           }
           leaf start-time {
             description "Start time for key transmission (YYYY-MM-DD.HH:MM)";
             type jt:time;
           }
         }
       }
       case case_3 {
         list multi-active-md5 {
           key name;
           ordered-by user;
           description "Authentication Multiple active MD5 keys";
           leaf name {
             description "Key ID for MD5 authentication";
             type union {
               type string {
                 pattern "<.*>|$.*";
               }
               type uint32 {
                 range "0 .. 255";
               }
             }
           }
           leaf key {
             description "MD5 authentication key value";
             type jt:unreadable;
             mandatory true;
           }
           leaf delete-if-not-inuse {
             description "Delete this key if not in use";
             type empty;
           }
         }
       }
       case case_4 {
         leaf keychain {
           description "Key chain name";
           type string {
             length "1 .. 128";
           }
         }
       }
     }
   }
   grouping juniper-protocols-bgpmcast {
     description "BGP Multicast configuration";
     uses apply-advanced;
     container traceoptions {
       description "Trace options for BGP Multicast";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
   }
   grouping juniper-protocols-bridge {
     uses apply-advanced;
     container traceoptions {
       description "Trace options for Layer 2 address service";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "bridging-domain" {
               description "Bridging domain operations";
             }
             enum "routing-instance" {
               description "Routing instance operations";
             }
             enum "bridge-interface" {
               description "Interface bridge operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "irb" {
               description "Integrated routing and bridging operations";
             }
             enum "vpls-ping" {
               description "VPLS ping operations";
             }
             enum "vpls-loop-prev" {
               description "VPLS loop prevention";
             }
             enum "logical-system" {
               description "Logical system operations";
             }
             enum "bmac-next-hop" {
               description "Backbone Mac Next hop operations ";
             }
             enum "bridge-bmac-next-hop" {
               description "Bmac Next hop bridge operations";
             }
             enum "isid" {
               description "I-Tagged Service ID";
             }
             enum "mc-ae" {
               description "Multi-chassis AE";
             }
             enum "kack" {
               description "Kernel-acknowledgment";
             }
             enum "storm-control" {
               description "Storm-control";
             }
             enum "redundant-trunk-group" {
               description "Redundant trunk group";
             }
             enum "unknown-unicast-forwarding" {
               description "Trace unknown unicast forwarding events";
             }
             enum "vxlan" {
               description "VXLAN";
             }
             enum "l2-license" {
               description "L2 license trace";
             }
             enum "telemetry" {
               description "Telemetry";
             }
             enum "network-isolation" {
               description "Network isolation detection";
             }
             enum "all" {
               description "All operations";
             }
           }
         }
       }
       container kernel {
         presence "enable kernel";
         description "Trace options for kernel";
         uses apply-advanced;
         container irb {
           presence "enable irb";
           description "Trace options for irb";
         }
       }
       container in-memory-debug {
         presence "enable in-memory-debug";
         description "Enable trace parameters in the memory";
       }
     }
     container global-mac-move {
       presence "enable global-mac-move";
       description "Enable mac move related options at global level";
       uses apply-advanced;
       leaf notification-time {
         description "Periodical time interval in secs during which MAC move notification occurs";
         units "seconds";
         type union {
           type uint32;
           type string {
             pattern "<.*>|$.*";
           }
         }
       }
       leaf threshold-time {
         description "Time during which if certain number of MAC moves happen warrant recording";
         units "seconds";
         type union {
           type uint32;
           type string {
             pattern "<.*>|$.*";
           }
         }
       }
       leaf reopen-time {
         description "Time after which a blocked interface is reopened";
         units "seconds";
         type union {
           type uint32;
           type string {
             pattern "<.*>|$.*";
           }
         }
       }
       leaf threshold-count {
         description "Count of MAC moves which warrant recording when happen in certain time";
         units "seconds";
         type union {
           type uint32;
           type string {
             pattern "<.*>|$.*";
           }
         }
       }
       container traceoptions {
         description "Enable logging for the MAC moves";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
       }
       leaf log {
         description "Syslog all the MAC moves as stored in the mac-move-buffer";
         type empty;
       }
       leaf disable-action {
         description "Disable mac move action globally";
         type empty;
       }
       list exclusive-mac {
         key name;
         ordered-by user;
         description "MAC addresses to be excluded in mac-move-limit or in VPLS loop prevention algorithm";
         leaf name {
           description "Source MAC address";
           type jt:mac-addr-prefix;
         }
         uses apply-advanced;
       }
     }
     leaf global-mac-table-aging-time {
       description "System level MAC table aging time";
       units "seconds";
       type union {
         type string {
           pattern "<.*>|$.*";
         }
         type uint32;
       }
     }
     leaf global-mac-ip-table-aging-time {
       description "System level MAC+IP table aging time";
       units "seconds";
       type union {
         type string {
           pattern "<.*>|$.*";
         }
         type uint32 {
           range "60 .. 1000000";
         }
       }
     }
     leaf mclag-arpreq-sync {
       description "Enable syncing ARP REQ packets to peer MCLAG PE";
       type empty;
     }
     choice ctx-limit-options {
       case case_1 {
         container global-ctx-limit {
           presence "enable global-ctx-limit";
           description "Context history limit";
           uses apply-advanced;
           leaf ctx-limit {
             description "Context history count limit";
             type union {
               type string {
                 pattern "<.*>|$.*";
               }
               type uint32 {
                 range "0 .. 5000000";
               }
             }
           }
         }
       }
       case case_2 {
         container global-ctx-mem-limit {
           presence "enable global-ctx-mem-limit";
           description "Context history memory limit (in bytes)";
           uses apply-advanced;
           leaf ctx-mem-limit {
             description "Context history memory limit in bytes";
             type union {
               type uint32;
               type string {
                 pattern "<.*>|$.*";
               }
             }
           }
         }
       }
     }
     container ctxt-history {
       description "Ctxt-history configuration";
       uses apply-advanced;
       container file {
         description "Ctxt-history files";
         uses apply-advanced;
         leaf files {
           description "Maximum number of ctxt-history files";
           default "0";
           type union {
             type string {
               pattern "<.*>|$.*";
             }
             type uint32 {
               range "0 .. 100";
             }
           }
         }
         leaf size {
           description "Maximum ctxt-hist file size";
           type string;
         }
       }
     }
     container global-mac-limit {
       presence "enable global-mac-limit";
       description "System level MAC limit options";
       uses apply-advanced;
       leaf mac-limit {
         description "System level MAC limit";
         type union {
           type string {
             pattern "<.*>|$.*";
           }
           type uint64;
         }
       }
       leaf packet-action {
         type enumeration {
           enum "drop" {
             description "Enable packet-action drop when MAC limit is reached";
           }
         }
       }
       leaf low-watermark {
         description "Global MAC limit low watermark in percentage ";
         units "percent";
         type union {
           type string {
             pattern "<.*>|$.*";
           }
           type uint32 {
             range "1 .. 100";
           }
         }
       }
       leaf high-watermark {
         description "Global MAC limit high watermark in percentage ";
         units "percent";
         type union {
           type string {
             pattern "<.*>|$.*";
           }
           type uint32 {
             range "1 .. 100";
           }
         }
       }
     }
     container global-mac-ip-limit {
       presence "enable global-mac-ip-limit";
       description "System level MAC+IP limit options";
       uses apply-advanced;
       leaf mac-ip-limit {
         description "System level MAC+IP limit";
         type union {
           type string {
             pattern "<.*>|$.*";
           }
           type uint64;
         }
       }
     }
     leaf global-mac-statistics {
       description "Enable MAC address statistics at system level";
       type empty;
     }
     leaf global-mac-ip-snooping {
       description "Enable global mac-ip snooping feature";
       type empty;
     }
     container niso-maintenance {
       description "Network isolation maintenance knob";
       uses apply-advanced;
       container down {
         description "Network isolation maintenance down knob";
         uses apply-advanced;
         leaf niso-group-name {
           description "Network isolation maintenance knob";
           type string;
         }
       }
     }
     container telemetry {
       presence "enable telemetry";
       description "Streaming Telemetry Data";
       uses apply-advanced;
       leaf enable-remote-entries {
         description "Enable Remote mac and mac-ip entries";
         type empty;
       }
     }
     leaf global-no-mac-learning {
       description "Disable dynamic MAC address learning at system level";
       type empty;
     }
     leaf global-no-hw-mac-learning {
       description "Disable hardware MAC-address learning at system level";
       type empty;
     }
     leaf global-no-control-mac-aging {
       description "Disable control MAC-address aging from software";
       type empty;
     }
     leaf mclag-arp-nd-sync {
       description "Arp and ND entry sync from peer device.";
       type empty;
     }
     container platform-parameters {
       presence "enable platform-parameters";
       description "Platform Parameters Setting";
       uses apply-advanced;
       container no-mac-flush-on-aa-ae-down {
         presence "enable no-mac-flush-on-aa-ae-down";
         description "Do not flush MAC & MAC-IP entries when active-active AE interface goes down";
         uses apply-advanced;
         choice enable-disable {
           case case_1 {
             leaf disable {
               description "Disable no-mac-flush-on-aa-ae-down";
               type empty;
             }
           }
         }
       }
     }
     container crb-proxy-mac {
       description "Configure proxy MAC address to be used in MAC-IP refresh";
       uses apply-advanced;
       container family {
         description "Address family";
         uses apply-advanced;
         container inet {
           description "Inet version 4 family";
           uses apply-advanced;
           leaf mac-address {
             description "Proxy MAC address";
             type jt:mac-unicast;
           }
         }
         container inet6 {
           description "Inet version 6 family";
           uses apply-advanced;
           leaf mac-address {
             description "Proxy MAC address";
             type jt:mac-unicast;
           }
         }
       }
     }
     leaf arp-nd-probe-disable {
       description "Disable probing for ip address";
       type empty;
     }
     leaf arp-nd-probe-failed-log {
       description "Enable syslog when probing for ip address fails";
       type empty;
     }
     leaf garp-na-enable {
       description "Send GARP or unsolicited NA to all connected access devices";
       type empty;
     }
     container mac-learning-log {
       description "Mac learning log options";
       uses apply-advanced;
       leaf system-timezone {
         description "Use system time zone for mac learn log";
         type empty;
       }
     }
   }
   grouping juniper-protocols-evpn-interconnect {
     description "Interconnect configuration for the routing instance";
     uses apply-advanced;
     leaf-list vrf-import {
       ordered-by user;
       description "Import policy for Interconnect";
       type jt:policy-algebra;
     }
     leaf-list vrf-export {
       ordered-by user;
       description "Export policy for Interconnect";
       type jt:policy-algebra;
     }
     container vrf-target {
       description "Interconnect target community configuration";
       uses apply-advanced;
       leaf community {
         description "Target community to use in import and export";
         type string {
         }
       }
       leaf import {
         description "Target community to use when filtering on import";
         type string {
         }
       }
       leaf export {
         description "Target community to use when marking routes on export";
         type string {
         }
       }
     }
     container route-distinguisher {
       description "Route distinguisher for this interconnect";
       leaf rd-type {
         description "Number in (16 bit:32 bit) or (32 bit 'L':16 bit) or (IP address:16 bit) format";
         type string {
         }
       }
     }
     list domain-path-id {
       key name;
       ordered-by user;
       description "DCI VRF domain path id configuration";
       max-elements 1;
       uses domain-id-type;
     }
     container esi {
       description "ESI configuration of interconnect";
       uses apply-advanced;
       leaf identifier {
         description "ESI value for interconnect";
         type jt:esi;
         mandatory true;
       }
       choice mode {
         case case_1 {
           leaf all-active {
             description "All-active mode";
             type empty;
           }
         }
       }
       container df-election-type {
         presence "enable df-election-type";
         description "DF Election Type";
         uses apply-advanced;
         choice pref_choice {
           case case_1 {
             container preference {
               presence "enable preference";
               description "Preference based DF election";
               uses apply-advanced;
               leaf value {
                 description "Preference value for EVPN Multihoming DF election";
                 default "32767";
                 type union {
                   type string {
                     pattern "<.*>|$.*";
                   }
                   type uint32 {
                     range "0 .. 65535";
                   }
                 }
               }
               leaf non-revertive {
                 description "Don't allow Designated Forwarder preemption";
                 type empty;
               }
             }
           }
         }
         choice mod_choice {
           case case_1 {
             container mod {
               presence "enable mod";
               description "MOD based DF election";
             }
           }
         }
       }
     }
     leaf suppress-host-routes-from-dci-to-dc {
       description "Suppress DCI Type-5 host routes into DC for non-stretched subnets";
       type empty;
     }
     leaf-list interconnected-vni-list {
       description "List of translated VNIs (1..16777214) or all, that are to be EVPN interconnected";
       type string;
     }
     leaf-list interconnected-vlan-list {
       ordered-by user;
       description "List of VLAN identifiers that are to be EVPN interconnected";
       type string;
     }
     container irb-symmetric-routing {
       description "Enable EVPN T-2 symmetric DCI routing";
       uses apply-advanced;
       leaf vni {
         description "VXLAN network identifier used for T-2 symmetric routing IP prefixes";
         type union {
           type string {
             pattern "<.*>|$.*";
           }
           type uint32 {
             range "1 .. 16777214";
           }
         }
       }
     }
     leaf encapsulation {
       type enumeration {
         enum "mpls" {
           description "MPLS encapsulation";
         }
         enum "vxlan" {
           description "VXLAN encapsulation";
         }
       }
     }
   }
   grouping domain-id-type {
     leaf name {
       description "Domain id for type 5 evpn DCI";
       type string {
       }
     }
     uses apply-advanced;
   }
   grouping juniper-protocols-isis {
     uses apply-advanced;
     list interface {
       key name;
       description "Interface configuration";
       leaf name {
         description "Interface name";
         type union {
           type jt:interface-name;
           type string {
             pattern "<.*>|$.*";
           }
         }
       }
       uses apply-advanced;
       container ldp-synchronization {
         description "Advertise maximum metric until LDP is operational";
         presence "enable ldp-synchronization";
         uses ldp-sync-obj;
       }
       list level {
         key name;
         ordered-by user;
         description "Configure levels on this interface";
         leaf name {
           description "IS-IS level number";
           type union {
             type string {
               pattern "<.*>|$.*";
             }
             type uint32 {
               range "1 .. 2";
             }
           }
         }
         uses apply-advanced;
         leaf te-metric {
           description "Traffic engineering metric";
           type union {
             type string {
               pattern "<.*>|$.*";
             }
             type uint32 {
               range "0 .. 16777215";
             }
           }
         }
         leaf no-advertise-adjacency-segment {
           description "Do not advertise an adjacency segment for this level";
           type empty;
         }
         container ipv4-adjacency-segment {
           description "Configure ipv4 adjacency segment";
           uses apply-advanced;
           container protected {
             description "Adjacency SID is eligible for protection";
             uses apply-advanced;
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             uses apply-advanced;
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
               mandatory true;
             }
           }
         }
         container srv6-adjacency-segment {
           description "Configure srv6 adjacency segment";
           uses apply-advanced;
           container unprotected {
             presence "enable unprotected";
             description "SRv6 Adjacency segment is uneligible for protection";
             uses apply-advanced;
             list locator {
               key name;
               ordered-by user;
               description "Locator to bind SRv6 adjacency segment";
               leaf name {
                 description "Locator name";
                 type string;
                 mandatory true;
               }
               uses apply-advanced;
               list end-x-sid {
                 key name;
                 ordered-by user;
                 description "Endpoint 128 bit address";
                 leaf name {
                   type jt:ipv6addr;
                 }
                 uses apply-advanced;
                 container flavor {
                   presence "enable flavor";
                   description "Configure end-x-SID flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
               container micro-adjacency-sid {
                 presence "enable micro-adjacency-sid";
                 description "Micro-adjacency-SID";
                 uses apply-advanced;
                 leaf static-sid {
                   description "Static micro-adjacency-SID";
                   type union {
                     type uint32;
                     type string {
                       pattern "<.*>|$.*";
                     }
                   }
                 }
               }
               container dynamic-end-x-sid {
                 presence "enable dynamic-end-x-sid";
                 description "Allocate end-x-SID dynamically";
                 uses apply-advanced;
                 container flavor {
                   presence "enable flavor";
                   description "Configure end-x-SID flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
         }
         list lan-neighbor {
           key name;
           ordered-by user;
           description "Configuration specific to a LAN neighbor";
           leaf name {
             description "Neighbor's sysid";
             type jt:sysid;
           }
           uses apply-advanced;
           container ipv4-adjacency-segment {
             description "Configure ipv4 adjacency segment";
             uses apply-advanced;
             container protected {
               description "Adjacency SID is eligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 1048575";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
                 mandatory true;
               }
             }
           }
           container srv6-adjacency-segment {
             description "Configure srv6 adjacency segment";
             uses apply-advanced;
             container unprotected {
               presence "enable unprotected";
               description "SRv6 Adjacency segment is uneligible for protection";
               uses apply-advanced;
               list locator {
                 key name;
                 ordered-by user;
                 description "Locator to bind SRv6 adjacency segment";
                 leaf name {
                   description "Locator name";
                   type string;
                   mandatory true;
                 }
                 uses apply-advanced;
                 list end-x-sid {
                   key name;
                   ordered-by user;
                   description "Endpoint 128 bit address";
                   leaf name {
                     type jt:ipv6addr;
                   }
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
                 container micro-adjacency-sid {
                   presence "enable micro-adjacency-sid";
                   description "Micro-adjacency-SID";
                   uses apply-advanced;
                   leaf static-sid {
                     description "Static micro-adjacency-SID";
                     type union {
                       type uint32;
                       type string {
                         pattern "<.*>|$.*";
                       }
                     }
                   }
                 }
                 container dynamic-end-x-sid {
                   presence "enable dynamic-end-x-sid";
                   description "Allocate end-x-SID dynamically";
                   uses apply-advanced;
                   container flavor {
                     presence "enable flavor";
                     description "Configure end-x-SID flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
         }
         container post-convergence-lfa {
           presence "enable post-convergence-lfa";
           description "Configure backup along post convergence on this interface";
           uses apply-advanced;
           container node-protection {
             presence "enable node-protection";
             description "Enable node protection";
             uses apply-advanced;
             leaf cost {
               description "Cost for node protection";
               type union {
                 type string {
                   pattern "<.*>|$.*";
                 }
                 type uint32 {
                   range "0 .. 16777215";
                 }
               }
             }
           }
           leaf srlg-protection {
             description "Enable srlg protection";
             type empty;
           }
           leaf fate-sharing-protection {
             description "Enable fate-sharing protection";
             type empty;
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf advertise-delay-metric {
               description "Advertise delay metric as per interface config";
               type empty;
             }
             leaf te-metric {
               description "Traffic engineering metric for this attribute group";
               type union {
                 type string {
                   pattern "<.*>|$.*";
                 }
                 type uint32 {
                   range "0 .. 16777215";
                 }
               }
             }
             leaf-list admin-group {
               ordered-by user;
               description "Administrative groups for this attribute-group";
               type string;
               max-elements 16;
             }
             leaf-list srlg {
               ordered-by user;
               description "SRLG Name";
               type string;
               max-elements 16;
             }
             container application {
               description "Standard Applications part of this attribute-group";
               uses apply-advanced;
               leaf flex-algorithm {
                 description "Set X flag in standard application bit mask";
                 type empty;
               }
             }
           }
         }
         choice enable-disable {
           case case_1 {
             leaf disable {
               description "Disable IS-IS for this level";
               type empty;
             }
           }
         }
         leaf metric {
           description "Metric for this level";
           type union {
             type string {
               pattern "<.*>|$.*";
             }
             type uint32 {
               range "0 .. 16777215";
             }
           }
         }
         leaf ipv4-multicast-metric {
           description "IPv4 multicast metric for this level";
           type union {
             type string {
               pattern "<.*>|$.*";
             }
             type uint32 {
               range "0 .. 16777215";
             }
           }
         }
         leaf ipv6-unicast-metric {
           description "IPv6 unicast metric for this level";
           type union {
             type string {
               pattern "<.*>|$.*";
             }
             type uint32 {
               range "0 .. 16777215";
             }
           }
         }
         leaf ipv6-multicast-metric {
           description "IPv6 multicast metric for this level";
           type union {
             type string {
               pattern "<.*>|$.*";
             }
             type uint32 {
               range "0 .. 16777215";
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
                 mandatory true;
               }
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf hello-authentication-key {
           description "Authentication key (password) for hello packets";
           type jt:unreadable;
         }
         leaf hello-authentication-type {
           description "Authentication type for hello packets";
           type enumeration {
             enum "md5" {
               description "MD5 authentication";
             }
             enum "simple" {
               description "Simple password authentication";
             }
           }
         }
         leaf hello-authentication-key-chain {
           description "Key chain name";
           type string {
             length "1 .. 128";
           }
         }
         leaf hello-interval {
           description "Interval between hello packet transmissions";
           units "seconds";
           type union {
             type string {
               pattern "<.*>|$.*";
             }
             type uint32 {
               range "1 .. 21845";
             }
           }
         }
         leaf hold-time {
           description "Time after which neighbors think the interface is down";
           units "seconds";
           type union {
             type string {
               pattern "<.*>|$.*";
             }
             type uint32 {
               range "1 .. 65535";
             }
           }
         }
         leaf priority {
           description "Designated router election priority";
           type union {
             type string {
               pattern "<.*>|$.*";
             }
             type uint32 {
               range "0 .. 127";
             }
           }
         }
         container flood-reflector {
           presence "enable flood-reflector";
           description "Configure interface as flood-reflector";
           uses apply-advanced;
           leaf cluster-id {
             description "Cluster-ID";
             type union {
               type string {
                 pattern "<.*>|$.*";
               }
               type uint32 {
                 range "1 .. 4294967295";
               }
             }
           }
         }
         container passive {
           presence "enable passive";
           description "Do not run IS-IS at this level, but advertise it";
           uses apply-advanced;
           leaf remote-node-iso {
             description "ISO System-ID of the remote node";
             type jt:sysid;
           }
           leaf remote-node-id {
             description "Remote address of the link";
             type jt:ipv4addr;
           }
         }
         leaf strict-bfd-old {
           description "Enable strict bfd over this interface";
           type empty;
         }
       }
       leaf delay-metric {
         description "Delay metric";
         units "microseconds";
         type union {
           type string {
             pattern "<.*>|$.*";
           }
           type uint32 {
             range "0 .. 16777215";
           }
         }
       }
       container delay-measurement {
         presence "enable delay-measurement";
         description "Enable delay measurement";
         uses apply-advanced;
         leaf probe-interval {
           description "Probe interval";
           units "seconds";
           type union {
             type string {
               pattern "<.*>|$.*";
             }
             type uint32 {
               range "1 .. 255";
             }
           }
         }
         leaf probe-count {
           description "Probe count";
           type union {
             type string {
               pattern "<.*>|$.*";
             }
             type uint32 {
               range "1 .. 15";
             }
           }
         }
         container normalize {
           description "Normalize Measured Link Delay";
           leaf interval {
             description "The value of the normalized interval in microseconds.";
             units "microseconds";
             type union {
               type string {
                 pattern "<.*>|$.*";
               }
               type uint32 {
                 range "1 .. 5000000";
               }
             }
             mandatory true;
           }
           leaf offset {
             description "The value of the normalized offset in microseconds (Must be < normalized interval).";
             units "microseconds";
             type union {
               type string {
                 pattern "<.*>|$.*";
               }
               type uint32 {
                 range "1 .. 5000000";
               }
             }
             mandatory true;
           }
         }
         container advertisement {
           description "Delay advertisement";
           uses apply-advanced;
           container periodic {
             description "Periodic advertisement parameters";
             uses apply-advanced;
             leaf threshold {
               description "Threshold";
               units "percentage";
               type union {
                 type string {
                   pattern "<.*>|$.*";
                 }
                 type uint32 {
                   range "0 .. 100";
                 }
               }
             }
             leaf interval {
               description "Interval";
               units "seconds";
               type union {
                 type string {
                   pattern "<.*>|$.*";
                 }
                 type uint32 {
                   range "30 .. 3600";
                 }
               }
             }
           }
           container accelerated {
             presence "enable accelerated";
             description "Accelerated advertisement parameters";
             uses apply-advanced;
             leaf threshold {
               description "Threshold";
               units "percentage";
               type union {
                 type string {
                   pattern "<.*>|$.*";
                 }
                 type uint32 {
                   range "0 .. 100";
                 }
               }
             }
           }
         }
       }
       leaf no-advertise-adjacency-segment {
         description "Do not advertise an adjacency segment for this interface";
         type empty;
       }
       choice protection-type {
         case case_1 {
           leaf link-protection {
             description "Protect interface from link faults only";
             type empty;
           }
         }
         case case_2 {
           leaf node-link-protection {
             description "Protect interface from both link and node faults";
             type empty;
           }
         }
       }
       leaf no-eligible-backup {
         description "Not eligible for backup traffic from protected interfaces";
         type empty;
       }
       leaf no-eligible-remote-backup {
         description "Not eligible for Remote-LFA backup traffic from protected interfaces";
         type empty;
       }
       container link-degradation-threshold {
         presence "enable link-degradation-threshold";
         description "Link up and down thresholds (in %) for proactive link protection";
         leaf link-down {
           description "Signal degradation threshold above which link marked down";
           type union {
             type string {
               pattern "<.*>|$.*";
             }
             type uint32 {
               range "0 .. 100";
             }
           }
           mandatory true;
         }
         leaf link-up {
           description "Signal degradation threshold below which link is marked up.";
           type union {
             type string {
               pattern "<.*>|$.*";
             }
             type uint32 {
               range "0 .. 100";
             }
           }
           mandatory true;
         }
       }
       container auto-bandwidth {
         description "Auto bandwidth configuration";
         uses apply-advanced;
         leaf template-name {
           description "Auto bandwidth template name";
           type string;
         }
         choice enable-disable {
           case case_1 {
             leaf disable {
               description "Disable Auto bandwidth on this interface";
               type empty;
             }
           }
         }
       }
       choice enable-disable {
         case case_1 {
           leaf disable {
             description "Disable IS-IS on this interface";
             type empty;
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf flood-group {
         description "ISO Area that this interface should send LSPs to";
         type string {
         }
       }
       leaf hello-authentication-key {
         description "Authentication key (password) for hello packets";
         status deprecated;
         type jt:unreadable;
       }
       leaf hello-authentication-type {
         description "Authentication type for hello packets";
         status deprecated;
         type enumeration {
           enum "md5" {
             description "MD5 authentication";
             status deprecated;
           }
           enum "simple" {
             description "Simple password authentication";
             status deprecated;
           }
         }
       }
       leaf hello-padding-type {
         description "Type of padding for hello packets";
         default "loose";
         type enumeration {
           enum "strict" {
             description "Padding for all adjacency states";
           }
           enum "adaptive" {
             description "Padding until state of neighbor adjacency is 'up'";
           }
           enum "loose" {
             description "Padding until state of adjacency is 'initializing'";
           }
           enum "disable" {
             description "Do not add any padding for hello packets";
           }
         }
       }
       leaf interface-group-holddown-delay {
         description "Time to wait before including in BBM calculation";
         units "seconds";
         type union {
           type string {
             pattern "<.*>|$.*";
           }
           type uint32 {
             range "0 .. 60";
           }
         }
       }
       choice layer2-map-choice {
         leaf layer2-map {
           description "Kernel ARP/ND creation for nexthops";
           type empty;
         }
         leaf no-layer2-map {
           description "Don't kernel ARP/ND creation for nexthops";
           type empty;
         }
       }
       leaf max-hello-size {
         description "Maximum size allowed for ISIS Hello PDUs";
         type union {
           type string {
             pattern "<.*>|$.*";
           }
           type uint32 {
             range "512 .. 16000";
           }
         }
       }
       leaf lsp-interval {
         description "Interval between LSP transmissions";
         default "100";
         units "milliseconds";
         type union {
           type string {
             pattern "<.*>|$.*";
           }
           type uint32 {
             range "1 .. 1000";
           }
         }
       }
       container csnp-interval {
         description "Rate of CSN packets (for LAN interfaces only)";
         choice csnp_interval_option {
           case case_1 {
             leaf csnp-interval-number {
               description "Interval between CSN packets";
               units "seconds";
               type union {
                 type string {
                   pattern "<.*>|$.*";
                 }
                 type uint32 {
                   range "1 .. 65535";
                 }
               }
             }
           }
           case case_2 {
             leaf disable {
               description "Do not send CSN packets on this interface";
               type empty;
             }
           }
         }
       }
       container strict-dual-isis {
         presence "enable strict-dual-isis";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container mesh-group {
         description "Add the interface to a mesh group";
         choice mesh_group_option {
           case case_1 {
             leaf mesh-group-number {
               description "Mesh group number for this interface";
               type union {
                 type uint32;
                 type string {
                   pattern "<.*>|$.*";
                 }
               }
             }
           }
           case case_2 {
             leaf blocked {
               description "Do not flood new LSPs on this interface";
               type empty;
             }
           }
         }
       }
       leaf point-to-point {
         description "Treat interface as point to point";
         type empty;
       }
       container passive {
         presence "enable passive";
         description "Do not run IS-IS, but advertise it";
         uses apply-advanced;
         leaf remote-node-iso {
           description "ISO System-ID of the remote node";
           type jt:sysid;
         }
         leaf remote-node-id {
           description "Remote address of the link";
           type jt:ipv4addr;
         }
       }
       leaf checksum {
         description "Enable checksum for packets on this interface";
         type empty;
       }
       leaf no-unicast-topology {
         description "Do not include this interface in the unicast topology";
         type empty;
       }
       leaf no-ipv4-multicast {
         description "Do not include this interface in the IPv4 multicast topology";
         type empty;
       }
       leaf no-ipv6-unicast {
         description "Do not include this interface in the IPv6 unicast topology";
         type empty;
       }
       leaf no-ipv6-multicast {
         description "Do not include this interface in the IPv6 multicast topology";
         type empty;
       }
       leaf no-adjacency-down-notification {
         description "Do not inform other protocols about adjacency down events";
         type empty;
       }
       container bfd-liveness-detection {
         description "Bidirectional Forwarding Detection options";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list family {
         key name;
         ordered-by user;
         description "Address family specific interface attributes";
         leaf name {
           type enumeration {
             enum "inet" {
               description "IPv4 family";
             }
             enum "inet6" {
               description "IPv6 family";
             }
           }
         }
         uses apply-advanced;
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "1 .. 255000";
                 }
               }
               mandatory true;
             }
           }
           leaf holddown-interval {
             description "Time to hold the session-UP notification to the client";
             units "milliseconds";
             type union {
               type string {
                 pattern "<.*>|$.*";
               }
               type uint32 {
                 range "0 .. 255000";
               }
             }
           }
         }
       }
       leaf strict-bfd {
         description "Enable strict bfd over this interface";
         type empty;
       }
       leaf-list srlg {
         ordered-by user;
         description "SRLG Name";
         type string;
         max-elements 16;
       }
     }
     list bier-sub-domain {
       key name;
       description "Configuration of bier subdomain";
       leaf name {
         description "Enable bier subdomain id";
         type union {
           type uint8;
           type string {
             pattern "<.*>|$.*";
           }
         }
       }
     }
     container prefix-unreachable {
       presence "enable prefix-unreachable";
       description "Configure unreachable prefix advertisement parameters";
       uses apply-advanced;
       container originator {
         description "Parameters for originating unreachable prefix advertisements";
         uses apply-advanced;
         leaf unplanned-lifetime {
           description "Lifetime of unplanned UPA";
           units "seconds";
           type union {
             type string {
               pattern "<.*>|$.*";
             }
             type uint32 {
               range "30 .. 65535";
             }
           }
         }
         leaf metric {
           description "Metric value of unplanned UPA";
           type union {
             type string {
               pattern "<.*>|$.*";
             }
             type uint32 {
               range "4261412865 .. 4294967295";
             }
           }
         }
         leaf max-advertisements {
           description "Maximum UPAs that can be originated at any point of time";
           type union {
             type string {
               pattern "<.*>|$.*";
             }
             type uint32 {
               range "1 .. 10000";
             }
           }
         }
       }
       leaf use-only-for-leaking {
         description "Do not use this UPA route for resolution";
         type empty;
       }
     }
     container source-packet-routing {
       presence "enable source-packet-routing";
       description "Enable Source Packet Routing (SPRING)";
       uses apply-advanced;
       container adjacency-segment {
         description "Configure attributes for Adjacency Segments in SPRING";
         uses apply-advanced;
         leaf hold-time {
           description "Duration(ms) for which adjacency segments will be retained after isolating from an interface";
           type union {
             type string {
               pattern "<.*>|$.*";
             }
             type uint32 {
               range "180000 .. 900000";
             }
           }
         }
       }
       container udp-tunneling {
         description "Enable SR over UDP feature";
         uses apply-advanced;
         leaf encapsulation {
           description "Enable UDP Tunnel Encapsulation";
           type empty;
         }
         leaf decapsulation {
           description "Enable UDP Tunnel decapsulation";
           type empty;
         }
       }
       container srgb {
         description "Set the SRGB global block in SPRING";
         leaf start-label {
           description "Start range for SRGB label block";
           type union {
             type string {
               pattern "<.*>|$.*";
             }
             type uint32;
           }
           mandatory true;
         }
         leaf index-range {
           description "Index to the SRGB start label block";
           type union {
             type string {
               pattern "<.*>|$.*";
             }
             type uint32;
           }
           mandatory true;
         }
       }
       container node-segment {
         description "Enable support for Node segments in SPRING";
         uses apply-advanced;
         leaf ipv4-index {
           description "Set IPv4 Node Segment index";
           type union {
             type string {
               pattern "<.*>|$.*";
             }
             type uint32 {
               range "0 .. 1048575";
             }
           }
         }
         leaf ipv6-index {
           description "Set IPv6 Node Segment index";
           type union {
             type string {
               pattern "<.*>|$.*";
             }
             type uint32 {
               range "0 .. 1048575";
             }
           }
         }
         leaf index-range {
           description "Set Range of Node Segment indices allowed";
           type union {
             type string {
               pattern "<.*>|$.*";
             }
             type uint32 {
               range "32 .. 16385";
             }
           }
         }
       }
       leaf-list flex-algorithm {
         description "Flex-algorithms we would like to participate in";
         type union {
           type string {
             pattern "<.*>|$.*";
           }
           type uint32 {
             range "128 .. 255";
           }
         }
         max-elements 16;
       }
       leaf use-flex-algorithm-metric-always {
         description "Use flex-algo prefix metric whenever available";
         type empty;
       }
       leaf strict-asla-based-flex-algorithm {
         description "Flex-Algorithm to ignore links not having ASLA sub-TLVs";
         type empty;
       }
       leaf new-capability-subtlv {
         description "Advertise all ranges in single spring capability subtlv";
         type empty;
       }
       leaf explicit-null {
         description "Set E and P bits in all Prefix SID advertisements";
         type empty;
       }
       leaf ultimate-hop-popping {
         description "Set P bit for no-php in all Prefix SID advertisements";
         type empty;
       }
       leaf mapping-server {
         description "Mapping server name";
         type string;
       }
       leaf no-strict-spf {
         description " Disable strict spf algo 1 advertisement";
         type empty;
       }
       leaf no-binding-sid-leaking {
         description " Disable SRMS binding sid leaking";
         type empty;
       }
       leaf ldp-stitching {
         description "Enable SR to LDP stitching";
         type empty;
       }
       leaf entropy-label {
         description " Enable entropy label";
         type empty;
       }
       container srv6 {
         presence "enable srv6";
         description "Enable IPv6 Segment Routing (SRv6)";
         uses apply-advanced;
         list locator {
           key name;
           ordered-by user;
           description "SRv6 Locator";
           leaf name {
             description "Locator name";
             type string;
             mandatory true;
           }
           uses apply-advanced;
           leaf anycast {
             description "Set A flag in the Prefix-Attribute sub-TLV";
             type empty;
           }
           list end-sid {
             key name;
             ordered-by user;
             leaf name {
               type jt:ipv6addr;
             }
             uses apply-advanced;
             container flavor {
               presence "enable flavor";
               description "Configure end-SID flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
           container dynamic-end-sid {
             presence "enable dynamic-end-sid";
             description "Allocate end SID dynamically";
             uses apply-advanced;
             container flavor {
               presence "enable flavor";
               description "Configure end-SID flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
           leaf micro-node-sid {
             description "Program and advertise micro-node-SID";
             type empty;
           }
         }
         container sensor-based-stats {
           description "Configure sensor based stats in SRv6";
           uses apply-advanced;
           leaf remote-locator-ingress {
             description "Enable sensor based stats for remote locator ingress accounting";
             type empty;
           }
           leaf remote-locator-egress {
             description "Enable sensor based stats for remote locator egress accounting";
             type empty;
           }
         }
       }
       container sensor-based-stats {
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
       container traffic-statistics {
         description "Enable support for traffic statistics in SPRING";
         uses apply-advanced;
         container statistics-granularity {
           description "Granularity for traffic statistics in SPRING";
           uses apply-advanced;
           leaf per-interface {
             description "Interface Based traffic statistics in SPRING";
             type empty;
           }
         }
         leaf congestion-protection {
           description "Enable tactical traffic engineering";
           type empty;
         }
         leaf auto-bandwidth {
           description "Auto bandwidth name";
           type string;
         }
       }
     }
     container srm6 {
       presence "enable srm6";
       description "Enable SRm6";
       uses apply-advanced;
       container sid {
         description "Configure attributes for SID in srm6";
         uses apply-advanced;
         leaf node-sid {
           description "Set Node SID Value";
           type union {
             type string {
               pattern "<.*>|$.*";
             }
             type uint32 {
               range "1 .. 65535";
             }
           }
           mandatory true;
         }
         leaf address {
           description "IPv6 address corresponding to SID";
           type jt:ipv6addr;
           mandatory true;
         }
       }
     }
     list level {
       key name;
       ordered-by user;
       description "Configure global level attributes";
       leaf name {
         description "IS-IS level number";
         type union {
           type string {
             pattern "<.*>|$.*";
           }
           type uint32 {
             range "1 .. 2";
           }
         }
       }
       uses apply-advanced;
       leaf labeled-preference {
         description "Preference of labeled IS-IS routes";
         type union {
           type uint32;
           type string {
             pattern "<.*>|$.*";
           }
         }
       }
       leaf srv6-preference {
         description "Preference of SRV6 IS-IS routes";
         type union {
           type uint32;
           type string {
             pattern "<.*>|$.*";
           }
         }
       }
       leaf flex-algorithm-preference {
         description "Preference of flex-algorithm routes";
         type union {
           type uint32;
           type string {
             pattern "<.*>|$.*";
           }
         }
       }
       container source-packet-routing {
         presence "enable source-packet-routing";
         description "Enable Source Packet Routing (SPRING)";
         uses apply-advanced;
         choice enable-disable {
           case case_1 {
             leaf disable {
               description "Disable Source Packet Routing on this level";
               type empty;
             }
           }
         }
         leaf srms-preference {
           description "Set SRMS preference value";
           type union {
             type string {
               pattern "<.*>|$.*";
             }
             type uint32 {
               range "0 .. 255";
             }
           }
         }
       }
       choice enable-disable {
         case case_1 {
           leaf disable {
             description "Disable IS-IS on this level";
             type empty;
           }
         }
       }
       leaf authentication-key {
         description "Authentication key (password)";
         type jt:unreadable;
       }
       leaf authentication-type {
         description "Authentication type";
         type enumeration {
           enum "md5" {
             description "MD5 authentication";
           }
           enum "simple" {
             description "Simple password authentication";
           }
         }
       }
       leaf purge-originator {
         description "Add Purge Originator information";
         type enumeration {
           enum "self" {
             description "Add POI only for self-originated purge LSPs";
           }
           enum "empty" {
             description "Add POI for purge LSPs who do not have POI information";
           }
         }
       }
       leaf no-hello-authentication {
         description "Disable authentication for hello packets";
         type empty;
       }
       leaf no-csnp-authentication {
         description "Disable authentication for CSN packets";
         type empty;
       }
       leaf no-psnp-authentication {
         description "Disable authentication for PSN packets";
         type empty;
       }
       leaf no-lsp-authentication {
         description "Disable authentication for LSP packets";
         type empty;
       }
       leaf authentication-key-chain {
         description "Key chain name";
         type string {
           length "1 .. 128";
         }
       }
       leaf wide-metrics-only {
         description "Generate wide metrics only";
         type empty;
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf prefix-export-limit {
         description "Maximum number of external prefixes that can be exported";
         type union {
           type string {
             pattern "<.*>|$.*";
           }
           type uint32 {
             range "0 .. 4294967295";
           }
         }
       }
       leaf max-lsp-size {
         description "Maximum size allowed for LSPs";
         type union {
           type string {
             pattern "<.*>|$.*";
           }
           type uint32 {
             range "512 .. 9192";
           }
         }
       }
       container flood-reflector {
         description "Enable flood-reflector";
         uses apply-advanced;
         choice flood-reflector-choice {
           case case_1 {
             container reflector {
               description "Configure this as a flood-reflector";
               uses apply-advanced;
               leaf cluster-id {
                 description "Cluster-ID";
                 type union {
                   type string {
                     pattern "<.*>|$.*";
                   }
                   type uint32 {
                     range "1 .. 4294967295";
                   }
                 }
                 mandatory true;
               }
             }
           }
           case case_2 {
             leaf client {
               description "Configure interface as flood-reflector client";
               type empty;
             }
           }
         }
       }
     }
     list interface-group {
       key name;
       description "Interface grouping configuration";
       leaf name {
         description "Interface group name";
         type string;
       }
       uses apply-advanced;
       list level {
         key name;
         ordered-by user;
         description "Configure levels on this interface-group";
         leaf name {
           description "IS-IS level number";
           type union {
             type string {
               pattern "<.*>|$.*";
             }
             type uint32 {
               range "1 .. 2";
             }
           }
         }
         uses apply-advanced;
         container ipv4-adjacency-segment {
           description "Configure ipv4 adjacency segment";
           uses apply-advanced;
           container protected {
             description "Adjacency SID is eligible for protection";
             uses apply-advanced;
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             uses apply-advanced;
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 1048575";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
               mandatory true;
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
                 mandatory true;
               }
             }
           }
         }
       }
       container link-group-protection {
         description "Configure link group protection";
         uses apply-advanced;
         leaf minimum-bandwidth {
           description "Minimum bandwidth to carry traffic";
           type string;
         }
         leaf revert-bandwidth {
           description "Revert bandwidth to carry traffic";
           type string;
         }
       }
       list interface {
         key name;
         description "List interfaces for this group";
         leaf name {
           description "Interface name";
           type union {
             type jt:interface-name;
             type string {
               pattern "<.*>|$.*";
             }
           }
         }
         uses apply-advanced;
         leaf weight {
           description "Interface weight for adjacency set";
           type union {
             type string {
               pattern "<.*>|$.*";
             }
             type uint32 {
               range "1 .. 255";
             }
           }
         }
       }
     }
     container spf-options {
       description "Configure SPF attributes";
       uses apply-advanced;
       container microloop-avoidance {
         description "Configure microloop avoidance mechanisms";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Set maximum number of label supported for Micro-Loop-Avoidance calculations";
             type union {
               type string {
                 pattern "<.*>|$.*";
               }
               type uint32 {
                 range "2 .. 8";
               }
             }
           }
           leaf maximum-srv6-sids {
             description "Set maximum number of SRV6 SIDs supported for Micro-Loop-Avoidance calculations";
             type union {
               type string {
                 pattern "<.*>|$.*";
               }
               type uint32 {
                 range "2 .. 12";
               }
             }
           }
         }
       }
       leaf delay {
         description "Time to wait before running an SPF";
         units "milliseconds";
         type union {
           type string {
             pattern "<.*>|$.*";
           }
           type uint32 {
             range "50 .. 1000";
           }
         }
       }
       leaf holddown {
         description "Time to hold down before running an SPF";
         units "milliseconds";
         type union {
           type string {
             pattern "<.*>|$.*";
           }
           type uint32 {
             range "1000 .. 10000";
           }
         }
       }
       leaf rapid-runs {
         description "Number of rapid SPF runs before SPF holddown";
         type union {
           type string {
             pattern "<.*>|$.*";
           }
           type uint32 {
             range "1 .. 5";
           }
         }
       }
       container multipath {
         description "Configure multipath options";
         uses apply-advanced;
         container weighted {
           description "Weighted multipath options";
           uses apply-advanced;
           leaf one-hop {
             description "Enable load balancing on onehop multipath based on interface bandwidth";
             type empty;
           }
         }
       }
     }
     container traceoptions {
       description "Trace options for IS-IS";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "post-convergence-lfa" {
               description "Trace post-convergence-lfa related events";
             }
             enum "traffic-statistics" {
               description "Trace traffic-statistics related events";
             }
             enum "error" {
               description "Trace errored packets";
             }
             enum "spf" {
               description "Trace SPF events";
             }
             enum "packets" {
               description "Trace IS-IS packets";
             }
             enum "hello" {
               description "Trace hello packets";
             }
             enum "lsp" {
               description "Trace link-state packets";
             }
             enum "psn" {
               description "Trace partial sequence number (PSN) packets";
             }
             enum "csn" {
               description "Trace complete sequence number (CSN) packets";
             }
             enum "layer2-map" {
               description "Trace ARP/ND kernel state manipulation";
             }
             enum "lsp-generation" {
               description "Trace LSP generation";
             }
             enum "graceful-restart" {
               description "Trace graceful restart events";
             }
             enum "ldp-synchronization" {
               description "Trace synchronization between IS-IS and LDP";
             }
             enum "nsr-synchronization" {
               description "Trace NSR synchronization events";
             }
             enum "spring" {
               description "Trace source packet routing";
             }
             enum "prefix-sid" {
               description "Trace source packet routing, prefix-sids";
             }
             enum "flex-algorithm" {
               description "Trace flex-algorithm related events";
             }
             enum "adj-sid" {
               description "Trace adj-sid related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "srv6" {
               description "Trace srv6 related events";
             }
             enum "rmopd" {
               description "Trace rmopd interactions";
             }
             enum "mapping-server" {
               description "Trace mapping server related events";
             }
             enum "prefix-unreachable" {
               description "Trace unreachable prefix advertisement related events";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container backup-spf-options {
       description "Configure backup SPF attributes";
       uses apply-advanced;
       container remote-backup-calculation {
         presence "enable remote-backup-calculation";
         description "Calculate Remote LFA backup nexthops";
         uses apply-advanced;
       }
       container use-post-convergence-lfa {
         presence "enable use-post-convergence-lfa";
         description "Calculate Post Convergence Backup Nexthops";
         uses apply-advanced;
         leaf maximum-labels {
           description "Set maximum number of label supported for post convergence path calculations";
           type union {
             type string {
               pattern "<.*>|$.*";
             }
             type uint32 {
               range "2 .. 8";
             }
           }
         }
         leaf maximum-srv6-sids {
           description "Set maximum number of SRV6 SIDs for post convergence path calculations";
           type union {
             type string {
               pattern "<.*>|$.*";
             }
             type uint32 {
               range "2 .. 12";
             }
           }
         }
         leaf maximum-backup-paths {
           description "Set maximum equal cost backup post convergence paths";
           type union {
             type string {
               pattern "<.*>|$.*";
             }
             type uint32 {
               range "1 .. 8";
             }
           }
         }
       }
       container use-source-packet-routing {
         presence "enable use-source-packet-routing";
         description "Use SPRING routed paths for protection";
         uses apply-advanced;
       }
       leaf per-prefix-calculation {
         description "Calculate backup nexthops for non-best prefix originators";
         type empty;
       }
       leaf node-link-degradation {
         description "Degrade to link protection when nodelink protection not available";
         type empty;
       }
     }
     list context-identifier {
       key name;
       ordered-by user;
       description "Configuration for advertisement of a context-identifier ";
       leaf name {
         description "Context identifier range";
         type jt:ipprefix;
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
       }
     }
     container traffic-engineering {
       description "Configure traffic engineering attributes";
       uses apply-advanced;
       choice enable-disable {
         case case_1 {
           leaf disable {
             description "Disable traffic engineering";
             type empty;
           }
         }
       }
       leaf l3-unicast-topology {
         description "Download IGP topology into TED";
         type empty;
       }
       leaf ipv6 {
         description "Enable TEDv6";
         type empty;
       }
       leaf credibility-protocol-preference {
         description "Follow IGP protocol preference for TED protocol credibility";
         type empty;
       }
       leaf ipv4-multicast-rpf-routes {
         description "Install IPv4 routes for multicast RPF checks into inet.2";
         status deprecated;
         type empty;
       }
       leaf ignore-lsp-metrics {
         description "Ignore label-switched path metrics when doing shortcuts";
         type empty;
       }
       container tunnel-source-protocol {
         description "Protocols from which to pick label-switched paths";
         uses apply-advanced;
         container rsvp {
           presence "enable rsvp";
           description "Pick label-switched paths from rsvp";
           uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           uses apply-advanced;
           leaf preference {
             description "Preference for label-switched paths from this protocol";
             type union {
               type string {
                 pattern "<.*>|$.*";
               }
               type uint32 {
                 range "1 .. 255";
               }
             }
           }
         }
       }
       list family {
         key name;
         ordered-by user;
         description "Address family specific traffic-engineering attributes";
         leaf name {
           type enumeration {
             enum "inet" {
               description "IPv4 family";
             }
             enum "inet6" {
               description "IPv6 family";
             }
             enum "inet-mpls" {
               description "IPv4-MPLS family";
             }
             enum "inet6-mpls" {
               description "IPv6-MPLS family";
             }
           }
         }
         uses apply-advanced;
         container shortcuts {
           presence "enable shortcuts";
           description "Use label-switched paths as next hops, if possible";
           uses apply-advanced;
           leaf multicast-rpf-routes {
             description "Install routes for multicast RPF checks into multicast RIB";
             type empty;
           }
           leaf-list import {
             ordered-by user;
             description "Import policy for shortcut";
             type jt:policy-algebra;
           }
         }
       }
       container shortcuts {
         presence "enable shortcuts";
         description "Use label-switched paths as next hops, if possible";
         status deprecated;
         uses apply-advanced;
         leaf ignore-lsp-metrics {
           description "Ignore label-switched path metrics when doing shortcuts";
           status deprecated;
           type empty;
         }
       }
       container multipath {
         description "Configure label-switched-path multipath behavior";
         uses apply-advanced;
         leaf lsp-equal-cost {
           description "Include equal cost label-switched-paths";
           type empty;
         }
       }
       container advertisement {
         description "Configure traffic engineering attribute advertisements";
         uses apply-advanced;
         leaf always {
           description "Advertise applicable legacy TE attributes always";
           type empty;
         }
         container application-specific {
           description "Advertise application-specific TE attributes";
           uses apply-advanced;
           container all-applications {
             presence "enable all-applications";
             description "Advertise common application-specific link attributes";
             uses apply-advanced;
             leaf legacy {
               description "Use legacy TE attributes for this application";
               type empty;
             }
           }
         }
       }
     }
     list label-switched-path {
       key name;
       ordered-by user;
       description "Configuration for advertisement of a label-switched path";
       leaf name {
         description "Name of label-switched path to be advertised";
         type string {
           length "1 .. 64";
         }
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
         leaf metric {
           description "SPF metric for this level";
           type union {
             type string {
               pattern "<.*>|$.*";
             }
             type uint32 {
               range "0 .. 16777215";
             }
           }
         }
       }
     }
     choice enable-disable {
       case case_1 {
         leaf disable {
           description "Disable IS-IS";
           type empty;
         }
       }
     }
     leaf-list export {
       ordered-by user;
       description "Export policy";
       type jt:policy-algebra;
     }
     leaf-list import {
       ordered-by user;
       description "Import policy";
       type jt:policy-algebra;
     }
     leaf reference-bandwidth {
       description "Bandwidth for calculating metric defaults";
       type string;
     }
     choice layer2-map-choice {
       leaf layer2-map {
         description "Kernel ARP/ND creation for nexthops";
         type empty;
       }
       leaf no-layer2-map {
         description "Don't kernel ARP/ND creation for nexthops";
         type empty;
       }
     }
     leaf job-stats {
       description "Collect job statistics";
       type empty;
     }
     leaf lsp-lifetime {
       description "Lifetime of LSPs";
       units "seconds";
       type union {
         type string {
           pattern "<.*>|$.*";
         }
         type uint32 {
           range "350 .. 65535";
         }
       }
     }
     leaf max-lsp-size {
       description "Maximum size allowed for LSPs";
       default "1492";
       type union {
         type string {
           pattern "<.*>|$.*";
         }
         type uint32 {
           range "512 .. 9192";
         }
       }
     }
     leaf max-hello-size {
       description "Maximum size allowed for ISIS Hello PDUs";
       default "1492";
       type union {
         type string {
           pattern "<.*>|$.*";
         }
         type uint32 {
           range "512 .. 16000";
         }
       }
     }
     leaf max-snp-size {
       description "Maximum size allowed for Sequence Number (Complete/Partial) PDUs";
       default "1400";
       type union {
         type string {
           pattern "<.*>|$.*";
         }
         type uint32 {
           range "512 .. 1400";
         }
       }
     }
     leaf spf-delay {
       description "Time to wait before running an SPF";
       status deprecated;
       units "milliseconds";
       type union {
         type string {
           pattern "<.*>|$.*";
         }
         type uint32 {
           range "50 .. 120000";
         }
       }
     }
     leaf authentication-key {
       description "Authentication key (password)";
       status deprecated;
       type jt:unreadable;
     }
     leaf authentication-type {
       description "Authentication type";
       status deprecated;
       type enumeration {
         enum "md5" {
           description "MD5 authentication";
           status deprecated;
         }
         enum "simple" {
           description "Simple password authentication";
           status deprecated;
         }
       }
     }
     leaf loose-authentication-check {
       description "Verify authentication only if PDU has authentication TLV";
       type empty;
     }
     leaf max-areas {
       description "Maximum number of advertised Areas";
       default "3";
       type union {
         type string {
           pattern "<.*>|$.*";
         }
         type uint32 {
           range "3 .. 64";
         }
       }
     }
     leaf no-authentication-check {
       description "Disable authentication checking";
       type empty;
     }
     leaf no-ipv4-routing {
       description "Disable IPv4 routing";
       type empty;
     }
     leaf no-ipv6-routing {
       description "Disable IPv6 routing";
       type empty;
     }
     leaf no-adjacency-holddown {
       description "Disable adjacency hold down";
       type empty;
     }
     leaf multicast-topology {
       description "Enable multicast topology";
       status deprecated;
       type empty;
     }
     leaf ignore-attached-bit {
       description "Ignore the attached bit in Level 1 LSPs";
       type empty;
     }
     container rib-group {
       description "Routing table group for importing IS-IS routes";
       uses rib_group_type;
     }
     container no-external-export {
       description "No external export";
       uses apply-advanced;
       list protocol {
         key name;
         ordered-by user;
         description "Protocol parameters";
         leaf name {
           type enumeration {
             enum "bgp" {
               description "BGP";
             }
             enum "ospf" {
               description "OSPF";
             }
             enum "isis" {
               description "ISIS";
             }
             enum "l-isis" {
               description "Labelled ISIS";
             }
             enum "l-ospf" {
               description "Labelled OSPF";
             }
             enum "static" {
               description "Static";
             }
           }
         }
       }
     }
     container strict-dual-isis {
       presence "enable strict-dual-isis";
       description "Enable dual isis if spf computation is required for both ipv4 and ipv6 family";
       uses apply-advanced;
       leaf holdown {
         description "Time to wait for ipv4 and ipv6 connectivity";
         status deprecated;
         default "12";
         type union {
           type string {
             pattern "<.*>|$.*";
           }
           type uint32 {
             range "1 .. 65535";
           }
         }
       }
       leaf holddown {
         description "Time to wait for ipv4 and ipv6 connectivity";
         default "12";
         type union {
           type string {
             pattern "<.*>|$.*";
           }
           type uint32 {
             range "1 .. 65535";
           }
         }
       }
     }
     container topologies {
       description "Enable topologies";
       uses apply-advanced;
       leaf ipv4-multicast {
         description "Enable IPv4-multicast topology";
         type empty;
       }
       leaf ipv6-unicast {
         description "Enable IPv6-unicast topology";
         type empty;
       }
       leaf ipv6-multicast {
         description "Enable IPv6-multicast topology";
         type empty;
       }
     }
     container overload {
       presence "enable overload";
       description "Set the overload bit (no transit traffic)";
       uses apply-advanced;
       leaf timeout {
         description "Time after which overload bit is reset";
         units "seconds";
         type union {
           type string {
             pattern "<.*>|$.*";
           }
           type uint32 {
             range "60 .. 3600";
           }
         }
       }
       leaf advertise-high-metrics {
         description "Advertise high metrics instead of setting the overload bit";
         type empty;
       }
       leaf allow-route-leaking {
         description "Allow routes to be leaked when overload is configured";
         type empty;
       }
       leaf internal-prefixes {
         description "Allow internal prefixes to be advertised with high metric";
         type empty;
       }
       leaf external-prefixes {
         description "Allow external prefixes to be advertised with high metric";
         type empty;
       }
     }
     container dynamic-overload {
       description "Set the dynamic overload options";
       uses apply-advanced;
       leaf no-overload-on-prefix-export-limit {
         description "Do not set overload bit when prefix export limit is reached";
         type empty;
       }
       leaf auto-recovery {
         description "Enable Auto recovery to recover from dynamic overload state";
         type empty;
       }
     }
     container graceful-restart {
       description "IS-IS graceful restart options";
       choice enable-disable {
         case case_1 {
           leaf disable {
             description "Disable graceful restart";
             type empty;
           }
         }
       }
       leaf helper-disable {
         description "Disable graceful restart helper capability";
         type empty;
       }
       leaf restart-duration {
         description "Maximum time for graceful restart to finish";
         units "seconds";
         type union {
           type string {
             pattern "<.*>|$.*";
           }
           type uint32 {
             range "30 .. 300";
           }
         }
       }
     }
     list net {
       key name;
       description "Assign Network Entity Title (NET) configuration";
       leaf name {
         description "Assign Network Entity Title (NET) address to an IS-IS router";
         type jt:isoaddr;
       }
     }
     leaf rfc7775-compliance {
       description "RFC 7775 compliance for up/down bit and prefix attribute sub-tlv";
       type empty;
     }
     container pixel-tracing {
       description "Pixel-tracing for IS-IS";
       uses apply-advanced;
       choice enable-disable {
         case case_1 {
           leaf disable {
             description "Disable pixel-tracing for IS-IS";
             type empty;
           }
         }
       }
     }
   }
   grouping juniper-protocols-l2control {
     uses apply-advanced;
     container traceoptions {
       description "Global tracing options for STP";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "ppmlite" {
               description "Trace libppmlite processing";
             }
             enum "all" {
               description "Trace everything";
             }
           }
         }
         leaf disable {
           description "Disable this trace flag";
           type empty;
         }
       }
     }
     leaf nonstop-bridging {
       description "Enable nonstop operation";
       type empty;
     }
     choice ephemeral-db-support-choice {
       leaf ephemeral-db-support {
         description "Enable ephemeral DB supoort for STP";
         type empty;
       }
       leaf no-ephemeral-db-support {
         description "Don't enable ephemeral DB supoort for STP";
         type empty;
       }
     }
     container bpdu-block {
       presence "enable bpdu-block";
       description "Block BPDU on interface (BPDU Protect)";
       uses apply-advanced;
       list interface {
         key name;
         ordered-by user;
         description "Interface name to block BPDU on";
         leaf name {
           type string;
         }
         uses apply-advanced;
         leaf disable {
           description "Disable bpdu-block on a port";
           type empty;
         }
         leaf drop {
           description "Drop xSTP BPDUs";
           type empty;
         }
       }
       leaf disable-timeout {
         description "Disable timeout for BPDU Protect";
         units "seconds";
         type union {
           type string {
             pattern "<.*>|$.*";
           }
           type int32 {
             range "10 .. 3600";
           }
         }
       }
     }
     container l2pt {
       description "L2 protocol tunneling functionality";
       uses apply-advanced;
       list interface {
         key name;
         ordered-by user;
         leaf name {
           type union {
             type jt:interface-device;
             type string {
               pattern "<.*>|$.*";
             }
           }
         }
         uses apply-advanced;
         leaf enable-all-ifl {
           description "Enable tunneling for all the IFLs under the interface";
           type empty;
         }
         container protocol {
           description "Protocols for which L2 protocol tunneling need to be enabled";
           uses apply-advanced;
           container stp {
             presence "enable stp";
             description "Enable L2 protocol tunneling for STP";
           }
           container vtp {
             presence "enable vtp";
             description "Enable L2 protocol tunneling for VTP";
           }
           container cdp {
             presence "enable cdp";
             description "Enable L2 protocol tunneling for CDP";
           }
           container pvstp {
             presence "enable pvstp";
             description "Enable L2 protocol tunneling for PVSTP+";
           }
           container all {
             presence "enable all";
             description "Enable L2 protocol tunneling for all protocols";
             uses apply-advanced;
           }
         }
         container destination {
           description "Destination tunnel for which L2 protocol tunneling need to be enabled";
           uses apply-advanced;
           leaf vxlan-tunnel {
             description "Enable L2 protocol tunneling in vxlan-tunnel";
             type empty;
           }
         }
       }
     }
     container mac-rewrite {
       description "Mac rewrite functionality";
       uses apply-advanced;
       list interface {
         key name;
         ordered-by user;
         leaf name {
           type union {
             type jt:interface-device;
             type string {
               pattern "<.*>|$.*";
             }
           }
         }
         uses apply-advanced;
         leaf enable-all-ifl {
           description "Enable tunneling for all the IFLs under the interface";
           type empty;
         }
         container protocol {
           description "Protocols for which Mac rewrite need to be enabled";
           uses apply-advanced;
           container stp {
             presence "enable stp";
             description "Enable L2 protocol tunneling for STP";
           }
           container vtp {
             presence "enable vtp";
             description "Enable L2 protocol tunneling for VTP";
           }
           container cdp {
             presence "enable cdp";
             description "Enable L2 protocol tunneling for CDP";
           }
           container pvstp {
             presence "enable pvstp";
             description "Enable L2 protocol tunneling for PVSTP+";
           }
           container all {
             presence "enable all";
             description "Enable L2 protocol tunneling for all protocols";
             uses apply-advanced;
           }
         }
       }
     }
   }
   grouping juniper-protocols-lmp {
     uses apply-advanced;
     list te-link {
       key name;
       ordered-by user;
       description "Traffic engineering link";
       leaf name {
         description "Name of TE link";
         type string;
       }
       uses apply-advanced;
       leaf local-address {
         description "Address of the local end of the link";
         type jt:ipaddr;
       }
       leaf remote-address {
         description "Address of the remote end of the link";
         type jt:ipaddr;
       }
       leaf remote-id {
         description "Link ID for the remote end of the link";
         type union {
           type string {
             pattern "<.*>|$.*";
           }
           type uint32 {
             range "1 .. 4294967295";
           }
         }
       }
       leaf te-metric {
         description "Traffic engineering metric of the link";
         type union {
           type string {
             pattern "<.*>|$.*";
           }
           type uint32 {
             range "1 .. 65535";
           }
         }
       }
       choice enable-disable {
         case case_1 {
           leaf disable {
             description "Disable TE link";
             type empty;
           }
         }
       }
       container ethernet-vlan {
         presence "enable ethernet-vlan";
         description "TE link used for setup of  L2 VLAN LSP";
         uses apply-advanced;
         leaf-list vlan-id-range {
           description "VLAN id";
           type jt:vlan-range;
           max-elements 1;
         }
       }
       choice resource-option {
         case case_1 {
           list interface {
             key name;
             ordered-by user;
             description "Member interface of TE link";
             leaf name {
               description "Interface name";
               type union {
                 type jt:interface-device;
                 type string {
                   pattern "<.*>|$.*";
                 }
               }
             }
             uses apply-advanced;
             leaf local-address {
               description "Local address of the resource";
               type jt:ipaddr;
             }
             leaf remote-address {
               description "Remote address of the resource";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
         case case_2 {
           list label-switched-path {
             key name;
             ordered-by user;
             description "Member forwarding adjacency LSP of TE link";
             max-elements 1;
             leaf name {
               description "Name of label-switched path";
               type string;
             }
             uses apply-advanced;
             leaf local-address {
               description "Local address of the resource";
               type jt:ipaddr;
             }
             leaf remote-address {
               description "Remote address of the resource";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
       }
     }
     list peer {
       key name;
       ordered-by user;
       description "Define a network or LMP peer";
       leaf name {
         description "Name of peer";
         type string;
       }
       uses apply-advanced;
       leaf address {
         description "Address of peer";
         type jt:ipaddr;
         mandatory true;
       }
       container lmp-protocol {
         presence "enable lmp-protocol";
         description "LMP protocol attributes";
         uses apply-advanced;
         leaf hello-interval {
           description "Interval between Hello messages";
           units "milliseconds";
           type union {
             type string {
               pattern "<.*>|$.*";
             }
             type uint32 {
               range "150 .. 21845";
             }
           }
         }
         leaf hello-dead-interval {
           description "Delay for control channel shutdown when no Hello received";
           units "milliseconds";
           type union {
             type string {
               pattern "<.*>|$.*";
             }
             type uint32 {
               range "500 .. 65535";
             }
           }
         }
         leaf retransmission-interval {
           description "Minimum time before retransmitting a message";
           units "milliseconds";
           type union {
             type string {
               pattern "<.*>|$.*";
             }
             type uint32 {
               range "500 .. 300000";
             }
           }
         }
         leaf retry-limit {
           description "Number of times to retransmit a message";
           type union {
             type string {
               pattern "<.*>|$.*";
             }
             type uint32 {
               range "3 .. 1000";
             }
           }
         }
         leaf passive {
           description "Do not send Config messages to peer";
           type empty;
         }
       }
       leaf-list control-channel {
         ordered-by user;
         description "Control channel interfaces by priority";
         type union {
           type jt:interface-name;
           type string {
             pattern "<.*>|$.*";
           }
         }
       }
       list lmp-control-channel {
         key name;
         ordered-by user;
         description "Control channel IDs";
         uses lmp_control_channel_type;
       }
       leaf-list te-link {
         ordered-by user;
         description "List of TE links managed by this peer";
         type string;
       }
     }
     container traceoptions {
       description "LMP trace options";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace general configuration processing";
             }
             enum "server" {
               description "Trace server processing";
             }
             enum "routing" {
               description "Trace routing protocols interworking";
             }
             enum "packets" {
               description "Trace packet processing";
             }
             enum "hello-packets" {
               description "Trace hello packet processing";
             }
             enum "state" {
               description "Trace state transitions";
             }
             enum "nsr-synchronization" {
               description "Trace mirror and nsr transitions";
             }
             enum "all" {
               description "Trace everything";
             }
           }
         }
         leaf send {
           description "Trace transmitted packets";
           status deprecated;
           type empty;
         }
         leaf receive {
           description "Trace received packets";
           status deprecated;
           type empty;
         }
         leaf detail {
           description "Trace detailed information";
           status deprecated;
           type empty;
         }
         leaf disable {
           description "Disable this trace flag";
           status deprecated;
           type empty;
         }
       }
     }
   }
   grouping juniper-protocols-msdp {
     uses apply-advanced;
     leaf data-encapsulation {
       description "Set encapsulation of data packets";
       type enumeration {
         enum "disable" {
           description "Disable data encapsulation";
         }
         enum "enable" {
           description "Enable data encapsulation";
         }
       }
     }
     container rib-group {
       description "Routing table group";
       uses rib_group_inet_type;
     }
     container active-source-limit {
       description "Limit the number of active sources accepted";
       uses apply-advanced;
       leaf maximum {
         description "Maximum number of active sources accepted";
         default "25000";
         type union {
           type string {
             pattern "<.*>|$.*";
           }
           type uint32 {
             range "1 .. 1000000";
           }
         }
       }
       leaf threshold {
         description "RED threshold for active source acceptance";
         default "24000";
         type union {
           type string {
             pattern "<.*>|$.*";
           }
           type uint32 {
             range "1 .. 1000000";
           }
         }
       }
       leaf log-warning {
         description "Percentage of maximum at which to start generating warnings";
         default "100";
         type union {
           type string {
             pattern "<.*>|$.*";
           }
           type uint32 {
             range "1 .. 100";
           }
         }
       }
       leaf log-interval {
         description "Time between log messages";
         type union {
           type string {
             pattern "<.*>|$.*";
           }
           type uint32 {
             range "6 .. 32767";
           }
         }
       }
     }
     choice enable-disable {
       case case_1 {
         leaf disable {
           description "Disable MSDP";
           type empty;
         }
       }
     }
     leaf-list export {
       ordered-by user;
       description "Export policy";
       type jt:policy-algebra;
     }
     leaf-list import {
       ordered-by user;
       description "Import policy";
       type jt:policy-algebra;
     }
     leaf local-address {
       description "Local address";
       type jt:ipv4addr;
     }
     container traceoptions {
       description "Trace options for MSDP";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MSDP packets";
             }
             enum "route" {
               description "Trace routing information";
             }
             enum "nsr-synchronization" {
               description "Trace NSR synchronization events";
             }
             enum "source-active" {
               description "Trace source-active messages";
             }
             enum "source-active-request" {
               description "Trace source-active request messages";
             }
             enum "source-active-response" {
               description "Trace source-active response messages";
             }
             enum "keepalive" {
               description "Trace keepalive messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     list peer {
       key name;
       ordered-by user;
       description "Configure an MSDP peer";
       leaf name {
         description "Peer address";
         type jt:ipv4addr;
       }
       uses apply-advanced;
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           type union {
             type string {
               pattern "<.*>|$.*";
             }
             type uint32 {
               range "1 .. 100";
             }
           }
         }
         leaf log-interval {
           description "Time between log messages";
           type union {
             type string {
               pattern "<.*>|$.*";
             }
             type uint32 {
               range "6 .. 32767";
             }
           }
         }
       }
       leaf keep-alive {
         description "Time limit for sending out periodic keep alive to peer";
         units "seconds";
         type union {
           type string {
             pattern "<.*>|$.*";
           }
           type uint32 {
             range "10 .. 60";
           }
         }
       }
       leaf hold-time {
         description "Max time to terminating a peer for having not received any message from ";
         units "seconds";
         type union {
           type string {
             pattern "<.*>|$.*";
           }
           type uint32 {
             range "15 .. 150";
           }
         }
       }
       leaf sa-hold-time {
         description "Max time for holding a sa message before timing out";
         units "seconds";
         type union {
           type string {
             pattern "<.*>|$.*";
           }
           type uint32 {
             range "75 .. 300";
           }
         }
       }
       leaf default-peer {
         description "Default RPF peer";
         type empty;
       }
       leaf authentication-key {
         description "MD5 authentication key";
         type string {
           length "1 .. 126";
         }
       }
     }
     leaf keep-alive {
       description "Time limit for sending out periodic keep alive to peer";
       units "seconds";
       type union {
         type string {
           pattern "<.*>|$.*";
         }
         type uint32 {
           range "10 .. 60";
         }
       }
     }
     leaf hold-time {
       description "Max time to terminating a peer for having not received any message from ";
       units "seconds";
       type union {
         type string {
           pattern "<.*>|$.*";
         }
         type uint32 {
           range "15 .. 150";
         }
       }
     }
     leaf sa-hold-time {
       description "Max time for holding a sa message before timing out";
       units "seconds";
       type union {
         type string {
           pattern "<.*>|$.*";
         }
         type uint32 {
           range "75 .. 300";
         }
       }
     }
     list source {
       key name;
       ordered-by user;
       description "Configure parameters for each source";
       leaf name {
         description "Source address or prefix";
         type jt:ipprefix;
       }
       uses apply-advanced;
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           type union {
             type string {
               pattern "<.*>|$.*";
             }
             type uint32 {
               range "1 .. 100";
             }
           }
         }
         leaf log-interval {
           description "Time between log messages";
           type union {
             type string {
               pattern "<.*>|$.*";
             }
             type uint32 {
               range "6 .. 32767";
             }
           }
         }
       }
     }
     list group {
       key name;
       ordered-by user;
       description "Configure MSDP peer groups";
       leaf name {
         description "MSDP peer group name";
         type string;
       }
       uses apply-advanced;
       leaf mode {
         description "MSDP group source-active flooding mode";
         default "standard";
         type enumeration {
           enum "standard" {
             description "Use standard MSDP source-active flooding rules";
           }
           enum "mesh-group" {
             description "Group peers are mesh group members";
           }
         }
       }
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list peer {
         key name;
         ordered-by user;
         description "Configure an MSDP peer";
         leaf name {
           description "Peer address";
           type jt:ipv4addr;
         }
         uses apply-advanced;
         choice enable-disable {
           case case_1 {
             leaf disable {
               description "Disable MSDP";
               type empty;
             }
           }
         }
         leaf-list export {
           ordered-by user;
           description "Export policy";
           type jt:policy-algebra;
         }
         leaf-list import {
           ordered-by user;
           description "Import policy";
           type jt:policy-algebra;
         }
         leaf local-address {
           description "Local address";
           type jt:ipv4addr;
         }
         container traceoptions {
           description "Trace options for MSDP";
           uses apply-advanced;
           container file {
             description "Trace file options";
             leaf filename {
               description "Name of file in which to write trace information";
               type string {
                 length "1 .. 1024";
               }
               mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all MSDP packets";
                 }
                 enum "route" {
                   description "Trace routing information";
                 }
                 enum "nsr-synchronization" {
                   description "Trace NSR synchronization events";
                 }
                 enum "source-active" {
                   description "Trace source-active messages";
                 }
                 enum "source-active-request" {
                   description "Trace source-active request messages";
                 }
                 enum "source-active-response" {
                   description "Trace source-active response messages";
                 }
                 enum "keepalive" {
                   description "Trace keepalive messages";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         container active-source-limit {
           description "Limit the number of active sources accepted";
           uses apply-advanced;
           leaf maximum {
             description "Maximum number of active sources accepted";
             default "25000";
             type union {
               type string {
                 pattern "<.*>|$.*";
               }
               type uint32 {
                 range "1 .. 1000000";
               }
             }
           }
           leaf threshold {
             description "RED threshold for active source acceptance";
             default "24000";
             type union {
               type string {
                 pattern "<.*>|$.*";
               }
               type uint32 {
                 range "1 .. 1000000";
               }
             }
           }
           leaf log-warning {
             description "Percentage of maximum at which to start generating warnings";
             default "100";
             type union {
               type string {
                 pattern "<.*>|$.*";
               }
               type uint32 {
                 range "1 .. 100";
               }
             }
           }
           leaf log-interval {
             description "Time between log messages";
             type union {
               type string {
                 pattern "<.*>|$.*";
               }
               type uint32 {
                 range "6 .. 32767";
               }
             }
           }
         }
         leaf keep-alive {
           description "Time limit for sending out periodic keep alive to peer";
           units "seconds";
           type union {
             type string {
               pattern "<.*>|$.*";
             }
             type uint32 {
               range "10 .. 60";
             }
           }
         }
         leaf hold-time {
           description "Max time to terminating a peer for having not received any message from ";
           units "seconds";
           type union {
             type string {
               pattern "<.*>|$.*";
             }
             type uint32 {
               range "15 .. 150";
             }
           }
         }
         leaf sa-hold-time {
           description "Max time for holding a sa message before timing out";
           units "seconds";
           type union {
             type string {
               pattern "<.*>|$.*";
             }
             type uint32 {
               range "75 .. 300";
             }
           }
         }
         leaf default-peer {
           description "Default RPF peer";
           type empty;
         }
         leaf authentication-key {
           description "MD5 authentication key";
           type string {
             length "1 .. 126";
           }
         }
       }
     }
   }
   grouping juniper-protocols-mstp {
     uses apply-advanced;
     choice enable-disable {
       case case_1 {
         leaf disable {
           description "Disable MSTP";
           type empty;
         }
       }
     }
     leaf bpdu-destination-mac-address {
       description "Destination MAC address in the spanning tree BPDUs";
       type enumeration {
         enum "provider-bridge-group" {
           description "802.1ad provider bridge group address";
         }
       }
     }
     leaf configuration-name {
       description "Configuration name (part of MST configuration identifier)";
       type string {
         length "1 .. 32";
       }
     }
     leaf revision-level {
       description "Revision level (part of MST configuration identifier)";
       type union {
         type uint16;
         type string {
           pattern "<.*>|$.*";
         }
       }
     }
     leaf max-hops {
       description "Maximum number of hops";
       type union {
         type string {
           pattern "<.*>|$.*";
         }
         type uint16 {
           range "1 .. 255";
         }
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf bridge-priority {
       description "Priority of the bridge (in increments of 4k - 0,4k,8k,..60k)";
       type string {
       }
     }
     leaf backup-bridge-priority {
       description "Priority of the bridge (in increments of 4k - 4k,8k,..60k)";
       type string {
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses mstp-interface;
     }
     list msti {
       key name;
       description "Per-MSTI options";
       leaf name {
         type union {
           type string {
             pattern "<.*>|$.*";
           }
           type int32 {
             range "1 .. 4094";
           }
         }
       }
       uses apply-advanced;
       leaf bridge-priority {
         description "Priority of the bridge (in increments of 4k - 0,4k,8k,..60k)";
         type string {
         }
       }
       leaf backup-bridge-priority {
         description "Priority of the bridge (in increments of 4k - 4k,8k,..60k)";
         type string {
         }
       }
       leaf-list vlan {
         ordered-by user;
         description "VLAN ID or VLAN ID range [1..4094]";
         type string;
       }
       list interface {
         key name;
         description "Interface options";
         uses mstp-interface;
       }
     }
   }
   grouping juniper-protocols-mvpn {
     description "BGP-MVPN configuration";
     uses apply-advanced;
     container traceoptions {
       description "Trace options for BGP-MVPN";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "nlri" {
               description "Trace MVPN advertisements";
             }
             enum "topology" {
               description "Trace MVPN topology changes";
             }
             enum "tunnel" {
               description "Trace provider tunnel events";
             }
             enum "umh" {
               description "Trace Upstream Multicast Hop (UMH) events";
             }
             enum "intra-as-ad" {
               description "Trace MVPN intra-AS auto discovery routes";
             }
             enum "inter-as-ad" {
               description "Trace MVPN inter-AS auto discovery routes";
             }
             enum "spmsi-ad" {
               description "Trace MVPN SPMSI auto discovery routes";
             }
             enum "leaf-ad" {
               description "Trace MVPN leaf auto discovery routes";
             }
             enum "source-active" {
               description "Trace MVPN source active routes";
             }
             enum "cmcast-join" {
               description "Trace MVPN c-multicast join routes";
             }
             enum "mdt-safi-ad" {
               description "Trace MVPN MDT SAFI auto discovery routes";
             }
             enum "mvpn-limit" {
               description "Trace MVPN spmsi and cmcast limit events";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container autodiscovery-only {
       description "Use MVPN exclusively for PE router autodiscovery";
       status deprecated;
       uses apply-advanced;
       container intra-as {
         description "Intra-AS autodiscovery options";
         uses apply-advanced;
         leaf inclusive {
           description "Inclusive provider tunnel autodiscovery";
           type empty;
           mandatory true;
         }
       }
     }
     container family {
       description "BGP-MVPN address family";
       uses apply-advanced;
       container any {
         presence "enable any";
         description "BGP-MVPN properties for all families";
         uses apply-advanced;
         leaf disable {
           description "Disable all families";
           type empty;
         }
       }
       container inet {
         description "IPv4 BGP-MVPN properties";
         uses apply-advanced;
         container autodiscovery-only {
           description "Use MVPN exclusively for PE router autodiscovery";
           uses apply-advanced;
           container intra-as {
             description "Intra-AS autodiscovery options";
             uses apply-advanced;
             leaf inclusive {
               description "Inclusive provider tunnel autodiscovery";
               type empty;
               mandatory true;
             }
           }
         }
         leaf disable {
           description "Disable family IPv4";
           type empty;
         }
       }
       container inet6 {
         presence "enable inet6";
         description "IPv6 BGP-MVPN properties";
         uses apply-advanced;
         container autodiscovery-only {
           description "Use MVPN exclusively for PE router autodiscovery";
           uses apply-advanced;
           container intra-as {
             description "Intra-AS autodiscovery options";
             uses apply-advanced;
             leaf inclusive {
               description "Inclusive provider tunnel autodiscovery";
               type empty;
               mandatory true;
             }
           }
         }
         leaf disable {
           description "Disable family IPv6";
           type empty;
         }
       }
     }
     choice sender-receiver-site-choice {
       case case_1 {
         leaf receiver-site {
           description "MVPN instance has sites only with multicast receivers";
           type empty;
         }
       }
       case case_2 {
         leaf sender-site {
           description "MVPN instance has sites only with multicast sources";
           type empty;
         }
       }
     }
     leaf unicast-umh-election {
       description "Upstream Multicast Hop election based on unicast route preference";
       type empty;
     }
     container static-umh {
       description "Upstream Multicast Hop election based on static configuration";
       uses apply-advanced;
       leaf primary {
         description "Primary Upstream Multicast Hop";
         type jt:ipv4addr;
         mandatory true;
       }
       leaf backup {
         description "Secondary Upstream Multicast Hop";
         type jt:ipv4addr;
       }
       choice source-tree_choice {
         case case_1 {
           leaf source-tree {
             description "Mandatory attribute - static-umh applies only to MVPN source-tree c-multicast joins";
             type empty;
           }
         }
       }
     }
     leaf cmcast-joins-limit-inet {
       description "Maximum number of cmcast entries for v4";
       type union {
         type string {
           pattern "<.*>|$.*";
         }
         type uint32 {
           range "0 .. 15000";
         }
       }
     }
     leaf cmcast-joins-limit-inet6 {
       description "Maximum number of cmcast entries for v6";
       type union {
         type string {
           pattern "<.*>|$.*";
         }
         type uint32 {
           range "0 .. 15000";
         }
       }
     }
     container mvpn-mode {
       description "MVPN mode of operation";
       uses apply-advanced;
       choice mode {
         case case_1 {
           container rpt-spt {
             presence "enable rpt-spt";
             description "MVPN works in multicast RPT and SPT mode";
             uses apply-advanced;
             leaf spt-switch-timer {
               description "Timeout before a PE router switches between RPT and SPT";
               units "seconds";
               type union {
                 type string {
                   pattern "<.*>|$.*";
                 }
                 type uint32 {
                   range "0 .. 60";
                 }
               }
             }
           }
         }
         case case_2 {
           container spt-only {
             presence "enable spt-only";
             description "MVPN works in multicast SPT only mode (default mode)";
             uses apply-advanced;
             container source-active-advertisement {
               description "Attributes associated with advertising Source-Active A-D routes";
               uses apply-advanced;
               leaf dampen {
                 description "Time to wait before re-advertising source-active route";
                 units "minutes";
                 type union {
                   type string {
                     pattern "<.*>|$.*";
                   }
                   type uint32 {
                     range "1 .. 30";
                   }
                 }
               }
               leaf min-rate {
                 description "Minimum traffic rate required to advertise Source-Active route";
                 units "bits per second";
                 type string;
                 mandatory true;
               }
             }
             leaf convert-sa-to-msdp {
               description "Turn on MVPN SA route to MSDP SA conversion";
               type empty;
             }
           }
         }
       }
     }
     container route-target {
       description "Configure route-targets for MVPN routes";
       uses apply-advanced;
       container import-target {
         description "Target communities used when importing routes";
         uses apply-advanced;
         container unicast {
           presence "enable unicast";
           description "Use the same target community as configured for unicast";
           choice receiver-sender-target-choice {
             case case_1 {
               leaf receiver {
                 description "Target community used when importing receiver site routes";
                 type empty;
               }
             }
             case case_2 {
               leaf sender {
                 description "Target community used when importing sender site routes";
                 type empty;
               }
             }
           }
         }
         container target {
           presence "enable target";
           description "Target community";
           leaf target-value {
             type string {
             }
           }
           choice receiver-sender-target-choice {
             case case_1 {
               leaf receiver {
                 description "Target community used when importing receiver site routes";
                 type empty;
               }
             }
             case case_2 {
               leaf sender {
                 description "Target community used when importing sender site routes";
                 type empty;
               }
             }
           }
         }
       }
       container export-target {
         description "Target communities used when exporting routes";
         uses apply-advanced;
         leaf unicast {
           description "Use the same target community as configured for unicast";
           type empty;
         }
         leaf target {
           description "Target community";
           type string {
           }
         }
       }
     }
     container mvpn-join-load-balance {
       description "MVPN Join Load Balancing Algorithm";
       uses apply-advanced;
       choice algorithm {
         case case_1 {
           container bytewise-xor-hash {
             presence "enable bytewise-xor-hash";
             description "Upstream selection using bytewise XOR hash";
           }
         }
       }
     }
     container hot-root-standby {
       description "MVPN live-live - hot root standby";
       uses apply-advanced;
       choice tree {
         case case_1 {
           container source-tree {
             presence "enable source-tree";
             description "MVPN live-live - hot root standby for source tree";
           }
         }
       }
       container min-rate {
         description "Minimum traffic rate for the provider tunnel below which switchover is initiated (in bps)";
         uses apply-advanced;
         leaf rate {
           description "Minium traffic rate for the provider tunnel below which switchover is initiated (in bps)";
           units "bits per second";
           type string;
         }
         leaf revert-delay {
           description "Time to delay updating of multicast routes to allow for multicast convergence";
           units "seconds";
           type union {
             type string {
               pattern "<.*>|$.*";
             }
             type uint32 {
               range "0 .. 600";
             }
           }
           mandatory true;
         }
         leaf ipmsi-min-rate {
           description "Separate minimum rate for the inclusive provider tunnel (in bps)";
           units "bits per second";
           type string;
         }
       }
     }
     container inter-region-template {
       description "MVPN inter-region tunnel mapping template";
       uses apply-advanced;
       list template {
         key name;
         ordered-by user;
         description "Define a inter-region template";
         leaf name {
           description "MVPN Template Name";
           type string;
         }
         uses apply-advanced;
         list region {
           key name;
           ordered-by user;
           description "BGP peer group names used as region";
           leaf name {
             description "Region name";
             type string;
           }
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
                 uses apply-advanced;
                 leaf root-address {
                   description "Non default loopback address";
                   type jt:ipaddr;
                 }
               }
             }
             case case_3 {
               container ingress-replication {
                 description "Ingress replication tunnel";
                 uses apply-advanced;
                 leaf create-new-ucast-tunnel {
                   description "Create new unicast tunnel for ingress replication";
                   type empty;
                 }
                 leaf transport-class {
                   description "Transport class this LSP belongs to";
                   type string {
                   }
                 }
                 container unicast-tunnel-name-regular-expression {
                   presence "enable unicast-tunnel-name-regular-expression";
                   description "Regular exppression for unicast tunnel name to match with RSVP tunnel LSP name";
                   uses apply-advanced;
                   leaf regular-expression {
                     description "Regular Expression";
                     type string {
                     }
                   }
                   leaf preferred {
                     description "Fall-back to default behavior of selecting active LSP";
                     type empty;
                   }
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
         container all-regions {
           description "Used for all regions not specified";
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
                 uses apply-advanced;
                 leaf root-address {
                   description "Non default loopback address";
                   type jt:ipaddr;
                 }
               }
             }
             case case_3 {
               container ingress-replication {
                 description "Ingress replication tunnel";
                 uses apply-advanced;
                 leaf create-new-ucast-tunnel {
                   description "Create new unicast tunnel for ingress replication";
                   type empty;
                 }
                 leaf transport-class {
                   description "Transport class this LSP belongs to";
                   type string {
                   }
                 }
                 container unicast-tunnel-name-regular-expression {
                   presence "enable unicast-tunnel-name-regular-expression";
                   description "Regular exppression for unicast tunnel name to match with RSVP tunnel LSP name";
                   uses apply-advanced;
                   leaf regular-expression {
                     description "Regular Expression";
                     type string {
                     }
                   }
                   leaf preferred {
                     description "Fall-back to default behavior of selecting active LSP";
                     type empty;
                   }
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
       }
     }
     leaf source-redundancy {
       description "Assume all the sources for a particular group is sending same data";
       type empty;
     }
     container umh-selection-additional-input {
       description "Additional parameters to consider during UMH";
       uses apply-advanced;
       leaf source-active-preference {
         description "Use the preference set in the source active route";
         type empty;
       }
       leaf tunnel-status {
         description "Use the RSVP or LDP tunnel status";
         type empty;
       }
     }
   }
   grouping juniper-protocols-mvrp {
     description "MVRP Configuration";
     uses apply-advanced;
     container traceoptions {
       description "Tracing options for MVRP";
       uses mrp-trace-options;
     }
     leaf join-timer {
       description "Join timer interval";
       default "200";
       units "milliseconds";
       type union {
         type string {
           pattern "<.*>|$.*";
         }
         type uint16 {
           range "100 .. 500";
         }
       }
     }
     leaf leave-timer {
       description "Leave timer interval";
       default "800";
       units "milliseconds";
       type union {
         type string {
           pattern "<.*>|$.*";
         }
         type uint16 {
           range "300 .. 1000";
         }
       }
     }
     leaf leaveall-timer {
       description "Leaveall timer interval";
       default "10";
       units "seconds";
       type union {
         type string {
           pattern "<.*>|$.*";
         }
         type uint16 {
           range "10 .. 60";
         }
       }
     }
     leaf no-dynamic-vlan {
       description "Disable dynamic VLAN creation";
       type empty;
     }
     leaf no-attribute-length-in-pdu {
       description "No attribute length while sending pdu ";
       type empty;
     }
     leaf bpdu-destination-mac-address {
       description "Destination MAC address in the MVRP BPDUs";
       type enumeration {
         enum "provider-bridge-group" {
           description "802.1ad provider bridge group address";
         }
       }
     }
     list interface {
       key name;
       ordered-by user;
       description "Configure interface options";
       leaf name {
         description "Interface name";
         type union {
           type jt:interface-device;
           type string {
             pattern "<.*>|$.*";
           }
         }
       }
       uses apply-advanced;
       leaf join-timer {
         description "Join timer interval";
         units "milliseconds";
         type union {
           type string {
             pattern "<.*>|$.*";
           }
           type uint16 {
             range "100 .. 500";
           }
         }
       }
       leaf leave-timer {
         description "Leave timer interval";
         units "milliseconds";
         type union {
           type string {
             pattern "<.*>|$.*";
           }
           type uint16 {
             range "300 .. 1000";
           }
         }
       }
       leaf leaveall-timer {
         description "Leaveall timer interval";
         units "seconds";
         type union {
           type string {
             pattern "<.*>|$.*";
           }
           type uint16 {
             range "10 .. 60";
           }
         }
       }
       leaf point-to-point {
         description "Port is point to point";
         type empty;
       }
       leaf registration {
         description "Registration mode";
         default "normal";
         type enumeration {
           enum "normal" {
             description "Normal registration mode";
           }
           enum "restricted" {
             description "Restricted registration mode";
           }
           enum "forbidden" {
             description "Forbidden registration mode";
           }
         }
       }
     }
   }
   grouping juniper-protocols-ospf {
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         type string;
       }
       container spf-options {
         description "Configure options for SPF";
         uses apply-advanced;
         container microloop-avoidance {
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
         container multipath {
           description "Configure multipath options";
           uses apply-advanced;
           container weighted {
             description "Weighted multipath options";
             uses apply-advanced;
             leaf one-hop {
               description "Enable load balancing on onehop multipath based on interface bandwidth";
               type empty;
             }
           }
         }
       }
       container backup-spf-options {
         description "Configure options for backup SPF";
         uses apply-advanced;
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           type empty;
         }
         leaf disable {
           description "Do not run backup SPF";
           type empty;
         }
         leaf no-install {
           description "Do not install backup nexthops into the RIB";
           type empty;
         }
         leaf downstream-paths-only {
           description "Use only downstream backup paths";
           type empty;
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       container microloop-avoidance {
         description "Configure microloop avoidance mechanism";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
       container multipath {
         description "Configure multipath options";
         uses apply-advanced;
         container weighted {
           description "Weighted multipath options";
           uses apply-advanced;
           leaf one-hop {
             description "Enable load balancing on onehop multipath based on interface bandwidth";
             type empty;
           }
         }
       }
     }
     container backup-spf-options {
       description "Configure options for backup SPF";
       uses apply-advanced;
       container remote-backup-calculation {
         presence "enable remote-backup-calculation";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         description "Calculate post-convergence backup paths";
         uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         type empty;
       }
       leaf disable {
         description "Do not run backup SPF";
         type empty;
       }
       leaf no-install {
         description "Do not install backup nexthops into the RIB";
         type empty;
       }
       leaf downstream-paths-only {
         description "Use only downstream backup paths";
         type empty;
       }
       container per-prefix-calculation {
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         type empty;
       }
       leaf l3-unicast-topology {
         description "Download IGP topology into TED";
         type empty;
       }
       container ignore-lsp-metrics {
         presence "enable ignore-lsp-metrics";
         description "Ignore label-switched path metrics when doing shortcuts";
         uses apply-advanced;
         leaf unconfigured-only {
           description "Ignore lsp metrics for unconfigured only";
           type empty;
         }
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         uses apply-advanced;
         leaf always {
           description "Advertise TE parameters in TE LSAs";
           type empty;
         }
       }
       container tunnel-source-protocol {
         description "Protocols from which to pick label-switched paths";
         uses apply-advanced;
         container rsvp {
           presence "enable rsvp";
           description "Pick label-switched paths from rsvp";
           uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           uses apply-advanced;
           leaf preference {
             description "Preference for label-switched paths from this protocol";
             type union {
               type string {
                 pattern "<.*>|$.*";
               }
               type uint32 {
                 range "1 .. 255";
               }
             }
           }
         }
       }
     }
     leaf flex-algorithm-preference {
       description "Preference of flex-algorithm L-OSPF routes";
       type union {
         type uint32;
         type string {
           pattern "<.*>|$.*";
         }
       }
     }
     container source-packet-routing {
       presence "enable source-packet-routing";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         description "Set the SRGB global block in SPRING";
         leaf start-label {
           description "Start range for SRGB label block";
           type union {
             type string {
               pattern "<.*>|$.*";
             }
             type uint32;
           }
           mandatory true;
         }
         leaf index-range {
           description "Index to the SRGB start label block";
           type union {
             type string {
               pattern "<.*>|$.*";
             }
             type uint32;
           }
           mandatory true;
         }
       }
       leaf mapping-server {
         description "Mapping server name";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
       leaf strict-asla-based-flex-algorithm {
         description "Flex-Algorithm to ignore links not having ASLA sub-TLVs";
         type empty;
       }
       container sensor-based-stats {
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                   mandatory true;
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
       }
       list sham-link-remote {
         key name;
         ordered-by user;
         description "Configure parameters for remote sham link endpoint";
         leaf name {
           description "Remote sham link endpoint address";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf keychain {
           description "Key chain name";
           type string {
             length "1 .. 128";
           }
         }
       }
       list interface {
         key name;
         ordered-by user;
         description "Include an interface in this area";
         leaf name {
           description "Interface name";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               type jt:ipv4addr;
             }
           }
         }
         leaf secondary {
           description "Treat interface as secondary";
           type empty;
         }
         leaf own-router-lsa {
           description "Generate a separate router LSA for this interface";
           type empty;
         }
         container bandwidth-based-metrics {
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
               mandatory true;
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "1 .. 255000";
                 }
               }
               mandatory true;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           type empty;
         }
         leaf no-advertise-adjacency-segment {
           description "Do not advertise an adjacency segment for this interface";
           type empty;
         }
         list neighbor {
           key name;
           ordered-by user;
           description "NBMA neighbor";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           type empty;
         }
         container post-convergence-lfa {
           presence "enable post-convergence-lfa";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           description "Configure ipv4 adjacency segment";
           uses apply-advanced;
           container protected {
             description "Adjacency SID is eligible for protection";
             uses apply-advanced;
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             uses apply-advanced;
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           leaf name {
             description "Address of neighbor";
             type jt:ipaddr;
           }
           uses apply-advanced;
           container ipv4-adjacency-segment {
             description "Configure ipv4 adjacency segment";
             uses apply-advanced;
             container protected {
               description "Adjacency SID is eligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               uses apply-advanced;
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container normalize {
             description "Normalize Measured Link Delay";
             leaf interval {
               description "The value of the normalized interval in microseconds.";
               units "microseconds";
               type union {
                 type string {
                   pattern "<.*>|$.*";
                 }
                 type uint32 {
                   range "1 .. 5000000";
                 }
               }
               mandatory true;
             }
             leaf offset {
               description "The value of the normalized offset in microseconds (Must be < normalized interval).";
               units "microseconds";
               type union {
                 type string {
                   pattern "<.*>|$.*";
                 }
                 type uint32 {
                   range "1 .. 5000000";
                 }
               }
               mandatory true;
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               type union {
                 type string {
                   pattern "<.*>|$.*";
                 }
                 type uint32 {
                   range "1 .. 4294967295";
                 }
               }
             }
             leaf-list admin-group {
               ordered-by user;
               description "Administrative groups for this attribute-group";
               type string;
               max-elements 16;
             }
             leaf delay-metric {
               description "Delay metric for this attribute-group";
               units "microseconds";
               type union {
                 type string {
                   pattern "<.*>|$.*";
                 }
                 type uint32 {
                   range "0 .. 16777215";
                 }
               }
             }
             leaf advertise-interface-delay {
               description "Use interface specific static/dynamic delay values as applicable in ASLA Sub-TLVs";
               type empty;
             }
             container application {
               description "Standard Applications part of this attribute-group";
               uses apply-advanced;
               leaf flex-algorithm {
                 description "Set X flag in standard application bit mask";
                 type empty;
               }
             }
           }
         }
       }
       leaf no-context-identifier-advertisement {
         description "Disable context identifier advertisments in this area";
         type empty;
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
                 mandatory true;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         leaf name {
           description "Context identifier";
           type jt:ipv4addr;
         }
         uses apply-advanced;
       }
       list label-switched-path {
         key name;
         ordered-by user;
         description "Configuration for advertisement of a label-switched path";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
                 mandatory true;
               }
             }
           }
         }
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "traffic-statistics" {
               description "Trace Segment Routing Traffic Statistics";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         type string;
       }
       leaf inet3 {
         description "Name of the IPv4/v6 inet.3 routing table group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
         mandatory true;
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-protocols-pgm {
     uses apply-advanced;
     container traceoptions {
       description "PGM trace options";
       uses apply-advanced;
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "state" {
               description "Trace state transitions";
             }
             enum "packets" {
               description "Trace packet processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
   }
   grouping juniper-protocols-pim {
     uses apply-advanced;
     leaf protocol-instance-name {
       description "Name of protocol instance under routing instance";
       type string;
     }
     container family {
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
     }
     choice enable-disable {
       case case_1 {
         leaf disable {
           description "Disable PIM";
           type empty;
         }
       }
     }
     container nonstop-routing {
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         leaf name {
           description "Group address or range to forward in dense mode";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           type jt:ipprefix;
         }
         uses apply-advanced;
         container wildcard-source {
           presence "enable wildcard-source";
           description "Select RPF for (*,g) and unspecified (s,g) joins";
           uses apply-advanced;
           leaf next-hop {
             description "Next-hop address";
             type jt:ipaddr;
             mandatory true;
           }
         }
         list source {
           key name;
           ordered-by user;
           description "IP prefix of one or more multicast sources";
           leaf name {
             description "IP prefix of source";
             type jt:ipprefix;
           }
           uses apply-advanced;
           leaf next-hop {
             description "Next-hop address";
             type jt:ipaddr;
             mandatory true;
           }
         }
       }
       list prefix-list {
         key name;
         ordered-by user;
         description "Multicast group prefix list";
         leaf name {
           description "Name of prefix list to match against";
           type string;
         }
         uses apply-advanced;
         container wildcard-source {
           presence "enable wildcard-source";
           description "Select RPF for (*,g) and unspecified (s,g) joins";
           uses apply-advanced;
           leaf next-hop {
             description "Next-hop address";
             type jt:ipaddr;
             mandatory true;
           }
         }
         list source {
           key name;
           ordered-by user;
           description "IP prefix of one or more multicast sources";
           leaf name {
             description "IP prefix of source";
             type jt:ipprefix;
           }
           uses apply-advanced;
           leaf next-hop {
             description "Next-hop address";
             type jt:ipaddr;
             mandatory true;
           }
         }
       }
     }
     container mvpn {
       presence "enable mvpn";
       description "PIM MVPN control-plane options";
       uses apply-advanced;
       container autodiscovery {
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             type empty;
           }
           container autodiscovery {
             description "PE router autodiscovery options for SSM MDTs";
             uses apply-advanced;
             leaf inet-mdt {
               description "MDT-SAFI PE autodiscovery for SSM MDTs";
               type empty;
             }
           }
           leaf disable {
             description "Disable family IPv4";
             type empty;
           }
         }
       }
     }
     container rib-group {
       description "Routing table group";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         leaf name {
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         type union {
           type string {
             pattern "<.*>|$.*";
           }
           type uint32 {
             range "1 .. 100";
           }
         }
       }
       leaf log-interval {
         description "Time between successive log messages";
         type union {
           type string {
             pattern "<.*>|$.*";
           }
           type uint32 {
             range "1 .. 65535";
           }
         }
       }
     }
     container rp {
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           description "Bootstrap address family";
           container inet {
             description "IPv4 bootstrap properties";
             uses pim_bootstrap_options_type;
           }
         }
       }
       container register-limit {
         description "Set limit on incoming registers that create (S,G) state";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           description "Group address range for which this router can be an RP (IPv4 only)";
           leaf name {
             type jt:ipv4prefix;
           }
           uses apply-advanced;
         }
         leaf override {
           description "Static RP mapping will take precedence over dynamic";
           type empty;
         }
         container family {
           description "Local RP address family";
           container inet {
             description "IPv4 local RP properties";
             uses apply-advanced;
             leaf address {
               description "Local RP address";
               type jt:ipv4addr;
               mandatory true;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   description "IPv4 address of one or more remote anycast RPs";
                   leaf name {
                     description "IPv4 address of remote anycast RP";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
         }
       }
       container auto-rp {
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
           }
           leaf override {
             description "Static RP mapping will take precedence over dynamic";
             type empty;
           }
         }
       }
       leaf register-probe-time {
         description "Register probe time";
         default "5";
         units "seconds";
         type union {
           type string {
             pattern "<.*>|$.*";
           }
           type uint32 {
             range "5 .. 60";
           }
         }
       }
     }
     leaf passive {
       description "Configure PIM protocol in passive mode";
       type empty;
     }
     list interface {
       key name;
       ordered-by user;
       description "PIM interface options";
       leaf name {
         description "Interface name";
         type string;
       }
       uses apply-advanced;
       container family {
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
       }
       choice enable-disable {
         case case_1 {
           leaf disable {
             description "Disable PIM on this interface";
             type empty;
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
           }
           enum "bidirectional-sparse-dense" {
             description "Bidirectional-sparse-dense mode";
           }
         }
       }
       leaf priority {
         description "Hello option DR priority";
         type union {
           type string {
             pattern "<.*>|$.*";
           }
           type uint32 {
             range "0 .. 4294967295";
           }
         }
       }
       container stickydr {
         presence "enable stickydr";
         description "Make DR sticky";
         uses apply-advanced;
       }
       container multiple-triggered-joins {
         presence "enable multiple-triggered-joins";
         description "Send multiple pim triggered joins in quick intervals";
         uses apply-advanced;
         leaf count {
           description "Set number of triggered joins to be sent";
           default "2";
           type union {
             type string {
               pattern "<.*>|$.*";
             }
             type uint16 {
               range "2 .. 15";
             }
           }
         }
         leaf interval {
           description "Set interval between multiple triggered joins to be sent in milliseconds";
           default "100";
           type union {
             type string {
               pattern "<.*>|$.*";
             }
             type uint16 {
               range "100 .. 1000";
             }
           }
         }
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         description "Configure PIM Dual DR";
         uses apply-advanced;
         leaf enhanced {
           description "Enable enhanced PIM Dual DR";
           type empty;
         }
       }
       leaf distributed-dr {
         description "PIM Distributed DR";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       leaf control-driven-sg {
         description "Build forwarding states from PIM sg join";
         type empty;
       }
       leaf disable-packet-register {
         description "Disable PIM packet registers on first hop router";
         type empty;
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             type jt:ipprefix;
           }
           uses apply-advanced;
           list source {
             key name;
             ordered-by user;
             description "IP prefix of one or more multicast sources ";
             leaf name {
               description "IP prefix of source";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     container cluster-id {
       description "Configure pim Cluster indentifier";
       leaf identifier {
         description "PIM Cluster identifier";
         type union {
           type string {
             pattern "<.*>|$.*";
           }
           type uint32 {
             range "1 .. 4294967295";
           }
         }
         mandatory true;
       }
       leaf private-tlv {
         description "Use cluster-id private tlv for inter-op purpose";
         type empty;
         mandatory true;
       }
     }
     container hello-options {
       description "Configure PIM hello options attributes";
       uses apply-advanced;
       leaf disable-interface-id-tlv {
         description "Disable interface-id TLV in PIM hellos";
         type empty;
       }
     }
     container hash-based-rpf-selection {
       presence "enable hash-based-rpf-selection";
       description "Configure PIM hash based rpf selection";
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     leaf control-driven-sg {
       description "Build forwarding states from PIM sg join";
       type empty;
     }
     leaf disable-packet-register {
       description "Disable PIM packet registers on first hop router";
       type empty;
     }
     container default-vpn-source {
       presence "enable default-vpn-source";
       description "Let all VRFs use master loopback address for mt interfaces";
       uses apply-advanced;
       leaf interface-name {
         description "Master loopback interface name";
         type union {
           type jt:interface-unit;
           type string {
             pattern "<.*>|$.*";
           }
         }
       }
     }
     container static {
       description "Static PIM Join";
       uses apply-advanced;
       leaf distributed {
         description "Distributed all PIM Joins";
         type empty;
       }
       list group {
         key name;
         ordered-by user;
         description "IP multicast group address";
         leaf name {
           description "IP multicast group address";
           type jt:ipaddr;
         }
         uses apply-advanced;
         leaf distributed {
           description "Distributed static group";
           type empty;
         }
         list source {
           key name;
           ordered-by user;
           description "IP multicast source address";
           leaf name {
             description "IP multicast source address";
             type jt:ipaddr;
           }
           uses apply-advanced;
           leaf distributed {
             description "Distributed static source";
             type empty;
           }
           leaf no-upstream-join {
             description "Prevent sending PIM join";
             type empty;
           }
         }
       }
     }
   }
   grouping juniper-protocols-protection-group {
     uses apply-advanced;
     container traceoptions {
       description "Tracing options for debugging protocol operation";
       uses erp-trace-options;
     }
     leaf restore-interval {
       description "Wait to restore interval";
       default "5";
       units "minutes";
       type union {
         type string {
           pattern "<.*>|$.*";
         }
         type uint32 {
           range "1 .. 12";
         }
       }
     }
     leaf guard-interval {
       description "Guard timer interval in 10ms steps";
       default "500";
       units "milliseconds";
       type union {
         type string {
           pattern "<.*>|$.*";
         }
         type uint32 {
           range "10 .. 2000";
         }
       }
     }
     leaf hold-interval {
       description "Hold off timer interval in 100ms steps";
       default "0";
       units "milliseconds";
       type union {
         type string {
           pattern "<.*>|$.*";
         }
         type uint32 {
           range "0 .. 10000";
         }
       }
     }
     list ethernet-ring {
       key name;
       ordered-by user;
       description "Ethernet ring";
       uses juniper-protocols-protection-group-ethernet-ring;
     }
   }
   grouping erp-trace-options {
     description "Trace options for Ethernet Ring Protocol";
     uses apply-advanced;
     list flag {
       key name;
       ordered-by user;
       description "Tracing parameters";
       leaf name {
         type enumeration {
           enum "events" {
             description "Trace events to the protocol state machine";
           }
           enum "pdu" {
             description "Trace R-APS PDU reception and transmission";
           }
           enum "timers" {
             description "Trace protocol timers";
           }
           enum "state-machine" {
             description "Trace R-APS state machine";
           }
           enum "periodic-packet-management" {
             description "Trace periodic packet management state and events";
           }
           enum "config" {
             description "Trace protocol configuration";
           }
           enum "normal" {
             description "Trace protocol general log messages";
           }
           enum "debug" {
             description "Trace protocol debug log messages";
           }
           enum "all" {
             description "Trace all";
           }
         }
       }
     }
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
   }
   grouping juniper-protocols-protection-group-ethernet-ring {
     description "Ethernet Ring protection group configuration";
     leaf name {
       description "Name of Ethernet Ring protection group";
       type string {
         length "1 .. 32";
       }
     }
     uses apply-advanced;
     leaf node-id {
       description "Node ID of the protection group, by default bridge's MAC";
       type jt:mac-unicast;
     }
     leaf ring-protection-link-owner {
       description "Ring protection link owner flag, one ring should have only one node as a ring protection link owner";
       type empty;
     }
     leaf level {
       description "MPG Level value for R-APS PDU";
       type union {
         type string {
           pattern "<.*>|$.*";
         }
         type uint32 {
           range "0 .. 7";
         }
       }
     }
     leaf restore-interval {
       description "Wait to restore interval";
       units "minutes";
       type union {
         type string {
           pattern "<.*>|$.*";
         }
         type uint32 {
           range "1 .. 12";
         }
       }
     }
     leaf guard-interval {
       description "Guard timer interval in 10ms";
       units "milliseconds";
       type union {
         type string {
           pattern "<.*>|$.*";
         }
         type uint32 {
           range "10 .. 2000";
         }
       }
     }
     leaf hold-interval {
       description "Hold off timer interval in 100ms steps";
       units "milliseconds";
       type union {
         type string {
           pattern "<.*>|$.*";
         }
         type uint32 {
           range "0 .. 10000";
         }
       }
     }
     leaf non-revertive {
       description "Non-revertive mode of operation";
       type empty;
     }
     leaf wait-to-block-interval {
       description "Wait to block interval";
       default "5";
       units "seconds";
       type union {
         type string {
           pattern "<.*>|$.*";
         }
         type uint32 {
           range "5 .. 10";
         }
       }
     }
     leaf major-ring-name {
       description "Name of major-ring to which this sub-ring node attached";
       type string {
         length "1 .. 32";
       }
     }
     leaf propagate-tc {
       description "Enable Topology Change Propagation to major-ring from the sub-ring";
       type empty;
     }
     leaf compatibility-version {
       description "G.8032 compatibility version";
       default "2";
       type union {
         type string {
           pattern "<.*>|$.*";
         }
         type uint32 {
           range "1 .. 2";
         }
       }
     }
     leaf ring-id {
       description "Ethernet Ring ID of protection group";
       default "1";
       type union {
         type string {
           pattern "<.*>|$.*";
         }
         type uint32 {
           range "1 .. 239";
         }
       }
     }
     leaf non-vc-mode {
       description "Node is operating in non virtual channel mode";
       type empty;
     }
     leaf dot1p-priority {
       description "IEEE 802.1p priority of transmitted R-APS";
       default "0";
       type union {
         type string {
           pattern "<.*>|$.*";
         }
         type uint32 {
           range "0 .. 7";
         }
       }
     }
     container east-interface {
       description "East interface configuration";
       presence "enable east-interface";
       uses erp-interface;
     }
     container west-interface {
       description "West interface configuration";
       presence "enable west-interface";
       uses erp-interface;
     }
     leaf control-vlan {
       description "Dedicated VLAN identifier - VLAN id or VLAN name";
       type string;
     }
     container data-channel {
       description "Ring instance data channel";
       presence "enable data-channel";
       uses erp-data-channel;
     }
   }
   grouping erp-data-channel {
     uses apply-advanced;
     leaf-list vlan {
       ordered-by user;
       description "VLAN ID or VLAN ID range [1..4094]";
       type string;
     }
   }
   grouping erp-interface {
     uses apply-advanced;
     container control-channel {
       presence "enable control-channel";
       description "Control channel of ring port";
       uses apply-advanced;
       leaf vlan {
         description "Dedicated VLAN identifier";
         type union {
           type string {
             pattern "<.*>|$.*";
           }
           type uint16 {
             range "1 .. 4094";
           }
         }
       }
       leaf control-channel-name {
         type union {
           type jt:interface-name;
           type string {
             pattern "<.*>|$.*";
           }
         }
         mandatory true;
       }
     }
     leaf ring-protection-link-end {
       description "Port is connecting to ring protection link";
       type empty;
     }
     leaf interface-none {
       description "Port is not used";
       type empty;
     }
   }
   grouping juniper-protocols-rip {
     uses apply-advanced;
     container traceoptions {
       description "Trace options for RIP";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "auth" {
               description "Trace RIP authentication";
             }
             enum "error" {
               description "Trace RIP errors";
             }
             enum "expiration" {
               description "Trace RIP route expiration processing";
             }
             enum "holddown" {
               description "Trace RIP hold-down processing";
             }
             enum "packets" {
               description "Trace all RIP packets";
             }
             enum "request" {
               description "Trace RIP information packets";
             }
             enum "trigger" {
               description "Trace RIP triggered updates";
             }
             enum "update" {
               description "Trace RIP update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses rip_filter_obj;
         }
       }
     }
     container rib-group {
       description "Routing table group for importing RIP routes";
       uses rib_group_inet_type;
     }
     leaf metric-in {
       description "Metric value to add to incoming routes";
       type union {
         type string {
           pattern "<.*>|$.*";
         }
         type uint32 {
           range "1 .. 15";
         }
       }
     }
     container send {
       description "Configure RIP send options";
       choice send-opts {
         case case_1 {
           leaf broadcast {
             description "Broadcast RIPv2 packets (RIPv1 compatible)";
             type empty;
           }
         }
         case case_2 {
           leaf multicast {
             description "Multicast RIPv2 packets";
             type empty;
           }
         }
         case case_3 {
           leaf none {
             description "Do not send RIP updates";
             type empty;
           }
         }
         case case_4 {
           leaf version-1 {
             description "Broadcast RIPv1 packets";
             type empty;
           }
         }
       }
     }
     container receive {
       description "Configure RIP receive options";
       choice receive-opts {
         case case_1 {
           leaf both {
             description "Accept both RIPv1 and RIPv2 packets";
             type empty;
           }
         }
         case case_2 {
           leaf none {
             description "Do not receive RIP packets";
             type empty;
           }
         }
         case case_3 {
           leaf version-1 {
             description "Accept RIPv1 packets only";
             type empty;
           }
         }
         case case_4 {
           leaf version-2 {
             description "Accept only RIPv2 packets";
             type empty;
           }
         }
       }
     }
     choice check-zero-choice {
       leaf check-zero {
         description "Check reserved fields on incoming RIPv2 packets";
         type empty;
       }
       leaf no-check-zero {
         description "Don't check reserved fields on incoming RIPv2 packets";
         type empty;
       }
     }
     leaf message-size {
       description "Number of route entries per update message";
       type union {
         type string {
           pattern "<.*>|$.*";
         }
         type uint32 {
           range "25 .. 255";
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     choice authentication {
       case case_1 {
         leaf authentication-type {
           type enumeration {
             enum "none" {
               description "No authentication";
             }
             enum "simple" {
               description "Simple password authentication";
             }
             enum "md5" {
               description "MD5 authentication";
             }
           }
         }
       }
       case case_2 {
         list authentication-selective-md5 {
           key name;
           ordered-by user;
           description "MD5 authentication with one or more keys";
           leaf name {
             description "Key ID for MD5 authentication";
             type union {
               type string {
                 pattern "<.*>|$.*";
               }
               type uint32 {
                 range "0 .. 255";
               }
             }
           }
           leaf key {
             description "MD5 authentication key value";
             type jt:unreadable;
             mandatory true;
           }
           leaf start-time {
             description "Start time for key transmission (YYYY-MM-DD.HH:MM)";
             type jt:time;
           }
         }
       }
     }
     leaf authentication-key {
       description "Authentication key (password)";
       type jt:unreadable;
     }
     list group {
       key name;
       ordered-by user;
       description "Instance configuration";
       leaf name {
         description "Group name";
         type string {
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       leaf demand-circuit {
         description "Enable demand circuit on this interface";
         type empty;
       }
       leaf max-retrans-time {
         description "Maximum time to re-transmit a message in demand-circuit";
         type union {
           type string {
             pattern "<.*>|$.*";
           }
           type uint32 {
             range "5 .. 180";
           }
         }
       }
       container bfd-liveness-detection {
         description "Bidirectional Forwarding Detection options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf interface-type {
           description "Interface type for the neighbor";
           type enumeration {
             enum "p2mp" {
               description "Point-to-multipoint link";
             }
           }
         }
         leaf dynamic-peers {
           description "Learn peers dynamically on a p2mp interface";
           type empty;
         }
         list peer {
           key name;
           ordered-by user;
           description "P2MP peer";
           leaf name {
             description "Address of peer";
             type jt:ipaddr;
           }
         }
         leaf metric-in {
           description "Metric value to add to incoming routes";
           type union {
             type string {
               pattern "<.*>|$.*";
             }
             type uint32 {
               range "1 .. 15";
             }
           }
         }
         container send {
           description "Configure RIP send options";
           choice send-opts {
             case case_1 {
               leaf broadcast {
                 description "Broadcast RIPv2 packets (RIPv1 compatible)";
                 type empty;
               }
             }
             case case_2 {
               leaf multicast {
                 description "Multicast RIPv2 packets";
                 type empty;
               }
             }
             case case_3 {
               leaf none {
                 description "Do not send RIP updates";
                 type empty;
               }
             }
             case case_4 {
               leaf version-1 {
                 description "Broadcast RIPv1 packets";
                 type empty;
               }
             }
           }
         }
         container receive {
           description "Configure RIP receive options";
           choice receive-opts {
             case case_1 {
               leaf both {
                 description "Accept both RIPv1 and RIPv2 packets";
                 type empty;
               }
             }
             case case_2 {
               leaf none {
                 description "Do not receive RIP packets";
                 type empty;
               }
             }
             case case_3 {
               leaf version-1 {
                 description "Accept RIPv1 packets only";
                 type empty;
               }
             }
             case case_4 {
               leaf version-2 {
                 description "Accept only RIPv2 packets";
                 type empty;
               }
             }
           }
         }
         leaf demand-circuit {
           description "Enable demand circuit on this interface";
           type empty;
         }
         leaf max-retrans-time {
           description "Maximum time to re-transmit a msg in demand-circuit";
           type union {
             type string {
               pattern "<.*>|$.*";
             }
             type uint32 {
               range "5 .. 180";
             }
           }
         }
         choice check-zero-choice {
           leaf check-zero {
             description "Check reserved fields on incoming RIPv1 packets";
             type empty;
           }
           leaf no-check-zero {
             description "Don't check reserved fields on incoming RIPv1 packets";
             type empty;
           }
         }
         leaf any-sender {
           description "Disable strict checks on sender address";
           type empty;
         }
         leaf message-size {
           description "Number of route entries per update message";
           type union {
             type string {
               pattern "<.*>|$.*";
             }
             type uint32 {
               range "25 .. 255";
             }
           }
         }
         leaf-list import {
           ordered-by user;
           description "Import policy";
           type jt:policy-algebra;
         }
         choice authentication {
           case case_1 {
             leaf authentication-type {
               type enumeration {
                 enum "none" {
                   description "No authentication";
                 }
                 enum "simple" {
                   description "Simple password authentication";
                 }
                 enum "md5" {
                   description "MD5 authentication";
                 }
               }
             }
           }
           case case_2 {
             list authentication-selective-md5 {
               key name;
               ordered-by user;
               description "MD5 authentication with one or more keys";
               leaf name {
                 description "Key ID for MD5 authentication";
                 type union {
                   type string {
                     pattern "<.*>|$.*";
                   }
                   type uint32 {
                     range "0 .. 255";
                   }
                 }
               }
               leaf key {
                 description "MD5 authentication key value";
                 type jt:unreadable;
                 mandatory true;
               }
               leaf start-time {
                 description "Start time for key transmission (YYYY-MM-DD.HH:MM)";
                 type jt:time;
               }
             }
           }
         }
         leaf authentication-key {
           description "Authentication key (password)";
           type jt:unreadable;
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container graceful-restart {
       presence "enable graceful-restart";
       description "RIP graceful restart options";
       uses apply-advanced;
       choice enable-disable {
         case case_1 {
           leaf disable {
             description "Disable graceful restart";
             type empty;
           }
         }
       }
       leaf restart-time {
         description "Time after which RIP is declared out of restart";
         type union {
           type string {
             pattern "<.*>|$.*";
           }
           type uint32 {
             range "1 .. 600";
           }
         }
       }
     }
   }
   grouping juniper-protocols-router-discovery {
     uses apply-advanced;
     choice enable-disable {
       case case_1 {
         leaf disable {
           description "Disable router discovery";
           type empty;
         }
       }
     }
     container traceoptions {
       description "Trace options for router discovery";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     list interface {
       key name;
       ordered-by user;
       description "Interfaces on which to configure router discovery";
       leaf name {
         description "Interface name";
         type union {
           type jt:interface-name;
           type string {
             pattern "<.*>|$.*";
           }
         }
       }
       uses apply-advanced;
       leaf max-advertisement-interval {
         description "Maximum time before sending advertisements";
         units "seconds";
         type union {
           type string {
             pattern "<.*>|$.*";
           }
           type uint32 {
             range "4 .. 1800";
           }
         }
       }
       leaf min-advertisement-interval {
         description "Minimum time before sending advertisements";
         units "seconds";
         type union {
           type string {
             pattern "<.*>|$.*";
           }
           type uint32 {
             range "3 .. 1800";
           }
         }
       }
       leaf lifetime {
         description "How long addresses in advertisements are valid";
         units "seconds";
         type union {
           type string {
             pattern "<.*>|$.*";
           }
           type uint32 {
             range "3 .. 9000";
           }
         }
       }
     }
     list address {
       key name;
       ordered-by user;
       description "IP addresses to include in advertisements";
       leaf name {
         description "IP addresses to include in router advertisements";
         type jt:ipv4addr;
       }
       uses apply-advanced;
       leaf advertise {
         description "Advertise the IP address in advertisements";
         type empty;
       }
       leaf ignore {
         description "Do not advertise the IP address in advertisements";
         type empty;
       }
       leaf broadcast {
         description "Include IP address only in broadcast advertisements";
         type empty;
       }
       leaf multicast {
         description "Include IP address only in multicast advertisements";
         type empty;
       }
       leaf ineligible {
         description "IP address can never become a default router";
         type empty;
       }
       leaf priority {
         description "Preference of the address to become a default router";
         type union {
           type int32;
           type string {
             pattern "<.*>|$.*";
           }
         }
       }
     }
   }
   grouping juniper-protocols-rsvp {
     description "RSVP options";
     uses apply-advanced;
     choice enable-disable {
       case case_1 {
         leaf disable {
           description "Disable RSVP";
           type empty;
         }
       }
     }
     container graceful-restart {
       description "Configure graceful restart attributes";
       uses apply-advanced;
       choice enable-disable {
         case case_1 {
           leaf disable {
             description "Disable RSVP graceful restart capability";
             type empty;
           }
         }
       }
       leaf helper-disable {
         description "Disable graceful restart helper capability";
         type empty;
       }
       leaf maximum-helper-restart-time {
         description "Maximum wait time from down event to neighbor dead";
         default "20";
         units "seconds";
         type union {
           type string {
             pattern "<.*>|$.*";
           }
           type uint32 {
             range "1 .. 1800";
           }
         }
       }
       leaf maximum-helper-recovery-time {
         description "Maximum time restarting neighbor states are kept";
         default "180";
         units "seconds";
         type union {
           type string {
             pattern "<.*>|$.*";
           }
           type uint32 {
             range "1 .. 3600";
           }
         }
       }
     }
     container tunnel-services {
       presence "enable tunnel-services";
       description "Use tunnel services for P2MP LSP ultimate-hop popping";
       uses apply-advanced;
       leaf-list devices {
         ordered-by user;
         description "Tunnel services devices to use for P2MP LSPs";
         type union {
           type jt:interface-device;
           type string {
             pattern "<.*>|$.*";
           }
         }
       }
     }
     leaf no-p2mp-sublsp {
       description "Disable P2MP sub-LSP object generation";
       type empty;
     }
     leaf no-node-id-subobject {
       description "Do not include the node-id sub-object in the RRO";
       type empty;
     }
     leaf no-interface-hello {
       description "Disble interface Hellos on all RSVP interfaces";
       type empty;
     }
     container pop-and-forward {
       description "RSVP pop-and-forward specific global parameters";
       uses apply-advanced;
       container application-label {
         description "Number of application labels under the RSVP transport";
         uses apply-advanced;
         leaf depth {
           description "Application label depth";
           default "1";
           type union {
             type string {
               pattern "<.*>|$.*";
             }
             type uint32 {
               range "0 .. 3";
             }
           }
         }
       }
     }
     leaf hello-acknowledgements {
       description "Acknowledge Hellos on RSVP interfaces not having sessions";
       type empty;
     }
     leaf no-hello-acknowledgements {
       description "Do not ack Hellos on RSVP interfaces not having sessions";
       type empty;
     }
     container node-hello {
       presence "enable node-hello";
       description "Enable node-ID based Hellos on all RSVP interfaces";
       leaf hello-interval {
         description "Hello interval";
         default "9";
         units "seconds";
         type union {
           type string {
             pattern "<.*>|$.*";
           }
           type uint32 {
             range "0 .. 60";
           }
         }
       }
     }
     leaf no-node-hello {
       description "Disable node-ID based Hellos on the router";
       type empty;
     }
     leaf local-reversion {
       description "Enable local reversion at this Point of Local Repair";
       type empty;
     }
     leaf no-local-reversion {
       description "Disable local reversion at this Point of Local Repair";
       type empty;
     }
     leaf rfc6510-lsp-attributes {
       description "Use RFC6510 compliant LSP_ATTRIBUTES";
       type empty;
     }
     container fast-reroute {
       description "One-to-one fast-reroute protection mechanism";
       uses apply-advanced;
       leaf optimize-timer {
         description "Frequency of reoptimization for fast-reroute detour";
         units "seconds";
         type union {
           type string {
             pattern "<.*>|$.*";
           }
           type int32 {
             range "0 .. 65535";
           }
         }
       }
     }
     container load-balance {
       description "Per-packet load-balancing algorithm";
       uses apply-advanced;
       leaf bandwidth {
         description "Per-packet load balancing proportional to LSP bandwidth";
         type empty;
       }
     }
     container traceoptions {
       description "Trace options for RSVP";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "io-event" {
               description "Trace RSVP IO task related events";
             }
             enum "io-packets" {
               description "Trace all RSVP periodic refresh activity";
             }
             enum "packets" {
               description "Trace all RSVP trigger packets";
             }
             enum "path" {
               description "Trace RSVP trigger path messages";
             }
             enum "resv" {
               description "Trace RSVP trigger Resv messages";
             }
             enum "pathtear" {
               description "Trace RSVP PathTear messages";
             }
             enum "resvtear" {
               description "Trace RSVP ResvTear messages";
             }
             enum "state" {
               description "Trace state transitions";
             }
             enum "error" {
               description "Trace error conditions";
             }
             enum "route" {
               description "Trace routing information";
             }
             enum "lmp" {
               description "Trace RSVP-LMP related interactions";
             }
             enum "event" {
               description "Trace RSVP related events";
             }
             enum "nsr-synchronization" {
               description "Trace NSR synchronization events";
             }
             enum "lsp-prefix" {
               description "Prefix the trace messages with LSP information";
             }
             enum "enhanced-frr" {
               description "Enhanced FRR related information";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf refresh-time {
       description "Refresh time in seconds";
       default "1200";
       type union {
         type string {
           pattern "<.*>|$.*";
         }
         type uint32 {
           range "1 .. 65535";
         }
       }
     }
     leaf keep-multiplier {
       description "Keep multiplier";
       default "3";
       type union {
         type string {
           pattern "<.*>|$.*";
         }
         type uint32 {
           range "1 .. 255";
         }
       }
     }
     leaf graceful-deletion-timeout {
       description "Time to complete graceful deletion signaling";
       default "30";
       units "seconds";
       type union {
         type string {
           pattern "<.*>|$.*";
         }
         type uint32 {
           range "1 .. 300";
         }
       }
     }
     leaf setup-protection {
       description "Enable setup protection";
       type empty;
     }
     leaf no-p2mp-re-merge {
       description "Enable p2mp remerge";
       type empty;
     }
     leaf cross-credibility-cspf {
       description "Compute CSPF paths spanning protocols for bypass LSP, detour LSP and loose hop expansion";
       type empty;
     }
     container preemption {
       description "Set RSVP session preemption attributes";
       uses apply-advanced;
       choice preemption-type {
         case case_1 {
           leaf disabled {
             description "No RSVP session preemption";
             type empty;
           }
         }
         case case_2 {
           leaf normal {
             description "Run RSVP session preemption to accommodate new sessions";
             type empty;
           }
         }
         case case_3 {
           leaf aggressive {
             description "Run RSVP session preemption whenever necessary";
             type empty;
           }
         }
       }
       container soft-preemption {
         description "Options for establishing new path before tearing down a preempted LSP";
         uses apply-advanced;
         leaf cleanup-timer {
           description "Time a soft-preempted LSP will be maintained";
           units "seconds";
           type union {
             type string {
               pattern "<.*>|$.*";
             }
             type int32 {
               range "0 .. 10800";
             }
           }
         }
       }
     }
     leaf authentication-key {
       description "Authentication password";
       type jt:unreadable;
     }
     leaf no-authentication-check {
       description "Skip authentication check for received messages";
       type empty;
     }
     container associated-bidirectional-lsp {
       description "Set associated bidirectional LSP attributes";
       uses apply-advanced;
       leaf single-sided-provisioning {
         description "Enable unidirectional reverse LSP setup for single sided provisioned forward LSP";
         type empty;
       }
     }
     leaf no-enhanced-frr-bypass {
       description "Disable enhanced facility backup FRR";
       type empty;
     }
     leaf no-node-hello-on-bypass {
       description "Do not send NodeID hello over bypass LSP";
       type empty;
     }
     container expand-flood-reflector-hop {
       presence "enable expand-flood-reflector-hop";
       description "Control expansion of flood reflector ERO strict hops";
     }
     list interface {
       key name;
       ordered-by user;
       description "RSVP interface options";
       leaf name {
         description "Interface name";
         type union {
           type jt:interface-name;
           type string {
             pattern "<.*>|$.*";
           }
         }
       }
       uses apply-advanced;
       choice enable-disable {
         case case_1 {
           leaf disable {
             description "Disable RSVP on this interface";
             type empty;
           }
         }
       }
       leaf authentication-key {
         description "Authentication password";
         type jt:unreadable;
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container subscription {
         description "Link bandwidth percentage for RSVP reservation";
         uses subscription-type;
       }
       leaf bandwidth {
         description "Available bandwidth for the interface units bps";
         type string;
       }
       container update-threshold {
         description "Change in reserved bandwidth to trigger IGP update";
         uses apply-advanced;
         container adaptive {
           description "Tune update-threshold dynamically";
           uses apply-advanced;
           list limit {
             key name;
             description "Available Bandwidth threshold limit";
             leaf name {
               description "Upper limit of Available bandwidth for this range";
               type string;
             }
             leaf threshold-percent {
               description "Percentage change in reserved bandwidth to trigger IGP update";
               default "10.0";
               units "percent";
               type decimal64 {
                 fraction-digits 9;
                 range "0.001 .. 20";
               }
             }
             leaf threshold-value {
               description "Change in reserved bandwidth to trigger IGP update (will be capped at 20% of link BW)";
               type string;
             }
           }
         }
         leaf threshold-percent {
           description "Percentage change in reserved bandwidth to trigger IGP update";
           default "10.0";
           units "percent";
           type decimal64 {
             fraction-digits 9;
             range "0.001 .. 20";
           }
         }
         leaf threshold-value {
           description "Change in reserved bandwidth to trigger IGP update (will be capped at 20% of link BW)";
           type string;
         }
       }
       container update-threshold-max-reservable {
         description "Change in non-rsvp bandwidth to trigger IGP update ";
         uses apply-advanced;
         leaf bandwidth {
           description "Change in non-rsvp bandwidth to trigger IGP update units bps";
           type string;
         }
         leaf percent {
           description "Percentage change in max-reservable bandwidth to trigger IGP update";
           units "percent";
           type union {
             type string {
               pattern "<.*>|$.*";
             }
             type uint32 {
               range "1 .. 100";
             }
           }
         }
       }
       container non-rsvp-bandwdith {
         description "Config knobs relating to non-rsvp bandwidth";
         uses apply-advanced;
         leaf local-bw-override-threshold {
           description "Overide threshold and update local bandwidth with non-rsvp bandwidth usage";
           type empty;
         }
       }
       container link-protection {
         presence "enable link-protection";
         description "Protect traffic with a label-stacked LSP";
         uses apply-advanced;
         choice enable-disable {
           case case_1 {
             leaf disable {
               description "Disable link protection on this interface";
               type empty;
             }
           }
         }
         container bandwidth {
           description "Bandwidth for each bypass";
           uses bandwidth-type;
         }
         leaf max-bypasses {
           description "Max number of bypasses permitted for protecting this interface";
           default "1";
           type union {
             type string {
               pattern "<.*>|$.*";
             }
             type uint32 {
               range "0 .. 99";
             }
           }
         }
         leaf constraint-aware-bypass {
           description "Compute constraint aware bypass LSPs";
           type empty;
         }
         leaf subscription {
           description "Percent of bandwidth guaranteed when admitting protected LSPs into bypasses";
           default "100";
           type union {
             type string {
               pattern "<.*>|$.*";
             }
             type uint32 {
               range "1 .. 65535";
             }
           }
         }
         leaf no-node-protection {
           description "Disallow node protection on this interface";
           type empty;
         }
         leaf optimize-timer {
           description "Interval between bypass reoptimizations";
           default "0";
           units "seconds";
           type union {
             type string {
               pattern "<.*>|$.*";
             }
             type uint32 {
               range "0 .. 65535";
             }
           }
         }
         leaf class-of-service {
           description "Class of service for the bypass LSP";
           type union {
             type string {
               pattern "<.*>|$.*";
             }
             type int32 {
               range "0 .. 7";
             }
           }
         }
         leaf hop-limit {
           description "Maximum allowed router hops for bypass";
           type union {
             type string {
               pattern "<.*>|$.*";
             }
             type uint32 {
               range "2 .. 255";
             }
           }
         }
         leaf no-cspf {
           description "Disable automatic path computation";
           type empty;
         }
         leaf exclude-srlg {
           description "Exclude SRLG links";
           type empty;
         }
         container priority {
           presence "enable priority";
           description "Preemption priorities for the bypass LSP";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         list path {
           key name;
           ordered-by user;
           description "Explicit route of bypass path";
           leaf name {
             description "Address of next system in path";
             type jt:ipv4addr;
           }
           choice loose_strict_none {
             case case_1 {
               leaf loose {
                 description "Next hop might not be adjacent";
                 type empty;
               }
             }
             case case_2 {
               leaf strict {
                 description "Next hop must be adjacent";
                 type empty;
               }
             }
           }
         }
         container admin-group {
           description "Administrative group policy";
           uses admin_group_include_exclude;
         }
         list bypass {
           key name;
           ordered-by user;
           description "Bypass with specific constraints";
           leaf name {
             description "Name of bypass";
             type string {
               length "1 .. 64";
             }
           }
           uses apply-advanced;
           leaf to {
             description "Address of egress router";
             type jt:ipv4addr;
             mandatory true;
           }
           container bandwidth {
             description "Bandwidth for each bypass";
             uses bandwidth-type;
           }
           container subscription {
             description "Bandwidth percent available on bypass for protected LSPs";
             presence "enable subscription";
             uses bypass-subscription-type;
           }
           leaf description {
             description "Text description of bypass";
             type string {
               length "1 .. 80";
             }
           }
           container priority {
             presence "enable priority";
             description "Preemption priorities for bypass";
           }
           leaf setup-priority {
             description "Set-up priority";
             type union {
               type string {
                 pattern "<.*>|$.*";
               }
               type uint32 {
                 range "0 .. 7";
               }
             }
           }
           leaf reservation-priority {
             description "Reservation priority";
             type union {
               type string {
                 pattern "<.*>|$.*";
               }
               type uint32 {
                 range "0 .. 7";
               }
             }
           }
           leaf class-of-service {
             description "Class of service for the bypass LSP";
             type union {
               type string {
                 pattern "<.*>|$.*";
               }
               type int32 {
                 range "0 .. 7";
               }
             }
           }
           leaf hop-limit {
             description "Maximum allowed router hops for bypass";
             type union {
               type string {
                 pattern "<.*>|$.*";
               }
               type uint32 {
                 range "2 .. 255";
               }
             }
           }
           leaf no-cspf {
             description "Disable automatic path computation";
             type empty;
           }
           leaf exclude-srlg {
             description "Exclude SRLG links";
             type empty;
           }
           list path {
             key name;
             ordered-by user;
             description "Explicit route of bypass path";
             leaf name {
               description "Address of next system in path";
               type jt:ipv4addr;
             }
             choice loose_strict_none {
               case case_1 {
                 leaf loose {
                   description "Next hop might not be adjacent";
                   type empty;
                 }
               }
               case case_2 {
                 leaf strict {
                   description "Next hop must be adjacent";
                   type empty;
                 }
               }
             }
           }
           container admin-group {
             description "Administrative group policy";
             uses admin_group_include_exclude;
           }
         }
         container optimize {
           description "Configure compute optimization algorithm";
           uses apply-advanced;
           choice compute-algo {
             case case_1 {
               leaf bandwidth {
                 description "Compute path optimized for available bandwidth";
                 type empty;
               }
             }
           }
         }
       }
     }
     list peer-interface {
       key name;
       ordered-by user;
       description "Configuration for peer interface";
       leaf name {
         description "Name of peer interface";
         type string;
       }
       uses apply-advanced;
       choice enable-disable {
         case case_1 {
           leaf disable {
             description "Disable RSVP on this control peer";
             type empty;
           }
         }
       }
       leaf authentication-key {
         description "Authentication password";
         type jt:unreadable;
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container dynamic-bidirectional-transport {
         presence "enable dynamic-bidirectional-transport";
         description "Enable dynamic setup of bidirectional packet LSP for transporting non-packet GMPLS LSP";
         uses apply-advanced;
         leaf template {
           description "Template for the dynamic bidirectional packet LSP";
           type string {
           }
         }
       }
     }
     list lsp-set {
       key name;
       ordered-by user;
       description "Configuration for lsp set";
       leaf name {
         description "Name of lsp set";
         type string;
       }
       uses apply-advanced;
       choice enable-disable {
         case case_1 {
           leaf disable {
             description "Disable this lsp set";
             type empty;
           }
         }
       }
       container match-criteria {
         description "Match criteria for this lsp set";
         uses lsp-set-match-type;
       }
       container traceoptions {
         description "Trace options for this lsp set";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "io-event" {
                 description "Trace RSVP IO task related events";
               }
               enum "io-packets" {
                 description "Trace all RSVP periodic refresh activity";
               }
               enum "packets" {
                 description "Trace all RSVP packets";
               }
               enum "path" {
                 description "Trace RSVP path messages";
               }
               enum "resv" {
                 description "Trace RSVP Resv messages";
               }
               enum "pathtear" {
                 description "Trace RSVP PathTear messages";
               }
               enum "resvtear" {
                 description "Trace RSVP ResvTear messages";
               }
               enum "state" {
                 description "Trace state transitions";
               }
               enum "error" {
                 description "Trace error conditions";
               }
               enum "route" {
                 description "Trace routing information";
               }
               enum "lmp" {
                 description "Trace RSVP-LMP related interactions";
               }
               enum "event" {
                 description "Trace RSVP related events";
               }
               enum "nsr-synchronization" {
                 description "Trace NSR synchronization events";
               }
               enum "lsp-prefix" {
                 description "Prefix the trace messages with LSP information";
               }
               enum "enhanced-frr" {
                 description "Enhanced FRR related information";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container pixel-tracing {
       description "Always-on pixel-tracing";
       uses apply-advanced;
       choice enable-disable {
         case case_1 {
           leaf disable {
             description "Disable pixel-tracing for RSVP";
             type empty;
           }
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping bypass-subscription-type {
     uses apply-advanced;
     leaf subscription {
       description "Subscription percentage for bandwidth protection";
       default "100";
       type string;
     }
   }
   grouping juniper-protocols-stp {
     uses apply-advanced;
     choice enable-disable {
       case case_1 {
         leaf disable {
           description "Disable STP";
           type empty;
         }
       }
     }
     leaf bpdu-destination-mac-address {
       description "Destination MAC address in the spanning tree BPDUs";
       type enumeration {
         enum "provider-bridge-group" {
           description "802.1ad provider bridge group address";
         }
       }
     }
     leaf bridge-priority {
       description "Priority of the bridge (in increments of 4k - 0,4k,8k,..60k)";
       type string {
       }
     }
     leaf backup-bridge-priority {
       description "Priority of the bridge (in increments of 4k - 4k,8k,..60k)";
       type string {
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     leaf extended-system-id {
       description "Extended system identifier";
       type union {
         type string {
           pattern "<.*>|$.*";
         }
         type uint16 {
           range "0 .. 4095";
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
   }
   grouping juniper-protocols-vni-options {
     uses apply-advanced;
     list vni {
       key name;
       description "Per-vni options";
       leaf name {
         type union {
           type string {
             pattern "<.*>|$.*";
           }
           type int32 {
             range "1 .. 16777214";
           }
         }
       }
       uses apply-advanced;
       container vrf-target {
         description "VRF target community configuration";
         uses apply-advanced;
         leaf export {
           description "Target community to use when marking routes on export";
           status deprecated;
           type string {
           }
         }
         leaf community {
           description "Target community";
           type string {
           }
         }
       }
     }
   }
   grouping juniper-protocols-vstp {
     uses apply-advanced;
     choice enable-disable {
       case case_1 {
         leaf disable {
           description "Disable VSTP";
           type empty;
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     list vlan {
       key name;
       description "VLAN spanning tree options";
       leaf name {
         description "VLAN id or all";
         type string;
       }
       uses apply-advanced;
       leaf bridge-priority {
         description "Priority of the bridge (in increments of 4k - 0,4k,8k,..60k)";
         type string {
         }
       }
       leaf backup-bridge-priority {
         description "Priority of the bridge (in increments of 4k - 4k,8k,..60k)";
         type string {
         }
       }
       leaf max-age {
         description "Maximum age of received protocol bpdu";
         units "seconds";
         type union {
           type string {
             pattern "<.*>|$.*";
           }
           type uint16 {
             range "6 .. 40";
           }
         }
       }
       leaf hello-time {
         description "Time interval between configuration BPDUs";
         units "seconds";
         type union {
           type string {
             pattern "<.*>|$.*";
           }
           type uint16 {
             range "1 .. 10";
           }
         }
       }
       leaf forward-delay {
         description "Time spent in listening or learning state";
         units "seconds";
         type union {
           type string {
             pattern "<.*>|$.*";
           }
           type uint16 {
             range "4 .. 30";
           }
         }
       }
       leaf system-identifier {
         description "Sytem identifier to represent this node";
         type jt:mac-unicast;
       }
       container traceoptions {
         description "Tracing options for debugging protocol operation";
         uses stp-trace-options;
       }
       list interface {
         key name;
         description "Interface options";
         uses stp-interface;
       }
     }
     container vlan-group {
       presence "enable vlan-group";
       description "Spanning tree options for group of VLANs";
       uses apply-advanced;
       list group {
         key name;
         ordered-by user;
         description "Name if VLAN group";
         leaf name {
           description "VLAN group name";
           type string {
             length "1 .. 63";
           }
         }
         uses apply-advanced;
         leaf-list vlan {
           ordered-by user;
           description "VLAN ID or VLAN ID range [1..4094]";
           type string;
         }
         leaf bridge-priority {
           description "Priority of the bridge (in increments of 4k - 0,4k,8k,..60k)";
           type string {
           }
         }
         leaf backup-bridge-priority {
           description "Priority of the bridge (in increments of 4k - 4k,8k,..60k)";
           type string {
           }
         }
         leaf max-age {
           description "Maximum age of received protocol bpdu";
           units "seconds";
           type union {
             type string {
               pattern "<.*>|$.*";
             }
             type uint16 {
               range "6 .. 40";
             }
           }
         }
         leaf hello-time {
           description "Time interval between configuration BPDUs";
           units "seconds";
           type union {
             type string {
               pattern "<.*>|$.*";
             }
             type uint16 {
               range "1 .. 10";
             }
           }
         }
         leaf forward-delay {
           description "Time spent in listening or learning state";
           units "seconds";
           type union {
             type string {
               pattern "<.*>|$.*";
             }
             type uint16 {
               range "4 .. 30";
             }
           }
         }
         leaf system-identifier {
           description "Sytem identifier to represent this node";
           type jt:mac-unicast;
         }
         container traceoptions {
           description "Tracing options for debugging protocol operation";
           uses stp-trace-options;
         }
         list interface {
           key name;
           description "Interface options";
           uses stp-interface;
         }
       }
     }
   }
   grouping juniper-routing-options {
     uses apply-advanced;
     container logical-system-mux {
       description "Logical system control daemon information";
       uses apply-advanced;
       container traceoptions {
         description "Trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "debug" {
                 description "Trace debug-level lrmuxd activities";
               }
               enum "parse" {
                 description "Trace configuration parsing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container auto-bandwidth {
       presence "enable auto-bandwidth";
       description "Auto bandwidth";
       uses apply-advanced;
       list template {
         key name;
         ordered-by user;
         description "Auto bandwidth template";
         leaf name {
           description "Auto bandwidth template name (Maximum length 64)";
           type string {
             length "1 .. 64";
           }
         }
         uses apply-advanced;
         leaf adjust-interval {
           description "Adjust interval";
           type union {
             type string {
               pattern "<.*>|$.*";
             }
             type uint32 {
               range "30 .. 3600";
             }
           }
         }
         leaf adjust-threshold {
           description "Percentage threshhold";
           type union {
             type string {
               pattern "<.*>|$.*";
             }
             type uint32 {
               range "0 .. 100";
             }
           }
         }
         leaf statistic-collection-interval {
           description "Collection interval";
           type union {
             type string {
               pattern "<.*>|$.*";
             }
             type uint32 {
               range "10 .. 300";
             }
           }
         }
         leaf auto-bandwidth-subscription {
           description "Percentage threshhold for subscription";
           type union {
             type string {
               pattern "<.*>|$.*";
             }
             type uint32 {
               range "0 .. 200";
             }
           }
         }
       }
       container traceoptions {
         description "Trace options for sr stats";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace All";
               }
               enum "timer" {
                 description "Trace traffic recv by periodic timer";
               }
               enum "state" {
                 description "Trace state of sensor";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container backup-selection {
       presence "enable backup-selection";
       description "Backup selection options";
       uses apply-advanced;
       list destination {
         key name;
         description "IP/IPv6 prefix for which backup selection policy is configured";
         leaf name {
           description "IP/IPv6 address (and optional prefix length)";
           type jt:ipprefix-mandatory;
           mandatory true;
         }
         uses apply-advanced;
         list interface {
           key name;
           description "Primary nexthop interface for which backup selection policy is configured";
           leaf name {
             description "Interface name";
             type union {
               type jt:interface-name;
               type string {
                 pattern "<.*>|$.*";
               }
             }
           }
           uses apply-advanced;
           container admin-group {
             description "Administrative group policies for backup-selection";
             uses apply-advanced;
             leaf-list exclude {
               description "Do not use interface if any admin group available";
               type string;
             }
             leaf-list include-all {
               description "Use interface if admin groups available entirely";
               type string;
             }
             leaf-list include-any {
               description "Use interface if any admin group is available";
               type string;
             }
             leaf-list preference {
               ordered-by user;
               description "Administrative groups in descending preference order";
               type string;
             }
           }
           leaf srlg {
             description "Evaluate Shared Risk Link Group(SRLG) characteristics for backup selection";
             default "loose";
             type enumeration {
               enum "loose" {
                 description "Loose SRLG";
               }
               enum "strict" {
                 description "Strict SRLG";
               }
             }
           }
           leaf protection-type {
             description "Type of protection to be considered";
             type enumeration {
               enum "link" {
                 description "Protect the primary interface from link faults only";
               }
               enum "node" {
                 description "Protect the primary interface from node faults only";
               }
               enum "node-link" {
                 description "Protect the primary interface from either link or node faults; prefer node protection";
               }
             }
           }
           leaf downstream-paths-only {
             description "Choose only the downstream nodes for backup";
             type empty;
           }
           leaf bandwidth-greater-equal-primary {
             description "Use backup nexthop only if bandwidth is >= bandwidth of primary nexthop";
             type empty;
           }
           container backup-neighbor {
             description "Backup Neighbor ID based policies for backup selection";
             uses apply-advanced;
             leaf-list exclude {
               description "List of backup neighbors to be excluded";
               type jt:ipv4addr;
             }
             leaf-list preference {
               ordered-by user;
               description "List of backup neighbors in descending order preference";
               type jt:ipv4addr;
             }
           }
           container node {
             description "Node ID based policies for backup selection";
             uses apply-advanced;
             leaf-list exclude {
               description "List of nodes to be excluded";
               type jt:ipv4addr;
             }
             leaf-list preference {
               ordered-by user;
               description "List of nodes in the descending order of preference";
               type jt:ipv4addr;
             }
           }
           container node-tag {
             description "Node  tag policies";
             uses apply-advanced;
             leaf-list exclude {
               description "The set of node tags to be excluded";
               type union {
                 type uint32;
                 type string {
                   pattern "<.*>|$.*";
                 }
               }
             }
             leaf-list preference {
               ordered-by user;
               description "The set of node tags in the descending order of preference";
               type union {
                 type uint32;
                 type string {
                   pattern "<.*>|$.*";
                 }
               }
             }
           }
           leaf root-metric {
             description "Root metric";
             type enumeration {
               enum "lowest" {
                 description "Choose lowest root metric";
               }
               enum "highest" {
                 description "Choose highest root metric";
               }
             }
           }
           leaf dest-metric {
             description "Destination metric";
             type enumeration {
               enum "lowest" {
                 description "Choose lowest destination metric";
               }
               enum "highest" {
                 description "Choose highest destination metric";
               }
             }
           }
           leaf-list metric-order {
             ordered-by user;
             description "Metric evaluation order";
             type enumeration {
               enum "root" {
               }
               enum "dest" {
               }
             }
             max-elements 2;
           }
           leaf-list evaluation-order {
             ordered-by user;
             description "Interface policy criteria evaluation order";
             type enumeration {
               enum "admin-group" {
                 description "Administrative Group/Link Color";
               }
               enum "srlg" {
                 description "SRLG";
               }
               enum "bandwidth" {
                 description "Bandwidth";
               }
               enum "protection-type" {
                 description "Type of protection";
               }
               enum "backup-neighbor" {
                 description "Backup Neighbor";
               }
               enum "node" {
                 description "Node";
               }
               enum "node-tag" {
                 description "Node tag";
               }
               enum "metric" {
                 description "Metric related parameters";
               }
             }
           }
         }
       }
     }
     list flex-algorithm {
       key name;
       description "Configure flex-algorithms supported by this node.";
       leaf name {
         description "Algorithm id";
         type union {
           type string {
             pattern "<.*>|$.*";
           }
           type uint32 {
             range "128 .. 255";
           }
         }
       }
       uses apply-advanced;
       container definition {
         description "Configure flex-algorithm definition.";
         uses apply-advanced;
         leaf metric-type {
           type enumeration {
             enum "igp-metric" {
               description "Metric configured to be used for IGP";
             }
             enum "te-metric" {
               description "Traffic-engineering metric";
             }
             enum "delay-metric" {
               description "Min unidirectional link delay metric";
             }
           }
         }
         choice calculation-type {
           case case_1 {
             leaf spf {
               description "Normal SPF of type 0";
               type empty;
             }
           }
           case case_2 {
             leaf strict-spf {
               description "Strict SPF";
               type empty;
             }
           }
         }
         leaf use-flex-algorithm-prefix-metric {
           description "Set M flag in the flex-algorithm definition flags";
           type empty;
         }
         leaf priority {
           description "Priority of the flex-algorithm advertisement.";
           type union {
             type string {
               pattern "<.*>|$.*";
             }
             type uint32 {
               range "0 .. 255";
             }
           }
         }
         leaf-list exclude-srlg {
           ordered-by user;
           description "SRLG Name";
           type string;
           max-elements 16;
         }
         container admin-group {
           description "Administrative group policy";
           uses admin_group_include_exclude;
         }
       }
       leaf color {
         description "Color to be associated with this flex-algorithm";
         type union {
           type uint32;
           type string {
             pattern "<.*>|$.*";
           }
         }
       }
       leaf-list secondary-colors {
         description "Colors to be associated with the current flex-algorithm";
         type union {
           type uint32;
           type string {
             pattern "<.*>|$.*";
           }
         }
         max-elements 7;
       }
       container use-transport-class {
         presence "enable use-transport-class";
         description "Install ingress routes via transport class RIBs";
         uses apply-advanced;
         leaf inet3-install {
           description "Install flex-algo routes in inet{6}.3 table";
           type empty;
         }
       }
       leaf compute-igp-metric {
         description "Compute igp-metric for all routes with this flex-algorithm";
         type empty;
       }
     }
     container source-packet-routing {
       description "Source packet routing (SPRING)";
       uses apply-advanced;
       list mapping-server-entry {
         key name;
         ordered-by user;
         description "Mapping server entry";
         leaf name {
           description "Mapping server entry name";
           type string {
             length "1 .. 64";
           }
         }
         uses apply-advanced;
         list prefix-segment {
           key name;
           ordered-by user;
           description "Prefix segment";
           max-elements 256;
           leaf name {
             description "Prefix segment prefix";
             type jt:ipprefix;
           }
           uses apply-advanced;
           leaf index {
             description "Prefix segment index";
             type union {
               type string {
                 pattern "<.*>|$.*";
               }
               type uint32 {
                 range "0 .. 199999";
               }
             }
             mandatory true;
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
         list prefix-segment-range {
           key name;
           ordered-by user;
           description "Prefix segment range";
           max-elements 256;
           leaf name {
             description "Prefix segment range name";
             type string {
               length "1 .. 64";
             }
           }
           uses apply-advanced;
           leaf start-prefix {
             description "Start prefix";
             type jt:ipprefix;
             mandatory true;
           }
           leaf start-index {
             description "Start index";
             type union {
               type string {
                 pattern "<.*>|$.*";
               }
               type uint32 {
                 range "0 .. 199999";
               }
             }
             mandatory true;
           }
           leaf size {
             description "Size of prefix segment range";
             type union {
               type string {
                 pattern "<.*>|$.*";
               }
               type uint32 {
                 range "1 .. 1024";
               }
             }
             mandatory true;
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
       }
       container srv6 {
         description "SRv6 source-packet-routing";
         uses apply-advanced;
         list block {
           key name;
           ordered-by user;
           description "Block configuration options";
           leaf name {
             description "Block name";
             type string {
               length "1 .. 63";
             }
           }
           uses apply-advanced;
           leaf address {
             description "Block prefix for SRv6";
             type jt:ipv6prefix-mandatory;
             mandatory true;
           }
           container global-micro-sid {
             description "Global micro SID block range parameters";
             uses apply-advanced;
             leaf maximum-sids {
               description "Maximum number of SIDs used for global block";
               type union {
                 type string {
                   pattern "<.*>|$.*";
                 }
                 type uint32 {
                   range "0 .. 65536";
                 }
               }
             }
             leaf maximum-static-sids {
               description "Maximum number of static SIDs used for global block";
               type union {
                 type string {
                   pattern "<.*>|$.*";
                 }
                 type uint32 {
                   range "0 .. 65536";
                 }
               }
             }
           }
           container local-micro-sid {
             description "Local micro SID block range parameters";
             uses apply-advanced;
             leaf maximum-static-sids {
               description "Maximum number of static SIDs used for local block";
               type union {
                 type string {
                   pattern "<.*>|$.*";
                 }
                 type uint32 {
                   range "0 .. 65536";
                 }
               }
             }
           }
         }
         list locator {
           key name;
           ordered-by user;
           leaf name {
             description "Locator entry name";
             type string {
               length "1 .. 64";
             }
           }
           uses apply-advanced;
           leaf algorithm {
             description "Algorithm associated with this locator";
             type union {
               type string {
                 pattern "<.*>|$.*";
               }
               type uint32 {
                 range "0 .. 255";
               }
             }
           }
           leaf address {
             description "Configure Locator Service for SRv6";
             type jt:ipv6prefix;
             mandatory true;
           }
           leaf block-length {
             description "Block length associated with this locator";
             type union {
               type string {
                 pattern "<.*>|$.*";
               }
               type uint32 {
                 range "0 .. 112";
               }
             }
           }
           leaf function-length {
             description "Function length associated with this locator";
             type union {
               type string {
                 pattern "<.*>|$.*";
               }
               type uint32 {
                 range "16 .. 32";
               }
             }
           }
           leaf static-function-max-entries {
             description "Static function maximum entries";
             type union {
               type string {
                 pattern "<.*>|$.*";
               }
               type uint32 {
                 range "0 .. 4294967295";
               }
             }
           }
           container micro-sid {
             presence "enable micro-sid";
             description "Enable micro SID locator";
             uses apply-advanced;
             leaf block-name {
               description "Block name of micro SID locator";
               type string {
                 length "1 .. 63";
               }
             }
             container flavor {
               description "Flavor of micro SID locator";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
               leaf none {
                 description "No flavor";
                 type empty;
               }
             }
             leaf anycast {
               description "Anycast locator";
               type empty;
             }
             leaf node-sid {
               description "Static micro node SID";
               type empty;
             }
             list adjacency-sid {
               key name;
               description "Static micro adjacency SID";
               leaf name {
                 description "Static micro adjacency SID";
                 type union {
                   type uint32;
                   type string {
                     pattern "<.*>|$.*";
                   }
                 }
               }
               uses apply-advanced;
               list interface {
                 key name;
                 description "Interface for the adjacency SID";
                 max-elements 9;
                 leaf name {
                   description "Interface name";
                   type union {
                     type jt:interface-name;
                     type string {
                       pattern "<.*>|$.*";
                     }
                   }
                 }
                 uses apply-advanced;
                 leaf next-hop {
                   description "Next hop for adjacency SID";
                   type jt:ipv6addr;
                 }
                 leaf backup {
                   description "Marks the interface as protection for adjacency SID";
                   type empty;
                 }
               }
             }
           }
           list end-sid {
             key name;
             description "Static END SID";
             leaf name {
               description "Static END SID";
               type jt:ipv6addr;
             }
             uses apply-advanced;
             container flavor {
               presence "enable flavor";
               description "Configure END SID flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
           list end-x-sid {
             key name;
             description "Static END-X SID";
             leaf name {
               description "Static END-X SID";
               type jt:ipv6addr;
             }
             uses apply-advanced;
             list interface {
               key name;
               description "Interface for the END-X SID";
               max-elements 9;
               leaf name {
                 description "Interface name";
                 type union {
                   type jt:interface-name;
                   type string {
                     pattern "<.*>|$.*";
                   }
                 }
               }
               uses apply-advanced;
               leaf next-hop {
                 description "Next hop for END-X SID";
                 type jt:ipv6addr;
               }
               leaf backup {
                 description "Marks the interface as protection for END-X SID";
                 type empty;
               }
             }
             container flavor {
               presence "enable flavor";
               description "Configure END-X SID flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
         }
         leaf no-reduced-srh {
           description "SRv6 Encapsulation mode non reduced SRH";
           type empty;
         }
         leaf transit-srh-insert {
           description "SRv6 SRH insert mode on transit";
           type empty;
         }
         leaf no-propagate-ttl {
           description "Disable TTL propagation from IP/MPLS to SRv6 (on encap) and SRv6 to IP/MPLS (on decap)";
           type empty;
         }
         leaf icmp-tunneling {
           description "Allow SRv6 to be used for tunneling ICMP error packets";
           type empty;
         }
         container traceoptions {
           presence "enable traceoptions";
           description "Trace options for SRv6 process";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "srv6-oam-recv" {
                   description "Trace recv activity";
                 }
                 enum "srv6-oam-err" {
                   description "Trace error activity";
                 }
               }
             }
           }
         }
         container oam {
           description "OAM options";
           uses apply-advanced;
           container traceoptions {
             description "Trace options for MPLSOAM process";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 units "bytes";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "pipe" {
                     description "Trace pipe activity";
                   }
                   enum "rpc-packet-details" {
                     description "Trace SRv6 RPC packet details";
                   }
                   enum "database" {
                     description "Trace SRv6 database activity";
                   }
                   enum "network" {
                     description "Trace SRv6 network activity";
                   }
                   enum "traceroute" {
                     description "Trace SRv6 traceroute activity";
                   }
                   enum "all" {
                     description "Trace everything";
                   }
                 }
               }
             }
           }
         }
       }
     }
     leaf route-distinguisher-id {
       description "Identifier used in route distinguishers for routing instances";
       type jt:ipv4addr;
     }
     list domain-path-id {
       key name;
       ordered-by user;
       description "VRF domain id path configuration";
       max-elements 2;
       uses domain-id-type;
     }
     list rib {
       key name;
       description "Routing table options";
       leaf name {
         description "Routing table name";
         type string;
       }
       uses apply-advanced;
       container static {
         description "Static routes";
         uses apply-advanced;
         leaf rib-group {
           description "Routing table group";
           type string;
         }
         container defaults {
           description "Global route options";
           uses apply-advanced;
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           leaf explicit-null {
             description "Allows service label to be popped and will lookup nexthop-table inet6.0";
             type empty;
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         list route {
           key name;
           description "Static route";
           leaf name {
             type jt:ipprefix;
           }
           uses apply-advanced;
           leaf priority {
             description "Static route priority high/medium/low";
             type enumeration {
               enum "medium" {
                 description "Static route medium priority";
               }
               enum "low" {
                 description "Static route low priority";
               }
               enum "high" {
                 description "Static route high priority";
               }
             }
           }
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           leaf description {
             description "Static route description";
             type string {
             }
           }
           list qualified-next-hop {
             key name;
             ordered-by user;
             description "Next hop with qualifiers";
             uses qualified_nh_obj;
           }
           leaf backup-pe-group {
             description "Multicast source redundancy group";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf inline-disable {
               description "Disable inline mode for this BFD session";
               type empty;
             }
             leaf pdu-size {
               description "BFD transport protocol payload size";
               default "24";
               type union {
                 type string {
                   pattern "<.*>|$.*";
                 }
                 type uint32 {
                   range "24 .. 16000";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             container echo {
               description "Echo mode parameters";
               uses apply-advanced;
               leaf minimum-interval {
                 description "Minimum transmit and receive interval";
                 units "milliseconds";
                 type union {
                   type string {
                     pattern "<.*>|$.*";
                   }
                   type uint32 {
                     range "100 .. 255000";
                   }
                 }
                 mandatory true;
               }
             }
             container echo-lite {
               description "Echo-lite more parameters";
               uses apply-advanced;
               leaf minimum-interval {
                 description "Minimum transmit and receive interval";
                 units "milliseconds";
                 type union {
                   type string {
                     pattern "<.*>|$.*";
                   }
                   type uint32 {
                     range "1 .. 255000";
                   }
                 }
                 mandatory true;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           leaf explicit-null {
             description "Allows service label to be popped and will lookup nexthop-table inet6.0";
             type empty;
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
           list lsp-next-hop {
             key name;
             ordered-by user;
             description "LSP next hop";
             uses lsp_nh_obj;
           }
           container spring-te-lsp-next-hop {
             description "SPRING-TE LSP next hop";
             uses springte_lsp_nh_obj;
           }
           container p2mp-ldp-next-hop {
             description "Point-to-multipoint LDP LSP next hop";
             uses p2mp_ldp_lsp_nh_obj;
           }
         }
         leaf protocol-instance-name {
           description "Name of protocol instance under routing instance";
           type string;
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list route-target-filter {
           key name;
           description "Route-target-filter route";
           leaf name {
             type string {
               length "1 .. 47";
             }
           }
           uses apply-advanced;
           leaf autonomous-system {
             description "BGP AS for filter, overriding global configuration";
             type string {
             }
           }
           leaf-list community {
             ordered-by user;
             description "BGP community identifier";
             type jt:community;
           }
           leaf-list neighbor {
             ordered-by user;
             description "BGP peers for filter";
             type jt:ipaddr-scoped;
           }
           leaf-list group {
             ordered-by user;
             description "BGP groups for filter";
             type string;
           }
           leaf local {
             description "Locally originated filter";
             type empty;
           }
         }
         list route-target-community-filter {
           key name;
           description "Route-target-filter communites";
           leaf name {
             type string;
           }
           uses apply-advanced;
           leaf autonomous-system {
             description "BGP AS for filter, overriding global configuration";
             type string {
             }
           }
           leaf-list community {
             ordered-by user;
             description "BGP community identifier";
             type jt:community;
           }
           leaf-list neighbor {
             ordered-by user;
             description "BGP peers for filter";
             type jt:ipaddr-scoped;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
               mandatory true;
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
               mandatory true;
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
           mandatory true;
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
         leaf preserve-nexthop-hierarchy {
           description "Force multipath to create List nexthop";
           type empty;
         }
       }
       container policy-multipath {
         description "Policy based multipath";
         uses apply-advanced;
         leaf-list policy {
           ordered-by user;
           description "Import policy to create policy based multipath";
           type jt:policy-algebra;
         }
         container traceoptions {
           description "Trace options";
           uses apply-advanced;
           container file {
             description "Trace file options";
             leaf filename {
               description "Name of file in which to write trace information";
               type string {
                 length "1 .. 1024";
               }
               mandatory true;
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Policy-multipath route tracing.";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         leaf preserve-nexthop-hierarchy {
           description "Enable preserved nexthop hierarchy";
           type empty;
         }
       }
       container protect {
         description "Protocol-independent protection";
         leaf core {
           description "Protect against unreachability to service-edge router";
           type empty;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container bgp-static {
         description "Routes for BGP static advertisements";
         uses apply-advanced;
         list route {
           key name;
           ordered-by user;
           description "BGP-static route";
           leaf name {
             description "IP address and optional prefix length of destination";
             type jt:ipprefix;
           }
           uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
       }
       container flow {
         description "Locally defined flow routing information";
         uses apply-advanced;
         container validation {
           description "Flow route validation options";
           presence "enable validation";
           uses flow-validation;
         }
         list route {
           key name;
           ordered-by user;
           description "Flow route";
           uses flow-route-inet6;
         }
         container interface-group {
           description "Interface-group for applying flow-spec filter";
           uses flow-interface-group;
         }
         leaf discard-action-for-unresolved-redir-addr {
           description "For action redirect IP if redirect address is unresolved install discard action filter";
           type empty;
         }
         choice per-route-accounting-choice {
           leaf per-route-accounting {
             description "Enable traffic accounting per flowspec route";
             type empty;
           }
           leaf no-per-route-accounting {
             description "Don't enable traffic accounting per flowspec route";
             type empty;
           }
         }
       }
       container rib-export {
         presence "enable rib-export";
         description "Group of routing tables to import the routes";
         uses apply-advanced;
         leaf ribexport-name {
           description "RIB export group name";
           type string;
         }
       }
       container label {
         presence "enable label";
         description "Label processing";
         uses apply-advanced;
         leaf-list allocation {
           ordered-by user;
           description "Label allocation policy";
           type jt:policy-algebra;
         }
         leaf-list substitution {
           ordered-by user;
           description "Label substitution policy";
           type jt:policy-algebra;
         }
       }
       leaf-list vpn-global-import {
         ordered-by user;
         description "Import policy for L3VPN routes to global RIB";
         type jt:policy-algebra;
       }
     }
     container label {
       presence "enable label";
       description "Label processing";
       uses apply-advanced;
       leaf-list allocation {
         ordered-by user;
         description "Label allocation policy";
         type jt:policy-algebra;
       }
       leaf-list substitution {
         ordered-by user;
         description "Label substitution policy";
         type jt:policy-algebra;
       }
     }
     leaf-list vpn-global-import {
       ordered-by user;
       description "Import policy for L3VPN routes to global RIB";
       type jt:policy-algebra;
     }
     container options {
       description "Miscellaneous options";
       uses apply-advanced;
       leaf no-send {
         description "Listen only; do not send protocol packets";
         status deprecated;
         type empty;
       }
       leaf no-resolve {
         description "Do not use DNS name resolution";
         status deprecated;
         type empty;
       }
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container resolution {
       presence "enable resolution";
       description "Route next-hop resolution options";
       uses apply-advanced;
       leaf-list tracefilter {
         ordered-by user;
         description "Filter policy";
         type jt:policy-algebra;
       }
       container traceoptions {
         description "Trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "pixel" {
                 description "Resolver pixel-tracing events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       choice preserve-nexthop-hierarchy-choice {
         leaf preserve-nexthop-hierarchy {
           description "Preserve nexthop hierarchy when installing nexthop to forwarding plane";
           type empty;
         }
         leaf no-preserve-nexthop-hierarchy {
           description "Don't preserve nexthop hierarchy when installing nexthop to forwarding plane";
           type empty;
         }
       }
       choice allow-expanded-over-compressed-choice {
         leaf allow-expanded-over-compressed {
           description "Allow resolution of expanded hierarchy over compressed";
           type empty;
         }
         leaf no-allow-expanded-over-compressed {
           description "Don't allow resolution of expanded hierarchy over compressed";
           type empty;
         }
       }
       list rib {
         key name;
         ordered-by user;
         description "Routing table resolution options";
         leaf name {
           description "Routing table name";
           type string;
         }
         uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
         leaf preserve-nexthop-hierarchy {
           description "Preserve nexthop hierarchy when installing nexthop to forwarding plane";
           type empty;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
       leaf no-policy-metric-for-non-recursive-routes {
         description "Disable metric manipulation via policy for non-recursive routes";
         type empty;
       }
       leaf disable-auto-resolve-on-scheme-changes {
         description "Manually trigger route re-resolution on Resolution Scheme changes.";
         type empty;
       }
       list scheme {
         key name;
         ordered-by user;
         description "Nexthop resolution fallback";
         leaf name {
           description "Name the resolution scheme";
           type string;
         }
         uses apply-advanced;
         leaf-list resolution-ribs {
           ordered-by user;
           description "Routing tables to use for nexthop resolution, in fallback order";
           type string;
         }
         leaf-list import-policy {
           ordered-by user;
           description "Import policy";
           type jt:policy-algebra;
         }
         leaf-list import-policy-append {
           ordered-by user;
           description "Append resolution import policy to scheme's policy list";
           type jt:policy-algebra;
         }
         leaf mapping-community {
           description "Community on route that maps to this resolution scheme";
           type string;
           mandatory true;
         }
       }
     }
     container interface-routes {
       description "Define routing table groups for interface routes";
       uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         uses apply-advanced;
         leaf-list import {
           ordered-by user;
           description "Import policy applied to secondary leaked routes";
           type jt:policy-algebra;
         }
         leaf-list import-primary {
           ordered-by user;
           description "Import policy applied to primary route";
           type jt:policy-algebra;
         }
         container export {
           description "Control exportability of local routes";
           uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     container traceoptions {
       description "Global routing protocol trace options";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "read-route" {
               description "Read route events tracing";
             }
             enum "events" {
               description "Trace-events events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container topologies {
       description "Define routing topologies";
       uses apply-advanced;
       list family {
         key name;
         ordered-by user;
         description "Address family";
         leaf name {
           type enumeration {
             enum "inet" {
               description "IPv4 family";
             }
             enum "inet6" {
               description "IPv6 family";
             }
           }
         }
         uses apply-advanced;
         list topology {
           key name;
           ordered-by user;
           description "Topology information";
           leaf name {
             description "Topology name";
             type string {
             }
           }
           uses apply-advanced;
         }
       }
     }
     leaf router-id {
       description "Router identifier";
       type jt:ipv4addr;
     }
     leaf route-distinguisher-id-use-router-id {
       description "Use Master instance Router-ID as route-distinguisher-id";
       type empty;
     }
     leaf ipv6-router-id {
       description "IPv6 router identifier";
       type string;
     }
     container graceful-restart {
       presence "enable graceful-restart";
       description "Graceful or hitless routing restart options";
       uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
     container flow {
       description "Locally defined flow routing information";
       uses apply-advanced;
       leaf firewall-install-disable {
         description "Disable installing flowspec firewall filters in dfwd ";
         type empty;
       }
       choice per-route-accounting-choice {
         leaf per-route-accounting {
           description "Enable traffic accounting per flowspec route";
           type empty;
         }
         leaf no-per-route-accounting {
           description "Don't enable traffic accounting per flowspec route";
           type empty;
         }
       }
       container validation {
         description "Flow route validation options";
         presence "enable validation";
         uses flow-validation;
       }
       container interface-group {
         description "Interface-group for applying flow-spec filter";
         uses flow-interface-group;
       }
       list route {
         key name;
         ordered-by user;
         description "Flow route";
         uses flow-route-inet;
       }
       leaf term-order {
         description "Term evaluation order for flow routes";
         type enumeration {
           enum "legacy" {
             description "Legacy term order (default)";
           }
           enum "standard" {
             description "RFC compliant term order";
           }
         }
       }
       leaf discard-action-for-unresolved-redir-addr {
         description "For action redirect IP if redirect address is unresolved install discard action filter";
         type empty;
       }
       container inet {
         presence "enable inet";
         description "Enable cumulative maximum inet paths/prefixes in flow";
         uses apply-advanced;
         container maximum-paths {
           description "Maximum number of paths";
           leaf limit {
             description "Maximum number of paths";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container maximum-prefixes {
           description "Maximum number of prefixes";
           leaf limit {
             description "Maximum number of prefixes";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       container inet6 {
         presence "enable inet6";
         description "Enable cumulative maximum inet6 paths/prefixes in flow";
         uses apply-advanced;
         container maximum-paths {
           description "Maximum number of paths";
           leaf limit {
             description "Maximum number of paths";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container maximum-prefixes {
           description "Maximum number of prefixes";
           leaf limit {
             description "Maximum number of prefixes";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       container global {
         presence "enable global";
         description "Enable cumulative maximum paths/prefixes in inet/inet6 flow";
         uses apply-advanced;
         container maximum-paths {
           description "Maximum number of paths";
           leaf limit {
             description "Maximum number of paths";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
         container maximum-prefixes {
           description "Maximum number of prefixes";
           leaf limit {
             description "Maximum number of prefixes";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     leaf no-soft-core {
       description "Disable soft assert to generate core and just log the event";
       type empty;
     }
     leaf highwatermark-log-interval {
       description "High watermark log interval (default 30 seconds)";
       units "seconds";
       type union {
         type string {
           pattern "<.*>|$.*";
         }
         type uint32 {
           range "5 .. 1200";
         }
       }
     }
     leaf time-averaged-watermark-interval {
       description "For calculating average watermark";
       units "days";
       type union {
         type string {
           pattern "<.*>|$.*";
         }
         type uint32 {
           range "1 .. 15";
         }
       }
     }
     container ppm {
       presence "enable ppm";
       description "Set periodic packet management properties";
       uses apply-advanced;
       leaf delegate-processing {
         description "Enable distribution of PPM sessions";
         status deprecated;
         type empty;
       }
       leaf no-delegate-processing {
         description "Disable PPM sessions distribution";
         type empty;
       }
       leaf bfd-redirect-rule-delay {
         description "Time to wait after installing redirect rule for BFD sessions";
         type union {
           type string {
             pattern "<.*>|$.*";
           }
           type uint32 {
             range "1 .. 120";
           }
         }
       }
       leaf redistribution-timer {
         description "Time to wait after switchover before starting timers";
         type union {
           type string {
             pattern "<.*>|$.*";
           }
           type uint32 {
             range "1 .. 120";
           }
         }
       }
     }
     leaf no-bfd-triggered-local-repair {
       description "Disable bfd triggered local repair";
       type empty;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container static {
       description "Static routes";
       uses apply-advanced;
       leaf rib-group {
         description "Routing table group";
         type string;
       }
       container defaults {
         description "Global route options";
         uses apply-advanced;
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         leaf explicit-null {
           description "Allows service label to be popped and will lookup nexthop-table inet6.0";
           type empty;
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       list route {
         key name;
         description "Static route";
         leaf name {
           type jt:ipprefix;
         }
         uses apply-advanced;
         leaf priority {
           description "Static route priority high/medium/low";
           type enumeration {
             enum "medium" {
               description "Static route medium priority";
             }
             enum "low" {
               description "Static route low priority";
             }
             enum "high" {
               description "Static route high priority";
             }
           }
         }
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         leaf description {
           description "Static route description";
           type string {
           }
         }
         list qualified-next-hop {
           key name;
           ordered-by user;
           description "Next hop with qualifiers";
           uses qualified_nh_obj;
         }
         leaf backup-pe-group {
           description "Multicast source redundancy group";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf inline-disable {
             description "Disable inline mode for this BFD session";
             type empty;
           }
           leaf pdu-size {
             description "BFD transport protocol payload size";
             default "24";
             type union {
               type string {
                 pattern "<.*>|$.*";
               }
               type uint32 {
                 range "24 .. 16000";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           container echo {
             description "Echo mode parameters";
             uses apply-advanced;
             leaf minimum-interval {
               description "Minimum transmit and receive interval";
               units "milliseconds";
               type union {
                 type string {
                   pattern "<.*>|$.*";
                 }
                 type uint32 {
                   range "100 .. 255000";
                 }
               }
               mandatory true;
             }
           }
           container echo-lite {
             description "Echo-lite more parameters";
             uses apply-advanced;
             leaf minimum-interval {
               description "Minimum transmit and receive interval";
               units "milliseconds";
               type union {
                 type string {
                   pattern "<.*>|$.*";
                 }
                 type uint32 {
                   range "1 .. 255000";
                 }
               }
               mandatory true;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         leaf explicit-null {
           description "Allows service label to be popped and will lookup nexthop-table inet6.0";
           type empty;
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
         list lsp-next-hop {
           key name;
           ordered-by user;
           description "LSP next hop";
           uses lsp_nh_obj;
         }
         container spring-te-lsp-next-hop {
           description "SPRING-TE LSP next hop";
           uses springte_lsp_nh_obj;
         }
         container p2mp-ldp-next-hop {
           description "Point-to-multipoint LDP LSP next hop";
           uses p2mp_ldp_lsp_nh_obj;
         }
       }
       leaf protocol-instance-name {
         description "Name of protocol instance under routing instance";
         type string;
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
       list route-target-filter {
         key name;
         description "Route-target-filter route";
         leaf name {
           type string {
             length "1 .. 47";
           }
         }
         uses apply-advanced;
         leaf autonomous-system {
           description "BGP AS for filter, overriding global configuration";
           type string {
           }
         }
         leaf-list community {
           ordered-by user;
           description "BGP community identifier";
           type jt:community;
         }
         leaf-list neighbor {
           ordered-by user;
           description "BGP peers for filter";
           type jt:ipaddr-scoped;
         }
         leaf-list group {
           ordered-by user;
           description "BGP groups for filter";
           type string;
         }
         leaf local {
           description "Locally originated filter";
           type empty;
         }
       }
       list route-target-community-filter {
         key name;
         description "Route-target-filter communites";
         leaf name {
           type string;
         }
         uses apply-advanced;
         leaf autonomous-system {
           description "BGP AS for filter, overriding global configuration";
           type string {
           }
         }
         leaf-list community {
           ordered-by user;
           description "BGP community identifier";
           type jt:community;
         }
         leaf-list neighbor {
           ordered-by user;
           description "BGP peers for filter";
           type jt:ipaddr-scoped;
         }
         leaf-list group {
           ordered-by user;
           description "BGP groups for filter";
           type string;
         }
         leaf local {
           description "Locally originated filter";
           type empty;
         }
       }
     }
     list martians {
       key "address choice-ident choice-value";
       ordered-by user;
       description "Invalid routes";
       uses martian_type;
     }
     container aggregate {
       description "Coalesced routes";
       uses rib_aggregate_type;
     }
     container generate {
       description "Route of last resort";
       uses rib_aggregate_type;
     }
     choice maximum-paths-type {
       case case_1 {
         container maximum-routes {
           description "Maximum number of routes";
           status deprecated;
           leaf limit {
             description "Maximum number of routes";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       case case_2 {
         container maximum-paths {
           description "Maximum number of paths";
           leaf limit {
             description "Maximum number of paths";
             type union {
               type string {
                 pattern "<.*>|$.*";
               }
               type uint32 {
                 range "1 .. 4294967295";
               }
             }
             mandatory true;
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     container maximum-prefixes {
       description "Maximum number of prefixes";
       leaf limit {
         description "Maximum number of prefixes";
         type union {
           type string {
             pattern "<.*>|$.*";
           }
           type uint32 {
             range "1 .. 4294967295";
           }
         }
         mandatory true;
       }
       choice log_type {
         case case_1 {
           leaf threshold {
             description "Percentage of limit at which to start generating warnings";
             type union {
               type string {
                 pattern "<.*>|$.*";
               }
               type uint32 {
                 range "1 .. 100";
               }
             }
           }
         }
         case case_2 {
           leaf log-only {
             description "Generate warning messages only";
             type empty;
           }
         }
       }
       leaf log-interval {
         description "Minimum interval between log messages";
         units "seconds";
         type union {
           type string {
             pattern "<.*>|$.*";
           }
           type uint32 {
             range "5 .. 86400";
           }
         }
       }
     }
     container multipath {
       presence "enable multipath";
       description "Protocol-independent load balancing";
       uses apply-advanced;
       container vpn-unequal-cost {
         presence "enable vpn-unequal-cost";
         description "Include VPN routes with unequal IGP metrics";
         leaf equal-external-internal {
           description "Include external and internal VPN routes";
           type empty;
         }
       }
       leaf as-path-compare {
         description "Compare AS path sequences in addition to AS path length";
         type empty;
       }
       leaf preserve-nexthop-hierarchy {
         description "Force multipath to create List nexthop";
         type empty;
       }
     }
     container policy-multipath {
       description "Policy based multipath";
       uses apply-advanced;
       leaf-list policy {
         ordered-by user;
         description "Import policy to create policy based multipath";
         type jt:policy-algebra;
       }
       container traceoptions {
         description "Trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Policy-multipath route tracing.";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf preserve-nexthop-hierarchy {
         description "Enable preserved nexthop hierarchy";
         type empty;
       }
     }
     container protect {
       description "Protocol-independent protection";
       leaf core {
         description "Protect against unreachability to service-edge router";
         type empty;
       }
     }
     container access {
       description "Access routes";
       uses apply-advanced;
       list route {
         key name;
         ordered-by user;
         description "Access route";
         leaf name {
           description "IP address of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
         leaf metric {
           description "Metric value";
           type union {
             type string {
               pattern "<.*>|$.*";
             }
             type uint32 {
               range "1 .. 255";
             }
           }
         }
         leaf preference {
           description "Preference value";
           type union {
             type uint32;
             type string {
               pattern "<.*>|$.*";
             }
           }
         }
         leaf tag {
           description "Tag string";
           type union {
             type uint32;
             type string {
               pattern "<.*>|$.*";
             }
           }
         }
         leaf tag2 {
           description "Tag2 string";
           type union {
             type uint32;
             type string {
               pattern "<.*>|$.*";
             }
           }
         }
       }
     }
     container access-internal {
       description "Access-internal routes";
       uses apply-advanced;
       list route {
         key name;
         ordered-by user;
         description "Access-internal route";
         leaf name {
           description "IP address and optional prefix length of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
       }
     }
     container bgp-static {
       description "Routes for BGP static advertisements";
       uses apply-advanced;
       list route {
         key name;
         ordered-by user;
         description "BGP-static route";
         leaf name {
           description "IP address and optional prefix length of destination";
           type jt:ipprefix;
         }
         uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
     }
     list rib-groups {
       key name;
       ordered-by user;
       description "Group of routing tables";
       uses rpd_rib_group_type;
     }
     container rib-exports {
       description "Group of routing tables to import the routes";
       uses apply-advanced;
       container restart-timer {
         description "Restart timer of rib-export for graceful restart";
         uses apply-advanced;
         leaf restart-timer-value {
           description "Value of restart timer";
           type union {
             type uint32;
             type string {
               pattern "<.*>|$.*";
             }
           }
         }
       }
       list rib-export-group {
         key name;
         ordered-by user;
         description "RIB export group";
         uses rpd-rib-export-group-type;
       }
     }
     leaf route-record {
       description "Enable route recording";
       type empty;
     }
     leaf-list instance-import {
       ordered-by user;
       description "Import policy for instance RIBs";
       type jt:policy-algebra;
     }
     leaf-list instance-export {
       ordered-by user;
       description "Export policy for instance RIBs";
       type jt:policy-algebra;
     }
     leaf-list pre-export-filter {
       ordered-by user;
       description "Pre-export filter for protocol export-policy";
       type jt:policy-algebra;
     }
     container auto-export {
       presence "enable auto-export";
       description "Export routes between routing instances";
       uses apply-advanced;
       choice enable-disable {
         case case_1 {
           leaf disable {
             description "Disable auto-export";
             type empty;
           }
         }
       }
       container traceoptions {
         description "Trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "export" {
                 description "Export processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container family {
         container inet {
           description "IPv4 parameters";
           uses export-af-obj;
         }
         container inet6 {
           description "IPv6 parameters";
           uses export-af-obj;
         }
         container iso {
           description "ISO parameters";
           uses export-af-obj;
         }
       }
     }
     container transport-class {
       presence "enable transport-class";
       description "Transport layer options";
       uses apply-advanced;
       leaf auto-create {
         description "Auto create on color discovery";
         type empty;
       }
       container fallback {
         description "Service routes resolution fallback";
         uses apply-advanced;
         leaf none {
           description "Resolve associated service-routes using this transport-class tunnels only";
           type empty;
         }
       }
       container ip-fabric {
         presence "enable ip-fabric";
         description "Enable ip-fabric mode";
       }
       leaf install-inet-default {
         description "Install routes by default into inet.0 instead of inet.3";
         type empty;
       }
       list name {
         key name;
         ordered-by user;
         description "Transport layer collecting Tunnels with similar characteristics";
         leaf name {
           description "Transport class name";
           type string;
         }
         uses apply-advanced;
         leaf color {
           description "Color(0..4294967295). This auto derives the Mapping Community and Route Target";
           type union {
             type uint32;
             type string {
               pattern "<.*>|$.*";
             }
           }
         }
         container fallback {
           description "Service routes resolution fallback";
           uses apply-advanced;
           leaf none {
             description "Resolve associated service-routes using this transport-class tunnels only";
             type empty;
           }
         }
         container tunnel-egress {
           description "Tunnel-Egress endpoint origination";
           uses apply-advanced;
           list end-point {
             key name;
             ordered-by user;
             description "Configure Tunnel-Egress endpoints";
             leaf name {
               description "Address of Tunnel egress endpoint";
               type jt:ipaddr;
             }
             uses apply-advanced;
             leaf-list import {
               ordered-by user;
               description "Import policy to set attributes";
               type jt:policy-algebra;
             }
           }
         }
       }
       container any-class {
         description "Predefined transport class collecting Tunnels of all transport classes";
         uses apply-advanced;
         leaf color {
           description "Color 32bit value. This auto derives the Mapping Community.";
           type union {
             type uint32;
             type string {
               pattern "<.*>|$.*";
             }
           }
         }
         container fallback {
           description "Service routes resolution fallback";
           uses apply-advanced;
           leaf none {
             description "Resolve associated service-routes using this transport-class tunnels only";
             type empty;
           }
         }
       }
       container best-effort {
         description "Best effort transport class";
         uses apply-advanced;
         leaf color {
           description "Color 32 bit value";
           type union {
             type uint32;
             type string {
               pattern "<.*>|$.*";
             }
           }
         }
         container fallback {
           description "Service routes resolution fallback";
           uses apply-advanced;
           leaf none {
             description "Resolve associated service-routes using this transport-class tunnels only";
             type empty;
           }
         }
       }
     }
     list diversity-association {
       key name;
       ordered-by user;
       description "Diversity Association Group configuration";
       leaf name {
         description "Diversity Association group name";
         type string {
           length "1 .. 64";
         }
       }
       uses apply-advanced;
       leaf group-id {
         description "Diversity Association group id";
         type union {
           type string {
             pattern "<.*>|$.*";
           }
           type uint16 {
             range "1 .. 65535";
           }
         }
       }
       leaf association-type {
         description "Association Type";
         type enumeration {
           enum "node" {
             description "Disjoint Level Node";
           }
           enum "link" {
             description "Disjoint Level Link";
           }
           enum "srlg-node" {
             description "Disjoint Level SRLG-Node";
           }
           enum "srlg-link" {
             description "Disjoint Level SRLG-Link";
           }
         }
       }
       leaf strict {
         description "Strict Disjointness";
         type empty;
       }
       leaf association-src-ipv4 {
         description "IPV4 Association Source";
         type jt:ipv4addr;
       }
       leaf association-src-ipv6 {
         description "IPV6 Association Source";
         type jt:ipv6addr;
       }
     }
     list te-policy-association {
       key name;
       ordered-by user;
       description "Policy association group configuration";
       leaf name {
         description "Policy association group name";
         type string {
           length "1 .. 64";
         }
       }
       uses apply-advanced;
       leaf group-id {
         description "Policy association group id";
         type union {
           type string {
             pattern "<.*>|$.*";
           }
           type uint16 {
             range "1 .. 65535";
           }
         }
       }
       leaf association-src-ipv4 {
         description "IPV4 association source";
         type jt:ipv4addr;
       }
       leaf association-src-ipv6 {
         description "IPV6 association source";
         type jt:ipv6addr;
       }
     }
     container dynamic-tunnels {
       description "Dynamic tunnel definitions";
       uses apply-advanced;
       list tunnel-attributes {
         key name;
         ordered-by user;
         description "Dynamic tunnel attributes definition";
         leaf name {
           description "Dynamic Tunnel attribute name";
           type string {
           }
         }
         uses apply-advanced;
         leaf dynamic-tunnel-source-prefix {
           description "Tunnel source address";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
             enum "IPIP" {
               description "Tunnel type IPIP";
             }
           }
           mandatory true;
         }
         leaf dynamic-tunnel-mtu {
           description "Dynamic Tunnel MTU value";
           type union {
             type string {
               pattern "<.*>|$.*";
             }
             type uint32 {
               range "296 .. 9232";
             }
           }
         }
         leaf dynamic-tunnel-anchor-pfe {
           description "Dynamic Tunnel anchor PFE name of format pfe-x/y/z";
           type string {
           }
         }
         leaf dynamic-tunnel-anti-spoof {
           type enumeration {
             enum "on" {
               description "Enable antispoofing check. Default is enabled";
             }
             enum "off" {
               description "Disable antispoofing check";
             }
           }
         }
         leaf dynamic-tunnel-reassembly {
           type enumeration {
             enum "on" {
               description "Enable reassembly check. Default is disabled";
             }
             enum "off" {
               description "Disable reassembly check";
             }
           }
         }
         leaf dynamic-tunnel-ttl {
           description "Dynamic Tunnel TTL value";
           type union {
             type string {
               pattern "<.*>|$.*";
             }
             type uint32 {
               range "1 .. 255";
             }
           }
         }
         leaf dynamic-tunnel-forwarding-class {
           description "Dynamic Tunnel forwarding class name";
           type string {
             length "1 .. 64";
           }
         }
         leaf dynamic-tunnel-payload-port-profile {
           description "Dynamic Tunnel UDP payload port profile";
           type string;
         }
         leaf dynamic-tunnel-propagate-dscp {
           description "Dynamic Tunnel Propagate DSCP";
           type empty;
         }
         leaf dynamic-tunnel-propagate-ecn {
           description "Dynamic Tunnel Propagate ECN";
           type empty;
         }
       }
       container forwarding-rib {
         presence "enable forwarding-rib";
         description "Forwarding routing table for dynamic-tunnel";
         uses apply-advanced;
         container inet.0 {
           presence "enable inet.0";
           description "Rib table inet.0";
           uses apply-advanced;
           leaf-list inet-import {
             ordered-by user;
             description "Import policy for V4 dynamic-tunnel";
             type jt:policy-algebra;
           }
         }
         container inet6.0 {
           presence "enable inet6.0";
           description "Rib table inet6.0";
           uses apply-advanced;
           leaf-list inet6-import {
             ordered-by user;
             description "Import policy for V6 dynamic-tunnel";
             type jt:policy-algebra;
           }
         }
       }
       container statistics {
         description "Fetch traffic statistics for  dynamic tunnels";
         uses apply-advanced;
         leaf interval {
           description "Time after which statistics has to be fetched";
           units "seconds";
           type union {
             type string {
               pattern "<.*>|$.*";
             }
             type uint16 {
               range "1 .. 65535";
             }
           }
           mandatory true;
         }
       }
       container traceoptions {
         description "Trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "tunnel-event" {
                 description "Trace create, delete, up, down event for nh based tunnel";
               }
               enum "flash-event" {
                 description "Trace flash event for tunnel forwarding route";
               }
               enum "stats-job" {
                 description "Trace taffic statistics job related stuff";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf log-updown {
         description "Logging actions for dynamic tunnel up/down events";
         type empty;
       }
       list gre {
         key name;
         ordered-by user;
         description "Enable dynamic gre tunnel mode";
         leaf name {
           description "Enable dynamic tunnel gre mode";
           type enumeration {
             enum "next-hop-based-tunnel" {
               description "Enable nh base dynamic-tunnel";
             }
             enum "full-resolved-next-hop-based-tunnel" {
               description "Enable full resolved nh base dynamic-tunnel";
             }
             enum "chain-full-resolve-next-hop-based-tunnel" {
               description "Enable chain full resolved nh base dynamic-tunnel";
             }
           }
         }
         uses apply-advanced;
       }
       list dynamic-tunnel {
         key name;
         ordered-by user;
         uses dynamic_tunnel_type;
       }
     }
     list interface {
       key name;
       ordered-by user;
       description "Direct/Host route FRR protection";
       leaf name {
         description "Interface name";
         type union {
           type jt:interface-name;
           type string {
             pattern "<.*>|$.*";
           }
         }
       }
       uses apply-advanced;
       leaf arp-prefix-limit {
         description "Max ARP/Host FRR routes allowed";
         type union {
           type string {
             pattern "<.*>|$.*";
           }
           type uint32 {
             range "1 .. 10000";
           }
         }
       }
       leaf supplementary-blackout-timer {
         description "ARP plimit blackout timer = kernel ARP timeout + supplementary-blackout-timer minutes.";
         type union {
           type string {
             pattern "<.*>|$.*";
           }
           type uint32 {
             range "1 .. 15";
           }
         }
       }
       choice protection-type {
         case case_1 {
           leaf link-protection {
             description "Protect interface from link faults only";
             type empty;
           }
         }
       }
     }
     container host-fast-reroute {
       presence "enable host-fast-reroute";
       description "Host Fast Re-route global values. Applies to all host FRR profiles.";
       uses apply-advanced;
       leaf global-arp-prefix-limit {
         description "Max ARP/Host FRR routes allowed per protected IFL";
         type union {
           type string {
             pattern "<.*>|$.*";
           }
           type uint32 {
             range "1 .. 10000";
           }
         }
       }
       leaf global-supplementary-blackout-timer {
         description "ARP plimit global blackout timer = kernel ARP timeout + global-supplementary-blackout-timer minutes.";
         type union {
           type string {
             pattern "<.*>|$.*";
           }
           type uint32 {
             range "1 .. 15";
           }
         }
       }
     }
     leaf warm-standby {
       description "Enable warm-standby";
       type empty;
     }
     leaf nonstop-routing {
       description "Enable nonstop routing";
       type empty;
     }
     container nonstop-routing-options {
       presence "enable nonstop-routing-options";
       description "Nonstop routing options";
       uses apply-advanced;
       leaf precision-timers-max-period {
         description "Set Max period for precision timer support from kernel after switchover";
         type union {
           type string {
             pattern "<.*>|$.*";
           }
           type uint32 {
             range "60 .. 1800";
           }
         }
       }
     }
     leaf nsr-phantom-holdtime {
       description "Set NSR phantom route hold time";
       type union {
         type string {
           pattern "<.*>|$.*";
         }
         type uint32 {
           range "0 .. 10000";
         }
       }
     }
     list srlg {
       key name;
       ordered-by user;
       description "SRLG configuration";
       leaf name {
         description "Group name";
         type string {
           length "1 .. 64";
         }
       }
       uses apply-advanced;
       leaf srlg-value {
         description "Group id";
         type union {
           type string {
             pattern "<.*>|$.*";
           }
           type uint32 {
             range "1 .. 4294967295";
           }
         }
       }
       leaf srlg-cost {
         description "Cost value";
         type union {
           type string {
             pattern "<.*>|$.*";
           }
           type uint32 {
             range "1 .. 65535";
           }
         }
       }
       leaf srlg-hold-down-include {
         description "Hold down include";
         type empty;
       }
       leaf srlg-hold-down-exclude {
         description "Hold down exclude";
         type empty;
       }
       leaf srlg-hold-down-interval {
         description "Hold down interval";
         type union {
           type string {
             pattern "<.*>|$.*";
           }
           type uint32 {
             range "1 .. 4294967295";
           }
         }
       }
     }
     container admin-groups-extended-range {
       description "Extended administrative groups range";
       uses apply-advanced;
       leaf minimum {
         description "Minimum value of the range for extended administrative groups";
         type union {
           type string {
             pattern "<.*>|$.*";
           }
           type uint32 {
             range "32 .. 4294967295";
           }
         }
         mandatory true;
       }
       leaf maximum {
         description "Maximum value of the range for extended administrative groups";
         type union {
           type string {
             pattern "<.*>|$.*";
           }
           type uint32 {
             range "32 .. 4294967295";
           }
         }
         mandatory true;
       }
     }
     list admin-groups-extended {
       key name;
       ordered-by user;
       description "Extended administrative groups";
       leaf name {
         description "Group name (Maximum length 64)";
         type string {
           length "1 .. 64";
         }
       }
       uses apply-advanced;
       leaf group-value {
         description "Group id";
         type union {
           type string {
             pattern "<.*>|$.*";
           }
           type uint32 {
             range "32 .. 4294967295";
           }
         }
       }
     }
     container source-routing {
       description "Source-routing options";
       uses apply-advanced;
       leaf ip {
         description "Enable IP Source Routing";
         type empty;
       }
       leaf ipv6 {
         description "Enable Type 0 RouteHeader processing";
         type empty;
       }
     }
     container forwarding-table {
       uses forwarding-table-type;
     }
     container fate-sharing {
       description "Fate-sharing links or nodes database";
       uses apply-advanced;
       list group {
         key name;
         ordered-by user;
         description "Group of objects sharing common characteristics";
         leaf name {
           description "Name of object groups sharing the same fate";
           type string {
           }
         }
         uses apply-advanced;
         leaf cost {
           description "Cost value";
           type union {
             type string {
               pattern "<.*>|$.*";
             }
             type uint32 {
               range "1 .. 65535";
             }
           }
         }
         leaf use-for-post-convergence-lfa {
           description "Use this fate-sharing group as a constraint for post-convergence-lfa";
           type empty;
         }
         list from {
           key name;
           uses fate_sharing_links;
         }
       }
     }
     container multicast {
       description "Global multicast options";
       uses apply-advanced;
       container traceoptions {
         description "Global multicast trace options";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "config-internal" {
                 description "Trace configuration internals";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf disable {
             description "Disable this trace flag";
             type empty;
           }
         }
       }
       leaf rpf {
         status deprecated;
         type string;
       }
       list scope {
         key name;
         ordered-by user;
         description "Multicast address scope";
         leaf name {
           description "Name to identify multicast address scope";
           type string;
         }
         uses apply-advanced;
         leaf prefix {
           description "Administratively scoped address";
           type jt:ipprefix;
           mandatory true;
         }
         leaf-list interface {
           ordered-by user;
           description "Interface on which to configure scoping";
           type union {
             type jt:interface-name;
             type string {
               pattern "<.*>|$.*";
             }
           }
         }
       }
       leaf-list scope-policy {
         ordered-by user;
         description "Scoping policy";
         type jt:policy-algebra;
       }
       list flow-map {
         key name;
         ordered-by user;
         description "Multicast flow map configuration";
         leaf name {
           description "Name of the flow map";
           type string;
         }
         uses apply-advanced;
         leaf-list policy {
           ordered-by user;
           description "Policy for matched flows";
           type jt:policy-algebra;
         }
         container bandwidth {
           presence "enable bandwidth";
           description "Bandwidth properties for matched flows";
           leaf bandwidth-value {
             description "Static or default bandwidth for the matched flows";
             units "bps";
             type string;
           }
           leaf adaptive {
             description "Auto-sense bandwidth for matched flows";
             type empty;
           }
         }
         leaf-list redundant-sources {
           ordered-by user;
           description "Redundant source addresses";
           type jt:ipaddr;
         }
         container forwarding-cache {
           description "Forwarding cache properties for matched flows";
           uses apply-advanced;
           container timeout {
             description "Timeout properties for matched flows";
             choice timeout_choice {
               case case_1 {
                 leaf timeout-value {
                   description "Timeout for forwarding cache entry";
                   units "minutes";
                   type union {
                     type string {
                       pattern "<.*>|$.*";
                     }
                     type uint32 {
                       range "1 .. 720";
                     }
                   }
                 }
               }
               case case_2 {
                 container never {
                   presence "enable never";
                   description "Forwarding cache entries never time out";
                   uses apply-advanced;
                   leaf non-discard-entry-only {
                     description "Apply only to non-discard entries";
                     type empty;
                   }
                 }
               }
             }
           }
         }
       }
       leaf-list resolve-filter {
         ordered-by user;
         description "Multicast resolve policy filter";
         status deprecated;
         type jt:policy-algebra;
       }
       leaf-list ssm-groups {
         ordered-by user;
         description "Source-specific multicast group ranges";
         type jt:ipprefix;
       }
       leaf cont-stats-collection-interval {
         description "IGMP/MLD continuous statistics collection interval";
         default "300";
         type union {
           type string {
             pattern "<.*>|$.*";
           }
           type uint16 {
             range "60 .. 3600";
           }
         }
       }
       leaf asm-override-ssm {
         description "Allow ASM state for SSM group ranges";
         type empty;
       }
       leaf-list rpf-check-policy {
         ordered-by user;
         description "Disable RPF check for a source group pair";
         type jt:policy-algebra;
       }
       container pim-to-igmp-proxy {
         description "PIM-to-IGMP proxy";
         uses apply-advanced;
         leaf-list upstream-interface {
           ordered-by user;
           description "Upstream interface list";
           type union {
             type jt:interface-name;
             type string {
               pattern "<.*>|$.*";
             }
           }
           max-elements 2;
         }
       }
       container pim-to-mld-proxy {
         description "PIM-to-MLD proxy";
         uses apply-advanced;
         leaf-list upstream-interface {
           ordered-by user;
           description "Upstream interface list";
           type union {
             type jt:interface-name;
             type string {
               pattern "<.*>|$.*";
             }
           }
           max-elements 2;
         }
       }
       leaf resolve-request-holdcount {
         description "Set resolve request holdcount for multicast";
         type union {
           type string {
             pattern "<.*>|$.*";
           }
           type uint32 {
             range "0 .. 256";
           }
         }
       }
       container forwarding-cache {
         description "Multicast forwarding cache";
         uses apply-advanced;
         leaf allow-maximum {
           description "Allow maximum of global and family level threshold values for suppress and reuse";
           type empty;
         }
         list family {
           key name;
           ordered-by user;
           description "Protocol family";
           leaf name {
             description "Protocol family";
             type enumeration {
               enum "inet" {
                 description "IPv4 family";
               }
               enum "inet6" {
                 description "IPv6 family";
               }
             }
           }
           uses apply-advanced;
           container threshold {
             presence "enable threshold";
             description "Multicast forwarding cache suppress threshold";
             uses apply-advanced;
             leaf suppress {
               description "Suppress threshold";
               type union {
                 type string {
                   pattern "<.*>|$.*";
                 }
                 type uint32 {
                   range "1 .. 200000";
                 }
               }
               mandatory true;
             }
             leaf reuse {
               description "Reuse threshold";
               type union {
                 type string {
                   pattern "<.*>|$.*";
                 }
                 type uint32 {
                   range "1 .. 200000";
                 }
               }
             }
             leaf mvpn-rpt-suppress {
               description "MVPN RP tree entry suppress threshold";
               type union {
                 type string {
                   pattern "<.*>|$.*";
                 }
                 type uint32 {
                   range "1 .. 200000";
                 }
               }
             }
             leaf mvpn-rpt-reuse {
               description "MVPN RP tree entry reuse threshold";
               type union {
                 type string {
                   pattern "<.*>|$.*";
                 }
                 type uint32 {
                   range "1 .. 200000";
                 }
               }
             }
             leaf log-warning {
               description "Percentage at which to start generating warnings";
               type union {
                 type string {
                   pattern "<.*>|$.*";
                 }
                 type uint32 {
                   range "1 .. 100";
                 }
               }
             }
           }
         }
         container threshold {
           description "Threshold";
           uses apply-advanced;
           leaf suppress {
             description "Suppress threshold";
             type union {
               type string {
                 pattern "<.*>|$.*";
               }
               type uint32 {
                 range "1 .. 200000";
               }
             }
             mandatory true;
           }
           leaf reuse {
             description "Reuse threshold";
             type union {
               type string {
                 pattern "<.*>|$.*";
               }
               type uint32 {
                 range "1 .. 200000";
               }
             }
           }
           leaf mvpn-rpt-suppress {
             description "MVPN RP tree entry suppress threshold";
             type union {
               type string {
                 pattern "<.*>|$.*";
               }
               type uint32 {
                 range "1 .. 200000";
               }
             }
           }
           leaf mvpn-rpt-reuse {
             description "MVPN RP tree entry reuse threshold";
             type union {
               type string {
                 pattern "<.*>|$.*";
               }
               type uint32 {
                 range "1 .. 200000";
               }
             }
           }
           leaf log-warning {
             description "Percentage at which to start generating warnings";
             type union {
               type string {
                 pattern "<.*>|$.*";
               }
               type uint32 {
                 range "1 .. 100";
               }
             }
           }
         }
         leaf timeout {
           description "Forwarding cache entry timeout in minutes";
           type union {
             type string {
               pattern "<.*>|$.*";
             }
             type uint32 {
               range "1 .. 720";
             }
           }
         }
       }
       list interface {
         key name;
         ordered-by user;
         description "Multicast interface options";
         uses multicast_interface_options_type;
       }
       list ssm-map {
         key name;
         ordered-by user;
         description "SSM map definitions";
         leaf name {
           description "SSM map name";
           type string;
         }
         uses apply-advanced;
         leaf-list policy {
           ordered-by user;
           description "Policy for matching group";
           type jt:policy-algebra;
         }
         leaf-list source {
           ordered-by user;
           description "One or more source addresses";
           type jt:ipaddr;
         }
       }
       list backup-pe-group {
         key name;
         ordered-by user;
         description "Backup PE group definitions";
         leaf name {
           description "PE group name";
           type string;
         }
         uses apply-advanced;
         leaf-list backups {
           ordered-by user;
           description "One or more IP addresses";
           type jt:ipaddr;
           max-elements 8;
         }
         leaf local-address {
           description "Address to be used as local-address for this group";
           type jt:ipaddr;
           mandatory true;
         }
       }
       leaf omit-wildcard-address {
         description "Omit wildcard source/group fields in SPMSI AD NLRI";
         type empty;
       }
       leaf local-address {
         description "Local address for PIM and MVPN sessions";
         type jt:ipv4addr;
       }
     }
     container programmable-rpd {
       description "RPD Server module management options";
       uses programmable-rpd-type;
     }
     container validation {
       description "Define Route validation";
       uses apply-advanced;
       container traceoptions {
         description "Trace options for route validation";
         uses apply-advanced;
         container file {
           description "Trace file options";
           leaf filename {
             description "Name of file in which to write trace information";
             type string {
               length "1 .. 1024";
             }
             mandatory true;
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errored packets";
               }
               enum "packets" {
                 description "Trace all I/O packets";
               }
               enum "keepalive" {
                 description "Trace keepalive packets";
               }
               enum "update" {
                 description "Trace update packets";
               }
               enum "nsr-synchronization" {
                 description "Trace NSR synchronization events";
               }
               enum "state" {
                 description "Trace state transitions";
               }
               enum "policy" {
                 description "Trace policy processing";
               }
               enum "task" {
                 description "Trace routing protocol task processing";
               }
               enum "timer" {
                 description "Trace routing protocol timer processing";
               }
               enum "client" {
                 description "Trace route validation client events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf source-file {
         description "Specify a local file to read data set";
         type string;
       }
       leaf-list notification-rib {
         ordered-by user;
         description "Define routing tables that get notified upon validation state change";
         type string;
       }
       list group {
         key name;
         description "Define a group of sessions";
         leaf name {
           description "Group name";
           type string;
         }
         uses apply-advanced;
         leaf authentication-algorithm {
           description "Authentication algorithm name";
           type enumeration {
             enum "ao" {
               description "TCP authentication option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         leaf max-sessions {
           description "Maximum connected session in this group";
           type union {
             type string {
               pattern "<.*>|$.*";
             }
             type uint32 {
               range "1 .. 63";
             }
           }
         }
         list session {
           key name;
           description "Configure a session";
           leaf name {
             type jt:ipaddr;
           }
           uses apply-advanced;
           container traceoptions {
             description "Trace options for route validation";
             uses apply-advanced;
             container file {
               description "Trace file options";
               leaf filename {
                 description "Name of file in which to write trace information";
                 type string {
                   length "1 .. 1024";
                 }
                 mandatory true;
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "error" {
                     description "Trace errored packets";
                   }
                   enum "packets" {
                     description "Trace all I/O packets";
                   }
                   enum "keepalive" {
                     description "Trace keepalive packets";
                   }
                   enum "update" {
                     description "Trace update packets";
                   }
                   enum "state" {
                     description "Trace state transitions";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf authentication-algorithm {
             description "Authentication algorithm name";
             type enumeration {
               enum "ao" {
                 description "TCP authentication option";
               }
             }
           }
           leaf tcpao-auth-mismatch {
             description "Continue without TCP-AO if any one TCP endpoint does not have TCP-AO configured";
             type enumeration {
               enum "allow-without-tcpao" {
                 description "Allow the connection establishment without TCP-AO";
               }
             }
           }
           leaf authentication-key-chain {
             description "Key chain name";
             type string {
               length "1 .. 128";
             }
           }
           leaf database {
             description "Named database in this instance to install validation entries";
             type string;
           }
           leaf refresh-time {
             description "Interval between keepalive packet transmissions";
             units "seconds";
             type union {
               type string {
                 pattern "<.*>|$.*";
               }
               type uint32 {
                 range "1 .. 1800";
               }
             }
           }
           leaf hold-time {
             description "Time after which the session is declared down.";
             units "seconds";
             type union {
               type string {
                 pattern "<.*>|$.*";
               }
               type uint32 {
                 range "10 .. 3600";
               }
             }
           }
           leaf record-lifetime {
             description "Lifetime of route validation records";
             units "seconds";
             type union {
               type string {
                 pattern "<.*>|$.*";
               }
               type uint32 {
                 range "60 .. 604800";
               }
             }
           }
           leaf preference {
             description "Preference for session establishment";
             type union {
               type string {
                 pattern "<.*>|$.*";
               }
               type uint32 {
                 range "1 .. 255";
               }
             }
           }
           leaf port {
             description "Portnumber to connect";
             type union {
               type string {
                 pattern "<.*>|$.*";
               }
               type uint16 {
                 range "1 .. 65535";
               }
             }
           }
           leaf local-address {
             type jt:ipaddr;
           }
         }
       }
       container static {
         description "Define static route validation record";
         uses apply-advanced;
         list record {
           key name;
           description "Static route validation record";
           leaf name {
             type jt:ipprefix;
           }
           uses apply-advanced;
           list maximum-length {
             key name;
             ordered-by user;
             leaf name {
               description "Maximum prefix-length for route validation record";
               type union {
                 type string {
                   pattern "<.*>|$.*";
                 }
                 type uint32 {
                   range "1 .. 128";
                 }
               }
             }
             uses apply-advanced;
             list origin-autonomous-system {
               key name;
               ordered-by user;
               leaf name {
                 description "Legitimate Origin Autonomous System";
                 type union {
                   type uint32;
                   type string {
                     pattern "<.*>|$.*";
                   }
                 }
               }
               uses apply-advanced;
               leaf validation-state {
                 description "Validation state for route validation record";
                 type enumeration {
                   enum "invalid" {
                     description "Invalid route validation state";
                   }
                   enum "valid" {
                     description "Valid route validation state";
                   }
                 }
               }
             }
           }
         }
       }
       list database {
         key name;
         description "Specify a named validation database";
         leaf name {
           description "Name of validation database";
           type string;
         }
         uses apply-advanced;
         container static {
           description "Define static route validation record";
           uses apply-advanced;
           list record {
             key name;
             description "Static route validation record";
             leaf name {
               type jt:ipprefix;
             }
             uses apply-advanced;
             list maximum-length {
               key name;
               ordered-by user;
               leaf name {
                 description "Maximum prefix-length for route validation record";
                 type union {
                   type string {
                     pattern "<.*>|$.*";
                   }
                   type uint32 {
                     range "1 .. 128";
                   }
                 }
               }
               uses apply-advanced;
               list origin-autonomous-system {
                 key name;
                 ordered-by user;
                 leaf name {
                   description "Legitimate Origin Autonomous System";
                   type union {
                     type uint32;
                     type string {
                       pattern "<.*>|$.*";
                     }
                   }
                 }
                 uses apply-advanced;
                 leaf validation-state {
                   description "Validation state for route validation record";
                   type enumeration {
                     enum "invalid" {
                       description "Invalid route validation state";
                     }
                     enum "valid" {
                       description "Valid route validation state";
                     }
                   }
                 }
               }
             }
           }
         }
       }
     }
     container congestion-protection {
       description "Configuration for Tactical Traffic Engineering";
       uses apply-advanced;
       list template {
         key name;
         ordered-by user;
         description "Network slice policy";
         max-elements 15;
         leaf name {
           description "Express Segment Template Name";
           type string;
         }
         uses apply-advanced;
         leaf statistics-collection-interval {
           description "Statistics collection interval.";
           type union {
             type uint32;
             type string {
               pattern "<.*>|$.*";
             }
           }
         }
         leaf-list policy {
           ordered-by user;
           description "Policy for matching specific prefixes for TTE";
           type jt:policy-algebra;
         }
         container high-threshold {
           description "High-threshold.";
           uses apply-advanced;
           leaf bandwidth {
             description "Percentage Maximum bandwidth";
             units "percent";
             type decimal64 {
               fraction-digits 9;
               range "0 .. 100";
             }
           }
           leaf consecutive-events {
             description "Number of consecutive threshold events before action is taken.";
             type union {
               type uint32;
               type string {
                 pattern "<.*>|$.*";
               }
             }
           }
         }
         container low-threshold {
           description "Low-threshold.";
           uses apply-advanced;
           leaf bandwidth {
             description "Percentage Minimum bandwidth";
             units "percent";
             type decimal64 {
               fraction-digits 9;
               range "0 .. 100";
             }
           }
           leaf consecutive-events {
             description "Number of consecutive threshold events before action is taken.";
             type union {
               type uint32;
               type string {
                 pattern "<.*>|$.*";
               }
             }
           }
           leaf tte-path {
             description "TTE alternate paths.";
             type enumeration {
               enum "ti-lfa" {
                 description "IGP computed TI-LFA alternate paths.";
               }
               enum "compute-service" {
                 description "TE computed alternate paths.";
               }
             }
           }
         }
       }
       list interface {
         key name;
         description "TTE interface options";
         leaf name {
           description "Interface name";
           type union {
             type jt:interface-name;
             type string {
               pattern "<.*>|$.*";
             }
           }
         }
         uses apply-advanced;
         leaf template {
           description "Template name.";
           type string;
         }
       }
       container traceoptions {
         description "Trace options for congestion protection";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             units "bytes";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "all" {
                 description "Trace everything";
               }
               enum "error" {
                 description "Trace errors";
               }
               enum "route" {
                 description "Trace route-related changes";
               }
               enum "state" {
                 description "Trace state transitions";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container server {
         description "Configuration for the TTE server";
         uses apply-advanced;
         container traceoptions {
           description "Trace options for congestion protection";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               units "bytes";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace everything";
                 }
                 enum "error" {
                   description "Trace errors";
                 }
                 enum "state" {
                   description "Trace state transitions";
                 }
                 enum "database" {
                   description "Trace database operations";
                 }
                 enum "flash" {
                   description "Trace route monitor transactions";
                 }
                 enum "japi" {
                   description "Trace JAPI transactions";
                 }
                 enum "event" {
                   description "Trace events";
                 }
                 enum "samples" {
                   description "Trace bandwidth samples";
                 }
                 enum "activation" {
                   description "Trace activation and deactivation decisions";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
     }
   }
   grouping dynamic_tunnel_type {
     description "Dynamic tunnel definition";
     leaf name {
       description "Tunnel name";
       type string {
       }
     }
     uses apply-advanced;
     leaf source-address {
       description "Tunnel source address";
       type jt:ipaddr;
     }
     choice tunnel-type {
       case case_1 {
         list rsvp-te {
           key name;
           ordered-by user;
           description "RSVP-TE point-to-point LSP";
           leaf name {
             description "Configure multiple entries for RSVP tunnel";
             type string;
           }
           uses apply-advanced;
           container label-switched-path-template {
             description "Template for dynamic point-to-point LSP parameters";
             uses apply-advanced;
             choice dynamic-template {
               case case_1 {
                 leaf template-name {
                   description "Name of point-to-point LSP template";
                   type string {
                   }
                 }
               }
               case case_2 {
                 leaf default-template {
                   description "Use default parameters";
                   type empty;
                 }
               }
             }
           }
           list destination-networks {
             key name;
             ordered-by user;
             description "Create tunnels for routes in these destination networks";
             uses app_network_type;
           }
         }
       }
       case case_2 {
         container spring-te {
           description "SPRING-TE LSP's";
           uses apply-advanced;
           leaf use-transport-class {
             description "Install dynamic-tunnel routes via transport class RIBs";
             type empty;
           }
           list source-routing-path-template {
             key name;
             ordered-by user;
             description "Template color mapping for SPRING-TE dynamic LSP parameters";
             uses spring-te-template-map;
           }
           list destination-networks {
             key name;
             ordered-by user;
             description "Create tunnels for routes in these destination networks";
             uses app_network_type;
           }
         }
       }
       case case_3 {
         leaf gre {
           description "Generic routing encapsulation type for IPv4";
           type empty;
         }
       }
       case case_4 {
       }
       case case_5 {
         leaf bgp-signal {
           description "BGP signals the encapsulation type for IPv4";
           type empty;
         }
       }
       case case_6 {
       }
       case case_7 {
       }
     }
     leaf use-transport-class {
       description "Install dynamic-tunnel routes via transport class RIBs";
       type empty;
     }
     leaf log-updown {
       description "Logging actions for dynamic tunnel up/down events";
       type empty;
     }
     list destination-networks {
       key name;
       ordered-by user;
       description "Create tunnels for routes in these destination networks";
       uses network_type;
     }
   }
   grouping app_network_type {
     leaf name {
       description "Network prefix";
       type jt:ipprefix;
     }
     uses apply-advanced;
   }
   grouping export-af-obj {
     uses apply-advanced;
     choice enable-disable {
       case case_1 {
         leaf disable {
           description "Disable auto-export for address family";
           type empty;
         }
       }
     }
     container unicast {
       description "Unicast routing information";
       presence "enable unicast";
       uses export-subaf-obj;
     }
     container multicast {
       description "Multicast routing information";
       presence "enable multicast";
       uses export-subaf-obj;
     }
     container flow {
       description "Flow routing information";
       presence "enable flow";
       uses export-subaf-obj;
     }
   }
   grouping export-subaf-obj {
     uses apply-advanced;
     choice enable-disable {
       case case_1 {
         leaf disable {
           description "Disable instance export";
           type empty;
         }
       }
     }
     leaf rib-group {
       description "Auxiliary rib-group of additional RIBs to consider";
       type string;
     }
   }
   grouping fate_sharing_links {
     leaf name {
       description "Router ID or LAN interface address";
       type jt:ipv4addr;
     }
     leaf to {
       description "Point-to-point links";
       type jt:ipv4addr;
     }
   }
   grouping flow-route-inet {
     leaf name {
       type string;
     }
     uses apply-advanced;
     leaf no-install {
       description "Don't install firewall filter in forwarding";
       type empty;
     }
     container match {
       description "Flow definition";
       uses flow-route-qualifier-inet;
     }
     container then {
       description "Actions to take for this flow";
       uses flow-route-op;
     }
   }
   grouping flow-route-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     leaf destination {
       description "Destination prefix for this traffic flow";
       type jt:ipv4prefix;
     }
     leaf source {
       description "Source prefix for this traffic flow";
       type jt:ipv4prefix;
     }
     leaf-list icmp-code {
       ordered-by user;
       description "ICMP message code";
       type string;
     }
     leaf-list icmp-type {
       ordered-by user;
       description "ICMP message type";
       type string;
     }
   }
   grouping forwarding-table-type {
     description "Forwarding table management options";
     uses apply-advanced;
     leaf oc-tlv-support {
       description "Send origin protocol and network-instance for route and stream next-hop origin protocol";
       type empty;
     }
     leaf remnant-holdtime {
       description "Time to hold inherited routes from FIB";
       type union {
         type string {
           pattern "<.*>|$.*";
         }
         type uint32 {
           range "0 .. 10000";
         }
       }
     }
     leaf send-gr-issu-message {
       description "Simulate gr-issu message reception from rpd-agent";
       type union {
         type string {
           pattern "<.*>|$.*";
         }
         type uint32 {
           range "1 .. 65535";
         }
       }
     }
     leaf chain-composite-max-label-count {
       description "Maximum labels inside chain composite for the platform.";
       type union {
         type string {
           pattern "<.*>|$.*";
         }
         type uint32 {
           range "1 .. 16";
         }
       }
     }
     leaf krt-nexthop-ack {
       description "Enable kernel nexthop ack";
       type empty;
     }
     leaf krt-nexthop-ack-timeout {
       description "Kernel nexthop ack timeout interval";
       type union {
         type string {
           pattern "<.*>|$.*";
         }
         type uint32 {
           range "1 .. 400";
         }
       }
     }
     leaf srv6-chain-merge {
       description "Enable merging of srv6 chain nexthops";
       type empty;
     }
     choice session-id-change-limiter-indirect-choice {
       leaf session-id-change-limiter-indirect {
         description "Enable indirect nexthop to limit session-id change propagation";
         type empty;
       }
       leaf no-session-id-change-limiter-indirect {
         description "Don't enable indirect nexthop to limit session-id change propagation";
         type empty;
       }
     }
     container consistency-checking {
       description "RIB/FIB consistency checking";
       status deprecated;
       uses apply-advanced;
       choice enable-disable {
         case case_1 {
           leaf enable {
             description "Enable consistency checking";
             type empty;
           }
         }
         case case_2 {
           leaf disable {
             description "Disable consistency checking";
             type empty;
           }
         }
       }
       leaf period {
         description "Periodicity of scan in seconds";
         type union {
           type string {
             pattern "<.*>|$.*";
           }
           type uint32 {
             range "30 .. 4294967295";
           }
         }
       }
       leaf threshold {
         description "Mismatch threshold until complaint";
         type union {
           type uint32;
           type string {
             pattern "<.*>|$.*";
           }
         }
       }
     }
     leaf-list export {
       ordered-by user;
       description "Export policy";
       type jt:policy-algebra;
     }
     leaf dynamic-list-next-hop {
       description "Dynamic next-hop mode for EVPN";
       type empty;
     }
     container evpn-egress-link-protection {
       presence "enable evpn-egress-link-protection";
       description "EVPN PE-CE egress link failure protection";
       uses apply-advanced;
     }
     leaf vpls-hotstandby-convergence {
       description "Enable convergence improvements for VPLS hot-standby";
       type empty;
     }
     container egress-chaining {
       description "Enable egress-chaining";
       uses apply-advanced;
       leaf spring-te {
         description "Enable egress-chaining for SPRING-TE routes";
         type empty;
       }
     }
     leaf evpn-aliasing-optimize {
       description "EVPN Aliasing convergence improvement";
       type empty;
     }
     choice indirect-next-hop-choice {
       leaf indirect-next-hop {
         description "Install indirect next hops in Packet Forwarding Engine";
         type empty;
       }
       leaf no-indirect-next-hop {
         description "Don't install indirect next hops in Packet Forwarding Engine";
         type empty;
       }
     }
     choice route-ack-converge-choice {
       leaf route-ack-converge {
         description "Enable the route ack convergence feature";
         type empty;
       }
       leaf no-route-ack-converge {
         description "Don't enable the route ack convergence feature";
         type empty;
       }
     }
     leaf long-live-ack-timer-val {
       description "Set default long live acknowledgement timer value";
       type union {
         type string {
           pattern "<.*>|$.*";
         }
         type uint32 {
           range "1 .. 65535";
         }
       }
     }
     choice pfe-install-error-choice {
       leaf pfe-install-error {
         description "Enable processing error from PFE for objects installed";
         type empty;
       }
       leaf no-pfe-install-error {
         description "Don't enable processing error from PFE for objects installed";
         type empty;
       }
     }
     list rib {
       key name;
       ordered-by user;
       status deprecated;
       leaf name {
         type string;
       }
     }
     leaf unicast-reverse-path {
       description "Unicast reverse path (RP) verification";
       type enumeration {
         enum "active-paths" {
           description "Consider active paths when performing RP verification";
         }
         enum "feasible-paths" {
           description "Consider all feasible paths for RP verification";
         }
       }
     }
     container ip-tunnel-rpf-check {
       presence "enable ip-tunnel-rpf-check";
       description "IP tunnel Reverse Path Forwarding Check";
       uses apply-advanced;
       leaf mode {
         default "strict";
         type enumeration {
           enum "strict" {
             description "Strict mode for rpf-check(Default)";
           }
           enum "loose" {
             description "Loose mode for rpf-check";
           }
         }
       }
       leaf fail-filter {
         description "Fail filter name for RPF check(family inet|inet6|any)";
         type string {
         }
       }
     }
     container fib-next-hop-split {
       description "Split nexthop to chain nexthop when installing fom rib to fib";
       uses apply-advanced;
       leaf labeled-isis {
         description "Create composite-chained nexthops for labeled ISIS routes";
         type empty;
       }
     }
     leaf multicast-composite-delete-defer-timeout {
       description "Time to defer multicast composite NH delete operation into FIB";
       type union {
         type string {
           pattern "<.*>|$.*";
         }
         type uint32 {
           range "1 .. 3600";
         }
       }
     }
   }
   grouping juniper-sampling-options {
     uses apply-advanced;
     choice enable-disable {
       case case_1 {
         leaf disable {
           description "Disable global sampling instance";
           type empty;
         }
       }
     }
     container traceoptions {
       description "Traffic sampling trace options";
       uses sampling_traceoptions_type;
     }
     container input {
       description "Traffic Sampling data acquisition";
       uses sampling_input_type;
     }
     container output {
       description "Traffic sampling data disposition";
       status deprecated;
       uses sampling_output_type;
     }
     container family {
       description "Address family of packets to sample";
       container inet {
         description "Sample IPv4 packets";
         uses apply-advanced;
         choice enable-disable {
           case case_1 {
             leaf disable {
               description "Disable sampling family inet";
               type empty;
             }
           }
         }
         container input {
           description "Settings for sampling of input packets";
           uses sampling_family_input_type;
         }
         container output {
           description "Traffic sampling data disposition";
           uses sampling_instance_inet_global_output_type;
         }
       }
       container inet6 {
         description "Sample IPv6 packets";
         uses apply-advanced;
         choice enable-disable {
           case case_1 {
             leaf disable {
               description "Disable sampling family inet6";
               type empty;
             }
           }
         }
         container input {
           description "Settings for sampling of input packets";
           uses sampling_family_input_type;
         }
         container output {
           description "Traffic sampling data disposition";
           uses sampling_family_inet6_output_type;
         }
       }
       container mpls {
         description "Sample mpls packets";
         uses apply-advanced;
         choice enable-disable {
           case case_1 {
             leaf disable {
               description "Disable sampling family mpls";
               type empty;
             }
           }
         }
         container input {
           description "Settings for sampling of input packets";
           uses sampling_family_input_type;
         }
         container output {
           description "Traffic sampling data disposition";
           uses sampling_global_mpls_output_type;
         }
       }
     }
     container jflow-service {
       description "Jflow service configuration";
       uses apply-advanced;
       container traceoptions {
         description "Jflow service trace options";
         uses jflow_service_traceoptions;
       }
     }
     container route-record {
       description "Sampling route record configuration";
       uses apply-advanced;
       container traceoptions {
         description "Sampling route record trace options";
         uses route_record_traceoptions;
       }
     }
   }
   grouping jflow_service_traceoptions {
     description "Traceoptions for jflow-service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of jflow-service to enable debuging output";
       leaf name {
         type enumeration {
           enum "parse" {
             description "Trace parsing code";
           }
           enum "rtsock" {
             description "Trace rtsock code";
           }
           enum "sm" {
             description "Trace State machine code";
           }
           enum "all" {
             description "Trace all area of jflow-service code";
           }
         }
       }
     }
   }
   grouping juniper-unified-edge-cos-options {
     uses apply-advanced;
     list classifier-profiles {
       key name;
       ordered-by user;
       description "Classifier tables for mobile subscribers (UMTS/EPS)";
       max-elements 8001;
       leaf name {
         description "Classification table name";
         type string {
         }
       }
       uses apply-advanced;
       leaf description {
         description "Text description of classifier profile";
         type string;
       }
       list qos-class-identifier {
         key name;
         ordered-by user;
         description "QCI mapping to forwarding class and loss priority";
         leaf name {
           description "Qci value";
           type union {
             type string {
               pattern "<.*>|$.*";
             }
             type uint32 {
               range "1 .. 9";
             }
           }
         }
         leaf forwarding-class {
           description "Forwarding class";
           type string {
           }
           mandatory true;
         }
         leaf loss-priority {
           description "Loss priority value";
           type enumeration {
             enum "low" {
               description "Loss priority low";
             }
             enum "high" {
               description "Loss priority high";
             }
           }
           mandatory true;
         }
       }
     }
     list gbr-bandwidth-pools {
       key name;
       ordered-by user;
       description "GBR bandwith pools configuration";
       max-elements 8001;
       leaf name {
         description "GBR Bandwidth pool name";
         type string {
         }
       }
       uses apply-advanced;
       leaf maximum-bandwidth {
         description "Bandwidth for pool";
         units "mega-bits per second";
         type union {
           type string {
             pattern "<.*>|$.*";
           }
           type uint32 {
             range "50000 .. 500000";
           }
         }
         mandatory true;
       }
       leaf downgrade-gtp-v1-gbr-bearers {
         description "Downgrade GTPv1 GBR bearer traffic class to background traffic class";
         type empty;
       }
     }
     list resource-threshold-profiles {
       key name;
       ordered-by user;
       description "Resource threshold profiles";
       max-elements 8001;
       leaf name {
         description "Resource threshold profile name";
         type string {
         }
       }
       uses apply-advanced;
       leaf description {
         description "Text description of resource threshold profile";
         type string;
       }
       container bearers-load {
         description "Number of bearers load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
             mandatory true;
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
             mandatory true;
           }
           leaf priority-level {
             description "Priority level - default 5";
             default "5";
             type union {
               type string {
                 pattern "<.*>|$.*";
               }
               type uint32 {
                 range "1 .. 15";
               }
             }
           }
         }
       }
       container memory {
         description "Memory load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
             mandatory true;
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
             mandatory true;
           }
           leaf priority-level {
             description "Priority level - default 5";
             default "5";
             type union {
               type string {
                 pattern "<.*>|$.*";
               }
               type uint32 {
                 range "1 .. 15";
               }
             }
           }
         }
       }
       container cpu {
         description "CPU load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
             mandatory true;
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
             mandatory true;
           }
           leaf priority-level {
             description "Priority level - default 5";
             default "5";
             type union {
               type string {
                 pattern "<.*>|$.*";
               }
               type uint32 {
                 range "1 .. 15";
               }
             }
           }
         }
       }
     }
     list cos-policy-profiles {
       key name;
       ordered-by user;
       description "QoS policy profile";
       max-elements 8001;
       leaf name {
         description "QoS policy profile name";
         type string {
         }
       }
       uses apply-advanced;
       leaf description {
         description "Text description of cos policy";
         type string;
       }
       container default-bearer-qci {
         description "Default bearer qci value";
         leaf qci-value {
           description "Default bearer qci value";
           type union {
             type string {
               pattern "<.*>|$.*";
             }
             type uint8 {
               range "5 .. 9";
             }
           }
           mandatory true;
         }
         leaf upgrade {
           description "Override qci value";
           type empty;
         }
         leaf reject {
           description "Reject calls with numerially lower qci";
           type empty;
         }
       }
       container allocation-retention-priority {
         description "ARP local policy";
         leaf priority-value {
           description "ARP policy configuration";
           type union {
             type string {
               pattern "<.*>|$.*";
             }
             type uint8 {
               range "1 .. 15";
             }
           }
         }
         leaf reject {
           description "Reject calls with higher priority value";
           type empty;
         }
       }
       container aggregated-qos-control {
         description "Aggregated qos control policy";
         uses apply-advanced;
         container maximum-bit-rate-uplink {
           description "Maximum bit rate uplink";
           leaf mbr-uplink {
             units "kbps";
             type union {
               type string {
                 pattern "<.*>|$.*";
               }
               type uint32 {
                 range "1 .. 1000000";
               }
             }
             mandatory true;
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 1000000";
               }
             }
             mandatory true;
           }
           leaf upgrade {
             description "Override maximum-bit-rate downlink value";
             type empty;
           }
           leaf reject {
             description "Reject calls with higher downlink maximum-bit-rate";
             type empty;
           }
         }
       }
       container pdp-qos-control {
         description "PDP qos control";
         uses apply-advanced;
         container maximum-bit-rate-uplink {
           description "Maximum bit rate uplink";
           leaf mbr-uplink {
             units "kbps";
             type union {
               type string {
                 pattern "<.*>|$.*";
               }
               type uint32 {
                 range "1 .. 10480000";
               }
             }
             mandatory true;
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 10480000";
               }
             }
             mandatory true;
           }
           leaf upgrade {
             description "Override maximum-bit-rate downlink value";
             type empty;
           }
           leaf reject {
             description "Reject calls with higher downlink maximum-bit-rate";
             type empty;
           }
         }
         container guaranteed-bit-rate-uplink {
           description "Guaranteed bit rate uplink";
           leaf gbr-uplink {
             units "kbps";
             type union {
               type string {
                 pattern "<.*>|$.*";
               }
               type uint32 {
                 range "1 .. 10480000";
               }
             }
             mandatory true;
           }
           leaf upgrade {
             description "Override guaranteed-bit-rate uplink value";
             type empty;
           }
           leaf reject {
             description "Reject calls with higher uplink guaranteed-bit-rate";
             type empty;
           }
         }
         container guaranteed-bit-rate-downlink {
           description "Guaranteed bit rate downlink";
           leaf gbr-downlink {
             units "kbps";
             type union {
               type string {
                 pattern "<.*>|$.*";
               }
               type uint32 {
                 range "1 .. 10480000";
               }
             }
             mandatory true;
           }
           leaf upgrade {
             description "Override guaranteed-bit-rate downlink value";
             type empty;
           }
           leaf reject {
             description "Reject calls with higher downlink guaranteed-bit-rate";
             type empty;
           }
         }
         list qci {
           key name;
           ordered-by user;
           description "PDP qos control per qci";
           leaf name {
             type union {
               type string {
                 pattern "<.*>|$.*";
               }
               type uint8 {
                 range "5 .. 9";
               }
             }
           }
           uses apply-advanced;
           container maximum-bit-rate-uplink {
             description "Maximum bit rate uplink";
             leaf mbr-uplink {
               units "kbps";
               type union {
                 type string {
                   pattern "<.*>|$.*";
                 }
                 type uint32 {
                   range "1 .. 10480000";
                 }
               }
               mandatory true;
             }
             leaf upgrade {
               description "Override maximum-bit-rate uplink value";
               type empty;
             }
             leaf reject {
               description "Reject calls with higher uplink maximum-bit-rate";
               type empty;
             }
           }
           container maximum-bit-rate-downlink {
             description "Maximum bit rate downlink";
             leaf mbr-downlink {
               units "kbps";
               type union {
                 type string {
                   pattern "<.*>|$.*";
                 }
                 type uint32 {
                   range "1 .. 10480000";
                 }
               }
               mandatory true;
             }
             leaf upgrade {
               description "Override maximum-bit-rate downlink value";
               type empty;
             }
             leaf reject {
               description "Reject calls with higher downlink maximum-bit-rate";
               type empty;
             }
           }
         }
       }
       container policer-action {
         description "Policer actions";
         uses apply-advanced;
         container non-gbr-bearer {
           description "Policer actions for non gbr bearers";
           uses apply-advanced;
           leaf violate-action {
             description "PDP policer violate action";
             type enumeration {
               enum "set-loss-priority-high" {
                 description "Violate action set loss priority high";
               }
               enum "transmit" {
                 description "Violate action transmit";
               }
             }
           }
         }
         container gbr-bearer {
           description "Policer actions for gbr bearers";
           uses apply-advanced;
           leaf exceed-action {
             description "PDP policer exceed action";
             type enumeration {
               enum "drop" {
                 description "Exceed action drop";
               }
               enum "transmit" {
                 description "Exceed action transmit";
               }
             }
           }
           leaf violate-action {
             description "PDP policer violate action";
             type enumeration {
               enum "set-loss-priority-high" {
                 description "Violate action set loss priority high";
               }
               enum "transmit" {
                 description "Violate action transmit";
               }
             }
           }
         }
       }
     }
   }
   grouping juniper_accounting_options {
     description "Accounting data configuration";
     uses apply-advanced;
     container periodic-refresh {
       description "Toggle periodic statistics collection";
       choice enable-disable {
         case case_1 {
           leaf disable {
             description "Disable statistics refresh";
             type empty;
           }
         }
       }
     }
     container detailed-transit-interface-stats {
       description "Display Layer 3 Transit Statistics";
       choice enable-disable {
         case case_1 {
           leaf disable {
             description "Disable detailed transit interface statistics";
             type empty;
           }
         }
       }
     }
     list file {
       key name;
       ordered-by user;
       description "Accounting data file configuration";
       leaf name {
         description "Name of file in which to write accounting data";
         type string {
         }
       }
       uses apply-advanced;
       leaf size {
         description "Maximum accounting data file size";
         type string;
       }
       leaf files {
         description "Maximum number of files for this profile";
         default "10";
         type union {
           type string {
             pattern "<.*>|$.*";
           }
           type uint32 {
             range "3 .. 1000";
           }
         }
       }
       leaf transfer-interval {
         description "Frequency at which to transfer files to archive sites";
         default "30";
         units "minutes";
         type union {
           type string {
             pattern "<.*>|$.*";
           }
           type uint32 {
             range "5 .. 2880";
           }
         }
       }
       leaf start-time {
         description "Start time for file transmission (yyyy-mm-dd.hh:mm) in local time format";
         type jt:time;
       }
       leaf compress {
         description "Transfer file in compressed format";
         type empty;
       }
       container backup-on-failure {
         description "Backup on transfer failure";
         uses apply-advanced;
         choice backuponfailure {
           case case_1 {
             leaf master-only {
               description "Backup on master only";
               type empty;
             }
           }
           case case_2 {
             leaf master-and-slave {
               description "Backup on both master and slave";
               type empty;
             }
           }
         }
       }
       leaf push-backup-to-master {
         description "Push backup files to master RE";
         type empty;
       }
       list archive-sites {
         key name;
         ordered-by user;
         description "List of archive destinations";
         leaf name {
           description "Primary and failover URLs to receive archive files";
           type string;
         }
         leaf password {
           description "Password for login into the archive site";
           type jt:unreadable;
         }
       }
     }
     list interface-profile {
       key name;
       ordered-by user;
       description "Interface profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       container fields {
         description "Statistics to log to file";
         uses apply-advanced;
         leaf input-bytes {
           description "Input bytes";
           type empty;
         }
         leaf output-bytes {
           description "Output bytes";
           type empty;
         }
         leaf input-packets {
           description "Input packets";
           type empty;
         }
         leaf output-packets {
           description "Output packets";
           type empty;
         }
         leaf input-errors {
           description "Generic input error packets";
           type empty;
         }
         leaf output-errors {
           description "Generic output error packets";
           type empty;
         }
         leaf input-multicast {
           description "Input packets arriving by multicast";
           type empty;
         }
         leaf output-multicast {
           description "Output packets sent by multicast";
           type empty;
         }
         leaf input-unicast {
           description "Input unicast packets";
           type empty;
         }
         leaf output-unicast {
           description "Output unicast packets";
           type empty;
         }
         leaf unsupported-protocol {
           description "Packets for unsupported protocol";
           type empty;
         }
         leaf rpf-check-bytes {
           description "Bytes failing IPv4 reverse-path-forwarding check";
           type empty;
         }
         leaf rpf-check-packets {
           description "Packets failing IPv4 reverse-path-forwarding check";
           type empty;
         }
         leaf rpf-check-total-bytes {
           description "Total Bytes failing reverse-path-forwarding check";
           type empty;
         }
         leaf rpf-check-total-packets {
           description "Total Packets failing reverse-path-forwarding check";
           type empty;
         }
       }
     }
     list filter-profile {
       key name;
       ordered-by user;
       description "Filter profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 1048576";
           }
         }
       }
       list counters {
         key name;
         ordered-by user;
         description "Name of counter";
         uses counter-object;
       }
       leaf start-time {
         description "Profile start time (yyyy-mm-dd.hh:mm) in local time format";
         type jt:time;
       }
     }
     list class-usage-profile {
       key name;
       ordered-by user;
       description "Class usage profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 1048576";
           }
         }
       }
       leaf start-time {
         description "Profile start time (yyyy-mm-dd.hh:mm) in local time format";
         type jt:time;
       }
       choice class-name {
         case case_1 {
           list destination-classes {
             key name;
             ordered-by user;
             description "Name of destination class";
             uses dest-class-name-object;
           }
         }
         case case_2 {
           list source-classes {
             key name;
             ordered-by user;
             description "Name of source class";
             uses source-class-name-object;
           }
         }
       }
     }
     list routing-engine-profile {
       key name;
       ordered-by user;
       description "Routing Engine profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       container fields {
         description "Information to log to file";
         uses apply-advanced;
         leaf host-name {
           description "Hostname for this router";
           type empty;
         }
         leaf date {
           description "Date";
           units "YYYYMMDD";
           type empty;
         }
         leaf time-of-day {
           description "Time of day";
           units "HHMMSS";
           type empty;
         }
         leaf uptime {
           description "Time since last reboot";
           units "seconds";
           type empty;
         }
         leaf cpu-load-1 {
           description "Average system load over last 1 minute";
           type empty;
         }
         leaf cpu-load-5 {
           description "Average system load over last 5 minutes";
           type empty;
         }
         leaf cpu-load-15 {
           description "Average system load over last 15 minutes";
           type empty;
         }
         leaf memory-usage {
           description "Instantaneous active memory usage";
           type empty;
         }
         leaf total-cpu-usage {
           description "Total CPU usage percentage";
           type empty;
         }
         leaf cpu-usage-5sec {
           description "System CPU usage for last 5 seconds";
           type empty;
         }
         leaf cpu-usage-1min {
           description "System CPU usage for the last minute";
           type empty;
         }
         leaf cpu-usage-5min {
           description "System CPU usage for the 5 minutes";
           type empty;
         }
         leaf free-mem {
           description "Total free memory available";
           type empty;
         }
         leaf total-mem {
           description "Total memory available";
           type empty;
         }
       }
     }
     list mib-profile {
       key name;
       ordered-by user;
       description "MIB profile for accounting data";
       leaf name {
         description "Name of profile";
         type string;
       }
       uses apply-advanced;
       leaf file {
         description "Name of file for accounting data";
         type string {
         }
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       leaf operation {
         description "SNMP operation";
         default "walk";
         type enumeration {
           enum "get" {
             description "Get SNMP object value";
           }
           enum "get-next" {
             description "Get next SNMP object value";
           }
           enum "walk" {
             description "Walk SNMP object values";
           }
         }
       }
       list object-names {
         key name;
         ordered-by user;
         description "Names of MIB objects";
         uses mib-variable-name-object;
       }
     }
     list flat-file-profile {
       key name;
       ordered-by user;
       description "Flat file profile for accounting data";
       leaf name {
         description "Name of profile";
         type string;
       }
       uses apply-advanced;
       leaf file {
         description "Name of file for accounting data";
         type string;
       }
       leaf interval {
         description "Polling interval";
         default "15";
         units "minutes";
         type union {
           type string {
             pattern "<.*>|$.*";
           }
           type uint32 {
             range "1 .. 2880";
           }
         }
       }
       leaf schema-version {
         description "Name of the schema";
         type string;
       }
       leaf start-time {
         description "Profile start time (yyyy-mm-dd.hh:mm) in local time format";
         type jt:time;
       }
       leaf use-fc-ingress-stats {
         description "Use Ingress stats for reporting forwarding class counters";
         type empty;
       }
       container fields {
         description "Statistics to log to file";
         uses apply-advanced;
         leaf all-fields {
           description "All parameters";
           type empty;
         }
         leaf service-accounting {
           description "Service accounting for filters - obsolete config";
           status deprecated;
           type empty;
         }
         container general-param {
           presence "enable general-param";
           description "General interface parameters";
           uses apply-advanced;
           leaf all-fields {
             description "All general interface parameters";
             type empty;
           }
           leaf timestamp {
             description "Timestamp";
             type empty;
           }
           leaf accounting-type {
             description "Accounting status type";
             type empty;
           }
           leaf descr {
             description "Description";
             type empty;
           }
           leaf routing-instances {
             description "Routing Instances where interface belongs";
             type empty;
           }
           leaf nas-port-id {
             description "NAS port id";
             type empty;
           }
           leaf line-id {
             description "Line id";
             type empty;
           }
           leaf vlan-id {
             description "Vlan-id";
             type empty;
           }
           leaf logical-interface {
             description "Logical-Interface";
             type empty;
           }
           leaf physical-interface {
             description "Physical Interface name";
             type empty;
           }
           leaf user-name {
             description "User name of the subscriber";
             type empty;
           }
         }
         container overall-packet {
           presence "enable overall-packet";
           description "Overall packet statistics";
           uses apply-advanced;
           leaf all-fields {
             description "All overall packet statistics";
             type empty;
           }
           leaf input-bytes {
             description "Input bytes";
             type empty;
           }
           leaf input-packets {
             description "Input packets";
             type empty;
           }
           leaf input-v6-bytes {
             description "Input IPV6 bytes";
             type empty;
           }
           leaf input-v6-packets {
             description "Input IPV6 packets";
             type empty;
           }
           leaf output-bytes {
             description "Output bytes";
             type empty;
           }
           leaf output-packets {
             description "Output packets";
             type empty;
           }
           leaf output-v6-bytes {
             description "Output IPV6 bytes";
             type empty;
           }
           leaf output-v6-packets {
             description "Output IPV6 packets";
             type empty;
           }
           leaf input-errors {
             description "Total input errors";
             type empty;
           }
           leaf output-errors {
             description "Total output errors";
             type empty;
           }
           leaf input-discards {
             description "Total input discards";
             type empty;
           }
           leaf input-v4-bytes {
             description "Input IPV4 bytes";
             type empty;
           }
           leaf input-v4-packets {
             description "Input IPV4 packets";
             type empty;
           }
           leaf output-v4-bytes {
             description "Output IPV4 bytes";
             type empty;
           }
           leaf output-v4-packets {
             description "Output IPV4 packets";
             type empty;
           }
           leaf input-bytes-per-sec {
             description "Input bytes per second";
             type empty;
           }
           leaf input-packets-per-sec {
             description "Input packets per second";
             type empty;
           }
         }
         container l2-stats {
           presence "enable l2-stats";
           description "Layer2 statistics";
           uses apply-advanced;
           leaf all-fields {
             description "All Layer2 statistics";
             type empty;
           }
           leaf input-mcast-bytes {
             description "L2 multicast bytes from input side";
             type empty;
           }
           leaf input-mcast-packets {
             description "L2 multicast packets from input side";
             type empty;
           }
         }
         container ingress-stats {
           presence "enable ingress-stats";
           description "Ingress queue statistics";
           uses apply-advanced;
           leaf all-fields {
             description "All ingress queue statistics";
             type empty;
           }
           leaf queue-id {
             description "Queue ID";
             type empty;
           }
           leaf input-packets {
             description "Total input packets on the queue";
             type empty;
           }
           leaf input-bytes {
             description "Total input bytes on the queue";
             type empty;
           }
           leaf output-packets {
             description "Total output packet on the queue";
             type empty;
           }
           leaf output-bytes {
             description "Total output bytes on the queue";
             type empty;
           }
           leaf drop-packets {
             description "Ingress queue dropped packets";
             type empty;
           }
         }
         container egress-stats {
           presence "enable egress-stats";
           description "Egress queue statistics";
           uses apply-advanced;
           leaf all-fields {
             description "All egress queue statistics";
             type empty;
           }
           leaf queue-id {
             description "Queue ID";
             type empty;
           }
           leaf input-packets {
             description "Total input packets on the queue";
             type empty;
           }
           leaf input-bytes {
             description "Total input bytes on the queue";
             type empty;
           }
           leaf output-packets {
             description "Total output packet on the queue";
             type empty;
           }
           leaf output-bytes {
             description "Total output bytes on the queue";
             type empty;
           }
           leaf tail-drop-packets {
             description "Egress queue tail dropped packets";
             type empty;
           }
           leaf red-drop-packets {
             description "Egress queue red dropped packets";
             type empty;
           }
           leaf red-drop-bytes {
             description "Egress queue red drop bytes";
             type empty;
           }
           leaf total-drop-packets {
             description "Egress queue total drop packets";
             type empty;
           }
         }
       }
       container format {
         description "Flat file accounting format";
         uses apply-advanced;
         choice flatfileformat {
           case case_1 {
             leaf ipdr {
               description "IPDR format";
               type empty;
             }
           }
           case case_2 {
             leaf csv {
               description "CSV format";
               type empty;
             }
           }
         }
       }
     }
     container cleanup-interval {
       presence "enable cleanup-interval";
       description "Backup files cleanup interval";
       uses apply-advanced;
       leaf interval {
         description "Cleanup interval in days";
         default "1";
         units "day";
         type union {
           type string {
             pattern "<.*>|$.*";
           }
           type uint32 {
             range "1 .. 31";
           }
         }
       }
     }
   }
   grouping counter-object {
     leaf name {
       description "Name of counter";
       type string;
     }
   }
   grouping dest-class-name-object {
     leaf name {
       description "Class name";
       type string;
     }
   }
   grouping junos_hash_key {
     description "Select data used in the hash key";
     uses apply-advanced;
     container hash-seed {
       presence "enable hash-seed";
       description "Hash seed";
       uses apply-advanced;
     }
     container family {
       description "Protocol family";
       container fcoe {
         description "FCoE protocol family";
         uses apply-advanced;
       }
       container inet {
         description "IPv4 protocol family";
         uses apply-advanced;
         container layer-3 {
           presence "enable layer-3";
           description "Include Layer 3 (IP) data in the hash key";
           uses apply-advanced;
           leaf destination-address {
             description "Include IP destination address in the hash key";
             type empty;
           }
         }
         container layer-4 {
           presence "enable layer-4";
           description "Include Layer 4 (TCP or UDP) data in the hash key";
           uses apply-advanced;
         }
       }
       container multiservice {
         description "Multiservice protocol family";
         uses apply-advanced;
         leaf source-mac {
           description "Include source MAC address in hash key";
           type empty;
         }
         leaf destination-mac {
           description "Include destination MAC address in hash key";
           type empty;
         }
       }
     }
   }
   grouping keepalives_type {
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping kmd-security-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     leaf rate-limit {
       description "Limit the incoming rate of trace messages";
       default "0";
       type union {
         type string {
           pattern "<.*>|$.*";
         }
         type uint32 {
           range "0 .. 4294967295";
         }
       }
     }
     list flag {
       key name;
       ordered-by user;
       description "Tracing parameters";
       leaf name {
         type enumeration {
           enum "timer" {
             description "Trace internal timer events";
           }
           enum "routing-socket" {
             description "Trace routing socket messages";
           }
           enum "parse" {
             description "Trace configuration processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "ams" {
             description "Trace AMS events";
           }
           enum "lic" {
             description "Trace License events";
           }
           enum "all" {
             description "Trace everything";
           }
         }
       }
     }
   }
   grouping layer2_pm_family_output_type {
     uses apply-advanced;
     choice interface-or-next-hop-index {
       case case_1 {
         leaf interface {
           description "Interface through which to send sampled traffic";
           type union {
             type jt:interface-name;
             type string {
               pattern "<.*>|$.*";
             }
           }
         }
       }
       case case_2 {
         leaf next-hop-group {
           description "Next-hop-group through which to send port-mirror traffic";
           type string;
         }
       }
       case case_3 {
         list routing-instance {
           key name;
           description "Routing instances";
           max-elements 1;
           uses layer2_pm_output-routing-instance-type;
         }
       }
       case case_4 {
         list vlan {
           key name;
           description "Outgoing VLAN for mirrored packets";
           max-elements 1;
           uses pm-rspan-vlan;
         }
       }
       case case_5 {
       }
     }
     leaf no-filter-check {
       description "Do not check for filters on port-mirroring interface";
       type empty;
     }
   }
   grouping layer2_pm_output-routing-instance-type {
     leaf name {
       description "Routing instance name";
       type string {
       }
     }
     uses apply-advanced;
     list vlan {
       key name;
       description "Outgoing VLAN for mirrored packets";
       max-elements 1;
       uses pm-rspan-vlan;
     }
   }
   grouping ldp-sync-obj {
     uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping lmp_control_channel_type {
     leaf name {
       description "Control channel interface";
       type union {
         type jt:interface-name;
         type string {
           pattern "<.*>|$.*";
         }
       }
     }
     uses apply-advanced;
     leaf remote-address {
       description "Control channel remote address";
       type jt:ipaddr;
     }
   }
   grouping log-object {
     description "Configure auditable security logs";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
   }
   grouping lr_interfaces_type {
     description "Physical interface";
     leaf name {
       description "Interface name";
       type union {
         type jt:interface-unit;
         type string {
           pattern "<.*>|$.*";
         }
       }
     }
     uses apply-advanced;
     list unit {
       key name;
       description "Logical interface";
       leaf name {
         type string;
       }
       uses apply-advanced;
       leaf interface-tag {
         description "Interface tag name";
         type string {
           length "1 .. 64";
         }
       }
       leaf alias {
         description "Interface alias";
         type string;
       }
       container peer-psd {
         presence "enable peer-psd";
         description "Peer psd";
         leaf psd-name {
           description "Peer psd name";
           type string;
           mandatory true;
         }
       }
       container peer-interface {
         presence "enable peer-interface";
         description "Peer interface";
         uses apply-advanced;
         leaf interface-name {
           description "Peer interface name";
           type union {
             type jt:interface-unit;
             type string {
               pattern "<.*>|$.*";
             }
           }
         }
       }
       container interface-shared-with {
         presence "enable interface-shared-with";
         description "Specify which PSD owns this logical interface";
         uses apply-advanced;
         leaf psd-name {
           description "Name of protected system domain (psd[1-31], ex. psd2)";
           type string {
           }
           mandatory true;
         }
       }
       choice enable-disable {
         case case_1 {
           leaf disable {
             description "Disable this logical interface";
             type empty;
           }
         }
       }
       leaf extended-telemetry {
         description "Enable extended telemetry";
         type empty;
       }
       leaf passive-monitor-mode {
         description "Use interface to tap packets from another router";
         type empty;
       }
       leaf clear-dont-fragment-bit {
         description "Clear DF bit in packet (AS PIC and J-series only as well as MIF)";
         type empty;
       }
       leaf description {
         description "Text description of interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-ppp-funi" {
             description "ATM PPP over FUNI";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "ethernet-tcc" {
             description "Ethernet translational cross-connect";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             type string;
           }
         }
         case case_2 {
           leaf vlan-id-range {
             description "Virtual LAN identifier range of form vid1-vid2";
             type jt:vlan-range;
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
               mandatory true;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
       leaf native-inner-vlan-id {
         description "Native virtual LAN identifier for singly tagged frames";
         type union {
           type string {
             pattern "<.*>|$.*";
           }
           type uint32 {
             range "0 .. 4094";
           }
         }
       }
       container accept-source-mac {
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       choice psn_vci_type {
         case case_1 {
         }
         case case_2 {
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         description "ATM VCI range start <start-vci> end <end-vci>";
         leaf start {
           description "ATM VCI range's start value";
           type union {
             type string {
               pattern "<.*>|$.*";
             }
             type uint16 {
               range "32 .. 4094";
             }
           }
           mandatory true;
         }
         leaf end {
           description "ATM VCI range's end value";
           type union {
             type string {
               pattern "<.*>|$.*";
             }
             type uint16 {
               range "32 .. 4094";
             }
           }
           mandatory true;
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       choice keepalive_choices {
         case case_1 {
           container keepalives {
             description "Send or demand keepalive messages";
             presence "enable keepalives";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           description "Encapsulation over tunnel";
           container vxlan-gpe {
             presence "enable vxlan-gpe";
             uses apply-advanced;
             container source {
               uses apply-advanced;
               leaf address {
                 description "Interface address prefix";
                 type jt:ipv4addr;
               }
               leaf mac-address {
                 description "Interface source mac address";
                 type jt:mac-addr;
               }
               leaf interface {
                 description "Name of the interface";
                 type union {
                   type jt:interface-name;
                   type string {
                     pattern "<.*>|$.*";
                   }
                 }
               }
             }
             container destination {
               uses apply-advanced;
               leaf address {
                 description "Interface address prefix";
                 type jt:ipv4addr;
               }
               leaf mac-address {
                 description "Interface destination mac address";
                 type jt:mac-addr;
               }
             }
             leaf tunnel-endpoint {
               description "Tunnel end point type";
               type enumeration {
                 enum "vxlan" {
                   description "To configure vxlan tunnel-end-point";
                 }
               }
               mandatory true;
             }
             container source-udp-port-range {
               description "Value range for source-udp-port";
               leaf min {
                 description "Minimum range value";
                 type union {
                   type string {
                     pattern "<.*>|$.*";
                   }
                   type uint32 {
                     range "1 .. 65535";
                   }
                 }
                 mandatory true;
               }
               leaf max {
                 description "Maximum range value";
                 type union {
                   type string {
                     pattern "<.*>|$.*";
                   }
                   type uint32 {
                     range "1 .. 65535";
                   }
                 }
                 mandatory true;
               }
             }
             leaf destination-udp-port {
               description "Value to write to the destination-udp-port field";
               type union {
                 type string {
                   pattern "<.*>|$.*";
                 }
                 type uint32 {
                   range "1 .. 65535";
                 }
               }
               mandatory true;
             }
             leaf vni {
               description "Value to write to the vni field";
               type union {
                 type string {
                   pattern "<.*>|$.*";
                 }
                 type uint32 {
                   range "0 .. 16777214";
                 }
               }
               mandatory true;
             }
           }
         }
         choice source_type {
           case case_1 {
             leaf source {
               description "Tunnel source address";
               type jt:ipaddr;
             }
           }
           case case_2 {
           }
           case case_3 {
           }
         }
         choice destination_type {
           case case_1 {
             leaf destination {
               description "Tunnel destination address";
               type jt:ipaddr;
             }
           }
           case case_2 {
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             type string {
             }
           }
         }
       }
       leaf compression-device {
         description "Logical interface used for compression";
         type union {
           type jt:interface-unit;
           type string {
             pattern "<.*>|$.*";
           }
         }
       }
       container layer2-policer {
         description "Layer2 policing for logical interface";
         uses apply-advanced;
         choice layer2-input-policer-choice {
           case case_1 {
             leaf input-policer {
               description "Two-color policer for received packets";
               type string;
             }
           }
           case case_2 {
           }
           case case_3 {
             leaf input-three-color {
               description "Color-blind three-color policer for received packets";
               type string;
             }
           }
         }
         choice layer2-output-policer-choice {
           case case_1 {
             leaf output-policer {
               description "Two-color policer for transmitted packets";
               type string;
             }
           }
           case case_2 {
             leaf output-three-color {
               description "Three-color policer for transmitted packets";
               type string;
             }
           }
         }
       }
       choice virtual-gateway {
         case case_1 {
           leaf no-auto-virtual-gateway-esi {
             description "Disable auto ESI generation for virtual gateway address";
             type empty;
           }
         }
         case case_2 {
           container virtual-gateway-esi {
             description "ESI configuration of virtual gateway";
             uses apply-advanced;
             leaf identifier {
               description "ESI value for the interface";
               type jt:esi;
               mandatory true;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             type string;
             mandatory true;
           }
           uses apply-advanced;
           leaf activate-all {
             description "Activate all rules and rulebases in the pcef profile";
             type empty;
           }
           list activate {
             key name;
             ordered-by user;
             description "Name of pcef profile rule or rulebase to activate";
             leaf name {
               description "Name of pcef profile rule or rulebase to activate";
               type string;
             }
             uses apply-advanced;
           }
         }
       }
       choice generate-eui64-choice {
         leaf generate-eui64 {
           description "To generate Link Local EUI-64 addresses";
           type empty;
         }
         leaf no-generate-eui64 {
           description "Don't to generate Link Local EUI-64 addresses";
           type empty;
         }
       }
       container family {
         description "Protocol family";
         container inet {
           presence "enable inet";
           description "IPv4 parameters";
           uses apply-advanced;
           container class-based-filtering {
             description "Enable class based filter on interface";
             uses apply-advanced;
           }
           container dhcp {
             description "Dynamic Host Configuration Protocol client configuration";
             presence "enable dhcp";
             uses dhcp-client-type;
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf no-redirects {
             description "Do not redirect traffic";
             type empty;
           }
           leaf nat-outside-interface {
             description "Public interface used for NAT";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           leaf allow-filter-on-re {
             description "Enable kernel filter on network ports";
             type empty;
           }
           container filter {
             description "Packet filtering";
             uses apply-advanced;
             choice input_choice {
               case case_1 {
                 container input {
                   description "Filter to be applied to received packets";
                   leaf filter-name {
                     description "Name of the filter";
                     type string;
                     mandatory true;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                     mandatory true;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32;
               }
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               type string;
             }
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
               mandatory true;
             }
             uses apply-advanced;
             leaf ipsec-vpn {
               description "Name of IPSec VPN";
               type string;
               mandatory true;
             }
           }
           choice tunnel-termination-status {
             case case_1 {
               leaf tunnel-termination {
                 description "Tunnel termination";
                 type empty;
               }
             }
             case case_2 {
               leaf no-tunnel-termination {
                 description "No Tunnel termination";
                 type empty;
               }
             }
           }
           list address {
             key name;
             ordered-by user;
             description "Interface address/destination prefix";
             leaf name {
               description "Interface address/destination prefix";
               type jt:ipv4prefix;
             }
             uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             container tag {
               description "Tag used for route/local";
               uses apply-advanced;
               leaf tag-value {
                 description "The tag value on the address";
                 type union {
                   type string {
                     pattern "<.*>|$.*";
                   }
                   type uint32 {
                     range "1 .. 4294967295";
                   }
                 }
                 mandatory true;
               }
               leaf type {
                 description "Tag type must be [1-16]";
                 type union {
                   type string {
                     pattern "<.*>|$.*";
                   }
                   type uint32 {
                     range "1 .. 16";
                   }
                 }
               }
             }
             container tag2 {
               description "Tag2 used for route/local";
               uses apply-advanced;
               leaf tag2-value {
                 description "The tag value on the address";
                 type union {
                   type string {
                     pattern "<.*>|$.*";
                   }
                   type uint32 {
                     range "1 .. 4294967295";
                   }
                 }
                 mandatory true;
               }
               leaf type {
                 description "Tag type must be [1-16]";
                 type union {
                   type string {
                     pattern "<.*>|$.*";
                   }
                   type uint32 {
                     range "1 .. 16";
                   }
                 }
               }
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
                 mandatory true;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
               leaf flood-as-unknown-unicast {
                 description "Broadcast the packet with unicast MAC";
                 type empty;
               }
             }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
               mandatory true;
             }
             leaf preferred-source-address {
               description "Preferred address on the donor interface";
               type string;
             }
             leaf destination {
               description "Destination address";
               type jt:ipv4addr;
             }
             leaf destination-profile {
               description "Profile to use for destination address";
               type string;
             }
           }
           leaf negotiate-address {
             description "Negotiate address with remote";
             type empty;
           }
           leaf destination-udp-port {
             description "Choose destination UDP port number";
             type union {
               type string {
                 pattern "<.*>|$.*";
               }
               type uint32 {
                 range "10000 .. 10009";
               }
             }
           }
           container auto-configure {
             description "Auto configuration";
             uses dynamic_ipv4_type;
           }
         }
         container mlppp {
           description "Multilink PPP protocol parameters";
           uses apply-advanced;
           leaf bundle {
             description "Logical interface name this link will join";
             type string;
             mandatory true;
           }
           choice anchor-points {
             case case_1 {
             }
             case case_2 {
             }
           }
           leaf dynamic-profile {
             description " dynamic profile for interface to use";
             type string {
               length "1 .. 80";
             }
           }
         }
         container mlfr-end-to-end {
           presence "enable mlfr-end-to-end";
           description "Multilink Frame Relay end-to-end protocol parameters";
           uses apply-advanced;
           leaf bundle {
             description "Logical interface name this link will join";
             type union {
               type jt:interface-unit;
               type string {
                 pattern "<.*>|$.*";
               }
             }
             mandatory true;
           }
         }
         container mlfr-uni-nni {
           presence "enable mlfr-uni-nni";
           description "Multilink Frame Relay UNI NNI protocol parameters";
           uses apply-advanced;
           leaf bundle {
             description "Logical interface name this link will join";
             type union {
               type jt:interface-unit;
               type string {
                 pattern "<.*>|$.*";
               }
             }
             mandatory true;
           }
         }
         container ccc {
           presence "enable ccc";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
         }
         container vpls {
           presence "enable vpls";
           description "Virtual private LAN service parameters";
           uses apply-advanced;
           leaf core-facing {
             description "Interface is core facing";
             type empty;
           }
         }
         container ethernet-switching {
           description "Ethernet switching parameters";
           presence "enable ethernet-switching";
           uses ethernet-switching-type;
         }
         container any {
           presence "enable any";
           description "Parameters for 'any' family";
           uses apply-advanced;
           container filter {
             description "Layer 2 packet filtering";
             uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         description "AMS subunit load balancing options";
         uses apply-advanced;
         leaf preferred-active {
           description "Preferred active Interface name";
           type union {
             type jt:interface-device;
             type string {
               pattern "<.*>|$.*";
             }
           }
         }
         leaf disable-hash {
           description "Hash based distribution is not needed for this subunit";
           type empty;
         }
         leaf modulo-key {
           description "Modulo based distribution";
           type enumeration {
             enum "source-ip" {
               description "Source Ip Address";
             }
             enum "destination-ip" {
               description "Destination Ip Address";
             }
           }
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       container interface-state {
         description "IRB interface state computation";
         uses apply-advanced;
         choice state {
           case case_1 {
             leaf local {
               description "IRB State computation based on local interface state";
               type empty;
             }
           }
           case case_2 {
             leaf remote {
               description "IRB State computation based on remote reachability";
               type empty;
             }
           }
           case case_3 {
             leaf local-remote {
               description "IRB State computation based on local or remote reachability";
               type empty;
             }
           }
           case case_4 {
             leaf local-interface {
               description "IRB State computation based on loopback AE port state";
               type union {
                 type jt:interface-name;
                 type string {
                   pattern "<.*>|$.*";
                 }
               }
             }
           }
         }
         leaf local-count {
           description "Minimum number of local layer2 link in up state to consider IRB up";
           type union {
             type uint16;
             type string {
               pattern "<.*>|$.*";
             }
           }
         }
         leaf vtep-count {
           description "Minimum number of VTEP link in up state to consider IRB up";
           type union {
             type uint16;
             type string {
               pattern "<.*>|$.*";
             }
           }
         }
         container hold-time {
           description "Delay before marking interface up or down for defect";
           uses apply-advanced;
           leaf up {
             description "Delay in seconds before marking IRB interface up";
             units "seconds";
             type union {
               type uint32;
               type string {
                 pattern "<.*>|$.*";
               }
             }
           }
           leaf down {
             description "Delay in seconds before marking IRB interface down";
             units "seconds";
             type union {
               type uint32;
               type string {
                 pattern "<.*>|$.*";
               }
             }
           }
         }
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf no-dhcp-flood {
         description "Disable dhcp flooding";
         type empty;
       }
       leaf etree-ac-role {
         description "ETREE attachment circuit role";
         type enumeration {
           enum "root" {
             description "ETREE root interface";
           }
           enum "leaf" {
             description "ETREE leaf interface";
           }
         }
       }
     }
   }
   grouping lsp-set-match-type {
     uses apply-advanced;
     leaf lsp-name {
       description "LSP name that matches this string";
       type string;
     }
     leaf lsp-regex {
       description "All LSPs that match this regular expression pattern";
       type string;
     }
     leaf p2mp-name {
       description "P2MP names that match this string";
       type string;
     }
     leaf p2mp-regex {
       description "P2MP names that match this regular expression pattern";
       type string;
     }
     choice router-type {
       case case_1 {
         leaf egress {
           description "All LSPs for which this router is egress";
           type empty;
         }
       }
       case case_2 {
         leaf ingress {
           description "All LSPs for which this router is ingress";
           type empty;
         }
       }
       case case_3 {
         leaf transit {
           description "All LSPs for which this router is transit";
           type empty;
         }
       }
     }
   }
   grouping lsp_nh_obj {
     leaf name {
       description "LSP to use to reach destination";
       type string;
       mandatory true;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping mac_addr_list_items {
     leaf name {
       description "Mac Address";
       type jt:mac-addr;
     }
     uses apply-advanced;
   }
   grouping mac_list {
     description "MAC address";
     leaf name {
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     leaf allow {
       type empty;
     }
   }
   grouping match_interface_object {
     leaf name {
       description "Interface to match";
       type union {
         type jt:interface-wildcard;
         type string {
           pattern "<.*>|$.*";
         }
       }
     }
   }
   grouping match_interface_object_oam {
     leaf name {
       description "Interface to match";
       type union {
         type jt:interface-wildcard;
         type string {
           pattern "<.*>|$.*";
         }
       }
     }
   }
   grouping match_interface_set_object {
     leaf name {
       description "Interface set to match";
       type string;
     }
   }
   grouping match_simple_dscp_value {
     uses apply-advanced;
     leaf value_keyword {
       type string;
     }
   }
   grouping match_simple_port_value {
     uses apply-advanced;
     leaf value_keyword {
       type string;
     }
   }
   grouping match_simple_protocol_value {
     uses apply-advanced;
     leaf value_keyword {
       type string;
     }
   }
   grouping metric_expression_type {
     uses apply-advanced;
     container metric {
       description "Parameters for metric attribute";
       leaf multiplier {
         description "Coefficient for metric attribute";
         type decimal64 {
           fraction-digits 9;
         }
       }
       leaf offset {
         description "Offset for metric attribute";
         type union {
           type int32;
           type string {
             pattern "<.*>|$.*";
           }
         }
       }
     }
     container metric2 {
       description "Parameters for metric2 attribute";
       leaf multiplier {
         description "Coefficient for metric2 attribute";
         default "1.0";
         type decimal64 {
           fraction-digits 9;
         }
       }
       leaf offset {
         description "Offset for metric2 attribute";
         type union {
           type int32;
           type string {
             pattern "<.*>|$.*";
           }
         }
       }
     }
     container actual-igp-cost {
       description "Parameters for actual IGP attribute";
       leaf multiplier {
         description "Coefficient for actual IGP metric attribute";
         type decimal64 {
           fraction-digits 9;
         }
       }
       leaf offset {
         description "Offset for actual IGP metric attribute";
         type union {
           type int32;
           type string {
             pattern "<.*>|$.*";
           }
         }
       }
     }
   }
   grouping mib-variable-name-object {
     leaf name {
       description "MIB variable name";
       type string {
       }
     }
   }
   grouping mpls_ifd_options {
     uses apply-advanced;
     container pop-all-labels {
       presence "enable pop-all-labels";
       description "Pop all MPLS labels off incoming packets";
       uses apply-advanced;
       leaf-list required-depth {
         ordered-by user;
         description "Required label depth of packet to pop all labels";
         type enumeration {
           enum "all" {
             description "Takes effect only in Stoli based FPCs, in all other FPCs equivalent to '[1 2]'";
           }
           enum "1" {
             description "Required label depth of packet to pop labels";
           }
           enum "2" {
             description "Required label depth of packet to pop labels";
           }
         }
       }
     }
   }
   grouping mpls_pm_family_output_type {
     uses apply-advanced;
   }
   grouping mrp-trace-options {
     description "Trace options for MMRP Protocol";
     uses apply-advanced;
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "events" {
             description "Trace events to the protocol state machine";
           }
           enum "pdu" {
             description "Trace RAPS PDU reception and transmission";
           }
           enum "timers" {
             description "Trace protocol timers";
           }
           enum "state-machine" {
             description "Trace information of the state machine";
           }
           enum "socket" {
             description "Trace soccket activity";
           }
           enum "error" {
             description "Trace all failure conditions";
           }
           enum "all" {
             description "Trace all";
           }
         }
       }
       leaf disable {
         description "Disable this trace flag";
         type empty;
       }
     }
   }
   grouping mstp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping multicast_interface_options_type {
     description "Multicast interface options";
     leaf name {
       description "Interface name";
       type union {
         type jt:interface-unit;
         type string {
           pattern "<.*>|$.*";
         }
       }
     }
     uses apply-advanced;
     container maximum-bandwidth {
       presence "enable maximum-bandwidth";
       description "Maximum multicast bandwidth for the interface";
       leaf bandwidth-limit {
         description "Maximum multicast bandwidth on the interface";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       type union {
         type string {
           pattern "<.*>|$.*";
         }
         type uint32 {
           range "0 .. 30";
         }
       }
     }
     leaf no-qos-adjust {
       description "Disable QoS adjustment for this interface";
       type empty;
     }
   }
   grouping network_type {
     leaf name {
       description "Network prefix";
       type jt:ipprefix;
     }
     uses apply-advanced;
     leaf-list dyn-tunnel-attribute-policy {
       ordered-by user;
       description "Import policy for dynamic-tunnel under this destination network";
       type jt:policy-algebra;
     }
     leaf preference {
       description "Preference of tunnel route under this destination network";
       type union {
         type uint32;
         type string {
           pattern "<.*>|$.*";
         }
       }
     }
     leaf-list colors {
       ordered-by user;
       description "Set of color list that will be supported for tunnel creation";
       type union {
         type uint32;
         type string {
           pattern "<.*>|$.*";
         }
       }
     }
     leaf best-effort {
       description "Best-effort transport class";
       type empty;
     }
   }
   grouping och-attributes {
     description "Optical channel configuration attributes";
     uses apply-advanced;
     leaf rate {
       description "Data rate of the OCH payload";
       type enumeration {
         enum "100g" {
           description "100Gbit OCH data rate";
         }
       }
     }
     leaf modulation {
       description "Optical modulation format";
       type enumeration {
         enum "qpsk" {
           description "QPSK Modulation Format";
         }
       }
     }
     leaf encoding {
       description "Optical encoding";
       type enumeration {
         enum "differential" {
           description "Differential encoding";
         }
       }
     }
     choice channel-number {
       case case_1 {
         leaf wavelength {
           description "Optical channel wavelength in nanometers";
           type enumeration {
             enum "1611.79" {
               description "1611.79 nm/186.000000 THz 3.125/6.25/12.5/50/75/100GHz spacing";
             }
             enum "1611.76" {
               description "1611.76 nm/186.003125 THz 3.125GHz spacing";
             }
             enum "1611.73" {
               description "1611.73 nm/186.006250 THz 3.125/6.25GHz spacing";
             }
             enum "1611.71" {
               description "1611.71 nm/186.009375 THz 3.125GHz spacing";
             }
             enum "1611.68" {
               description "1611.68 nm/186.012500 THz 3.125/6.25/12.5GHz spacing";
             }
             enum "1611.65" {
               description "1611.65 nm/186.015625 THz 3.125GHz spacing";
             }
             enum "1611.62" {
               description "1611.62 nm/186.018750 THz 3.125/6.25GHz spacing";
             }
             enum "1611.60" {
               description "1611.60 nm/186.021875 THz 3.125GHz spacing";
             }
             enum "1611.57" {
               description "1611.57 nm/186.025000 THz 3.125/6.25/12.5GHz spacing";
             }
             enum "1611.54" {
               description "1611.54 nm/186.028125 THz 3.125GHz spacing";
             }
             enum "1611.52" {
               description "1611.52 nm/186.031250 THz 3.125/6.25GHz spacing";
             }
             enum "1611.49" {
               description "1611.49 nm/186.034375 THz 3.125GHz spacing";
             }
             enum "1611.46" {
               description "1611.46 nm/186.037500 THz 3.125/6.25/12.5GHz spacing";
             }
             enum "1611.44" {
               description "1611.44 nm/186.040625 THz 3.125GHz spacing";
             }
             enum "1611.41" {
               description "1611.41 nm/186.043750 THz 3.125/6.25GHz spacing";
             }
             enum "1611.38" {
               description "1611.38 nm/186.046875 THz 3.125GHz spacing";
             }
             enum "1611.35" {
               description "1611.35 nm/186.050000 THz 3.125/6.25/12.5/50/75GHz spacing";
             }
             enum "1611.33" {
               description "1611.33 nm/186.053125 THz 3.125GHz spacing";
             }
             enum "1611.30" {
               description "1611.30 nm/186.056250 THz 3.125/6.25GHz spacing";
             }
             enum "1611.27" {
               description "1611.27 nm/186.059375 THz 3.125GHz spacing";
             }
             enum "1611.25" {
               description "1611.25 nm/186.062500 THz 3.125/6.25/12.5GHz spacing";
             }
             enum "1611.22" {
               description "1611.22 nm/186.065625 THz 3.125GHz spacing";
             }
             enum "1611.19" {
               description "1611.19 nm/186.068750 THz 3.125/6.25GHz spacing";
             }
             enum "1611.16" {
               description "1611.16 nm/186.071875 THz 3.125GHz spacing";
             }
             enum "1611.14" {
               description "1611.14 nm/186.075000 THz 3.125/6.25/12.5GHz spacing";
             }
             enum "1611.11" {
               description "1611.11 nm/186.078125 THz 3.125GHz spacing";
             }
             enum "1611.08" {
               description "1611.08 nm/186.081250 THz 3.125/6.25GHz spacing";
             }
             enum "1611.06" {
               description "1611.06 nm/186.084375 THz 3.125GHz spacing";
             }
             enum "1611.03" {
               description "1611.03 nm/186.087500 THz 3.125/6.25/12.5GHz spacing";
             }
             enum "1611.00" {
               description "1611.00 nm/186.090625 THz 3.125GHz spacing";
             }
             enum "1610.98" {
               description "1610.98 nm/186.093750 THz 3.125/6.25GHz spacing";
             }
             enum "1610.95" {
               description "1610.95 nm/186.096875 THz 3.125GHz spacing";
             }
             enum "1610.92" {
               description "1610.92 nm/186.100000 THz 3.125/6.25/12.5/100GHz spacing";
             }
             enum "1610.89" {
               description "1610.89 nm/186.103125 THz 3.125GHz spacing";
             }
             enum "1610.87" {
               description "1610.87 nm/186.106250 THz 3.125/6.25GHz spacing";
             }
             enum "1610.84" {
               description "1610.84 nm/186.109375 THz 3.125GHz spacing";
             }
             enum "1610.81" {
               description "1610.81 nm/186.112500 THz 3.125/6.25/12.5GHz spacing";
             }
             enum "1610.79" {
               description "1610.79 nm/186.115625 THz 3.125GHz spacing";
             }
             enum "1610.76" {
               description "1610.76 nm/186.118750 THz 3.125/6.25GHz spacing";
             }
             enum "1610.73" {
               description "1610.73 nm/186.121875 THz 3.125GHz spacing";
             }
             enum "1610.70" {
               description "1610.70 nm/186.125000 THz 3.125/6.25/12.5/75GHz spacing";
             }
             enum "1610.68" {
               description "1610.68 nm/186.128125 THz 3.125GHz spacing";
             }
             enum "1610.65" {
               description "1610.65 nm/186.131250 THz 3.125/6.25GHz spacing";
             }
             enum "1610.62" {
               description "1610.62 nm/186.134375 THz 3.125GHz spacing";
             }
             enum "1610.60" {
               description "1610.60 nm/186.137500 THz 3.125/6.25/12.5GHz spacing";
             }
             enum "1610.57" {
               description "1610.57 nm/186.140625 THz 3.125GHz spacing";
             }
             enum "1610.54" {
               description "1610.54 nm/186.143750 THz 3.125/6.25GHz spacing";
             }
             enum "1610.52" {
               description "1610.52 nm/186.146875 THz 3.125GHz spacing";
             }
             enum "1610.49" {
               description "1610.49 nm/186.150000 THz 3.125/6.25/12.5/50GHz spacing";
             }
             enum "1610.46" {
               description "1610.46 nm/186.153125 THz 3.125GHz spacing";
             }
             enum "1610.43" {
               description "1610.43 nm/186.156250 THz 3.125/6.25GHz spacing";
             }
             enum "1610.41" {
               description "1610.41 nm/186.159375 THz 3.125GHz spacing";
             }
             enum "1610.38" {
               description "1610.38 nm/186.162500 THz 3.125/6.25/12.5GHz spacing";
             }
             enum "1610.35" {
               description "1610.35 nm/186.165625 THz 3.125GHz spacing";
             }
             enum "1610.33" {
               description "1610.33 nm/186.168750 THz 3.125/6.25GHz spacing";
             }
             enum "1610.30" {
               description "1610.30 nm/186.171875 THz 3.125GHz spacing";
             }
             enum "1610.27" {
               description "1610.27 nm/186.175000 THz 3.125/6.25/12.5GHz spacing";
             }
             enum "1610.25" {
               description "1610.25 nm/186.178125 THz 3.125GHz spacing";
             }
             enum "1610.22" {
               description "1610.22 nm/186.181250 THz 3.125/6.25GHz spacing";
             }
             enum "1610.19" {
               description "1610.19 nm/186.184375 THz 3.125GHz spacing";
             }
             enum "1610.16" {
               description "1610.16 nm/186.187500 THz 3.125/6.25/12.5GHz spacing";
             }
             enum "1610.14" {
               description "1610.14 nm/186.190625 THz 3.125GHz spacing";
             }
             enum "1610.11" {
               description "1610.11 nm/186.193750 THz 3.125/6.25GHz spacing";
             }
             enum "1610.08" {
               description "1610.08 nm/186.196875 THz 3.125GHz spacing";
             }
             enum "1610.06" {
               description "1610.06 nm/186.200000 THz 3.125/6.25/12.5/100GHz spacing";
             }
             enum "1610.03" {
               description "1610.03 nm/186.203125 THz 3.125GHz spacing";
             }
             enum "1610.00" {
               description "1610.00 nm/186.206250 THz 3.125/6.25GHz spacing";
             }
             enum "1609.98" {
               description "1609.98 nm/186.209375 THz 3.125GHz spacing";
             }
             enum "1609.95" {
               description "1609.95 nm/186.212500 THz 3.125/6.25/12.5GHz spacing";
             }
             enum "1609.92" {
               description "1609.92 nm/186.215625 THz 3.125GHz spacing";
             }
             enum "1609.89" {
               description "1609.89 nm/186.218750 THz 3.125/6.25GHz spacing";
             }
             enum "1609.87" {
               description "1609.87 nm/186.221875 THz 3.125GHz spacing";
             }
             enum "1609.84" {
               description "1609.84 nm/186.225000 THz 3.125/6.25/12.5GHz spacing";
             }
             enum "1609.81" {
               description "1609.81 nm/186.228125 THz 3.125GHz spacing";
             }
             enum "1609.79" {
               description "1609.79 nm/186.231250 THz 3.125/6.25GHz spacing";
             }
             enum "1609.76" {
               description "1609.76 nm/186.234375 THz 3.125GHz spacing";
             }
             enum "1609.73" {
               description "1609.73 nm/186.237500 THz 3.125/6.25/12.5GHz spacing";
             }
             enum "1609.70" {
               description "1609.70 nm/186.240625 THz 3.125GHz spacing";
             }
             enum "1609.68" {
               description "1609.68 nm/186.243750 THz 3.125/6.25GHz spacing";
             }
             enum "1609.65" {
               description "1609.65 nm/186.246875 THz 3.125GHz spacing";
             }
             enum "1609.62" {
               description "1609.62 nm/186.250000 THz 3.125/6.25/12.5/50GHz spacing";
             }
             enum "1609.60" {
               description "1609.60 nm/186.253125 THz 3.125GHz spacing";
             }
             enum "1609.57" {
               description "1609.57 nm/186.256250 THz 3.125/6.25GHz spacing";
             }
             enum "1609.54" {
               description "1609.54 nm/186.259375 THz 3.125GHz spacing";
             }
             enum "1609.52" {
               description "1609.52 nm/186.262500 THz 3.125/6.25/12.5GHz spacing";
             }
             enum "1609.49" {
               description "1609.49 nm/186.265625 THz 3.125GHz spacing";
             }
             enum "1609.46" {
               description "1609.46 nm/186.268750 THz 3.125/6.25GHz spacing";
             }
             enum "1609.43" {
               description "1609.43 nm/186.271875 THz 3.125GHz spacing";
             }
             enum "1609.41" {
               description "1609.41 nm/186.275000 THz 3.125/6.25/12.5/75GHz spacing";
             }
             enum "1609.38" {
               description "1609.38 nm/186.278125 THz 3.125GHz spacing";
             }
             enum "1609.35" {
               description "1609.35 nm/186.281250 THz 3.125/6.25GHz spacing";
             }
             enum "1609.33" {
               description "1609.33 nm/186.284375 THz 3.125GHz spacing";
             }
             enum "1609.30" {
               description "1609.30 nm/186.287500 THz 3.125/6.25/12.5GHz spacing";
             }
             enum "1609.27" {
               description "1609.27 nm/186.290625 THz 3.125GHz spacing";
             }
             enum "1609.25" {
               description "1609.25 nm/186.293750 THz 3.125/6.25GHz spacing";
             }
             enum "1609.22" {
               description "1609.22 nm/186.296875 THz 3.125GHz spacing";
             }
             enum "1609.19" {
               description "1609.19 nm/186.300000 THz 3.125/6.25/12.5/50/75/100GHz spacing";
             }
             enum "1609.16" {
               description "1609.16 nm/186.303125 THz 3.125GHz spacing";
             }
             enum "1609.14" {
               description "1609.14 nm/186.306250 THz 3.125/6.25GHz spacing";
             }
             enum "1609.11" {
               description "1609.11 nm/186.309375 THz 3.125GHz spacing";
             }
             enum "1609.08" {
               description "1609.08 nm/186.312500 THz 3.125/6.25/12.5GHz spacing";
             }
             enum "1609.06" {
               description "1609.06 nm/186.315625 THz 3.125GHz spacing";
             }
             enum "1609.03" {
               description "1609.03 nm/186.318750 THz 3.125/6.25GHz spacing";
             }
             enum "1609.00" {
               description "1609.00 nm/186.321875 THz 3.125GHz spacing";
             }
             enum "1608.98" {
               description "1608.98 nm/186.325000 THz 3.125/6.25/12.5GHz spacing";
             }
             enum "1608.95" {
               description "1608.95 nm/186.328125 THz 3.125GHz spacing";
             }
             enum "1608.92" {
               description "1608.92 nm/186.331250 THz 3.125/6.25GHz spacing";
             }
             enum "1608.90" {
               description "1608.90 nm/186.334375 THz 3.125GHz spacing";
             }
             enum "1608.87" {
               description "1608.87 nm/186.337500 THz 3.125/6.25/12.5GHz spacing";
             }
             enum "1608.84" {
               description "1608.84 nm/186.340625 THz 3.125GHz spacing";
             }
             enum "1608.81" {
               description "1608.81 nm/186.343750 THz 3.125/6.25GHz spacing";
             }
             enum "1608.79" {
               description "1608.79 nm/186.346875 THz 3.125GHz spacing";
             }
             enum "1608.76" {
               description "1608.76 nm/186.350000 THz 3.125/6.25/12.5/50/75GHz spacing";
             }
             enum "1608.73" {
               description "1608.73 nm/186.353125 THz 3.125GHz spacing";
             }
             enum "1608.71" {
               description "1608.71 nm/186.356250 THz 3.125/6.25GHz spacing";
             }
             enum "1608.68" {
               description "1608.68 nm/186.359375 THz 3.125GHz spacing";
             }
             enum "1608.65" {
               description "1608.65 nm/186.362500 THz 3.125/6.25/12.5GHz spacing";
             }
             enum "1608.63" {
               description "1608.63 nm/186.365625 THz 3.125GHz spacing";
             }
             enum "1608.60" {
               description "1608.60 nm/186.368750 THz 3.125/6.25GHz spacing";
             }
             enum "1608.57" {
               description "1608.57 nm/186.371875 THz 3.125GHz spacing";
             }
             enum "1608.54" {
               description "1608.54 nm/186.375000 THz 3.125/6.25/12.5GHz spacing";
             }
             enum "1608.52" {
               description "1608.52 nm/186.378125 THz 3.125GHz spacing";
             }
             enum "1608.49" {
               description "1608.49 nm/186.381250 THz 3.125/6.25GHz spacing";
             }
             enum "1608.46" {
               description "1608.46 nm/186.384375 THz 3.125GHz spacing";
             }
             enum "1608.44" {
               description "1608.44 nm/186.387500 THz 3.125/6.25/12.5GHz spacing";
             }
             enum "1608.41" {
               description "1608.41 nm/186.390625 THz 3.125GHz spacing";
             }
             enum "1608.38" {
               description "1608.38 nm/186.393750 THz 3.125/6.25GHz spacing";
             }
             enum "1608.36" {
               description "1608.36 nm/186.396875 THz 3.125GHz spacing";
             }
             enum "1608.33" {
               description "1608.33 nm/186.400000 THz 3.125/6.25/12.5/100GHz spacing";
             }
             enum "1608.30" {
               description "1608.30 nm/186.403125 THz 3.125GHz spacing";
             }
             enum "1608.27" {
               description "1608.27 nm/186.406250 THz 3.125/6.25GHz spacing";
             }
             enum "1608.25" {
               description "1608.25 nm/186.409375 THz 3.125GHz spacing";
             }
             enum "1608.22" {
               description "1608.22 nm/186.412500 THz 3.125/6.25/12.5GHz spacing";
             }
             enum "1608.19" {
               description "1608.19 nm/186.415625 THz 3.125GHz spacing";
             }
             enum "1608.17" {
               description "1608.17 nm/186.418750 THz 3.125/6.25GHz spacing";
             }
             enum "1608.14" {
               description "1608.14 nm/186.421875 THz 3.125GHz spacing";
             }
             enum "1608.11" {
               description "1608.11 nm/186.425000 THz 3.125/6.25/12.5/75GHz spacing";
             }
             enum "1608.09" {
               description "1608.09 nm/186.428125 THz 3.125GHz spacing";
             }
             enum "1608.06" {
               description "1608.06 nm/186.431250 THz 3.125/6.25GHz spacing";
             }
             enum "1608.03" {
               description "1608.03 nm/186.434375 THz 3.125GHz spacing";
             }
             enum "1608.01" {
               description "1608.01 nm/186.437500 THz 3.125/6.25/12.5GHz spacing";
             }
             enum "1607.98" {
               description "1607.98 nm/186.440625 THz 3.125GHz spacing";
             }
             enum "1607.95" {
               description "1607.95 nm/186.443750 THz 3.125/6.25GHz spacing";
             }
             enum "1607.92" {
               description "1607.92 nm/186.446875 THz 3.125GHz spacing";
             }
             enum "1607.90" {
               description "1607.90 nm/186.450000 THz 3.125/6.25/12.5/50GHz spacing";
             }
             enum "1607.87" {
               description "1607.87 nm/186.453125 THz 3.125GHz spacing";
             }
             enum "1607.84" {
               description "1607.84 nm/186.456250 THz 3.125/6.25GHz spacing";
             }
             enum "1607.82" {
               description "1607.82 nm/186.459375 THz 3.125GHz spacing";
             }
             enum "1607.79" {
               description "1607.79 nm/186.462500 THz 3.125/6.25/12.5GHz spacing";
             }
             enum "1607.76" {
               description "1607.76 nm/186.465625 THz 3.125GHz spacing";
             }
             enum "1607.74" {
               description "1607.74 nm/186.468750 THz 3.125/6.25GHz spacing";
             }
             enum "1607.71" {
               description "1607.71 nm/186.471875 THz 3.125GHz spacing";
             }
             enum "1607.68" {
               description "1607.68 nm/186.475000 THz 3.125/6.25/12.5GHz spacing";
             }
             enum "1607.65" {
               description "1607.65 nm/186.478125 THz 3.125GHz spacing";
             }
             enum "1607.63" {
               description "1607.63 nm/186.481250 THz 3.125/6.25GHz spacing";
             }
             enum "1607.60" {
               description "1607.60 nm/186.484375 THz 3.125GHz spacing";
             }
             enum "1607.57" {
               description "1607.57 nm/186.487500 THz 3.125/6.25/12.5GHz spacing";
             }
             enum "1607.55" {
               description "1607.55 nm/186.490625 THz 3.125GHz spacing";
             }
             enum "1607.52" {
               description "1607.52 nm/186.493750 THz 3.125/6.25GHz spacing";
             }
             enum "1607.49" {
               description "1607.49 nm/186.496875 THz 3.125GHz spacing";
             }
             enum "1607.47" {
               description "1607.47 nm/186.500000 THz 3.125/6.25/12.5/100GHz spacing";
             }
             enum "1607.44" {
               description "1607.44 nm/186.503125 THz 3.125GHz spacing";
             }
             enum "1607.41" {
               description "1607.41 nm/186.506250 THz 3.125/6.25GHz spacing";
             }
             enum "1607.39" {
               description "1607.39 nm/186.509375 THz 3.125GHz spacing";
             }
             enum "1607.36" {
               description "1607.36 nm/186.512500 THz 3.125/6.25/12.5GHz spacing";
             }
             enum "1607.33" {
               description "1607.33 nm/186.515625 THz 3.125GHz spacing";
             }
             enum "1607.30" {
               description "1607.30 nm/186.518750 THz 3.125/6.25GHz spacing";
             }
             enum "1607.28" {
               description "1607.28 nm/186.521875 THz 3.125GHz spacing";
             }
             enum "1607.25" {
               description "1607.25 nm/186.525000 THz 3.125/6.25/12.5GHz spacing";
             }
             enum "1607.22" {
               description "1607.22 nm/186.528125 THz 3.125GHz spacing";
             }
             enum "1607.20" {
               description "1607.20 nm/186.531250 THz 3.125/6.25GHz spacing";
             }
             enum "1607.17" {
               description "1607.17 nm/186.534375 THz 3.125GHz spacing";
             }
             enum "1607.14" {
               description "1607.14 nm/186.537500 THz 3.125/6.25/12.5GHz spacing";
             }
             enum "1607.12" {
               description "1607.12 nm/186.540625 THz 3.125GHz spacing";
             }
             enum "1607.09" {
               description "1607.09 nm/186.543750 THz 3.125/6.25GHz spacing";
             }
             enum "1607.06" {
               description "1607.06 nm/186.546875 THz 3.125GHz spacing";
             }
             enum "1607.04" {
               description "1607.04 nm/186.550000 THz 3.125/6.25/12.5/50GHz spacing";
             }
             enum "1607.01" {
               description "1607.01 nm/186.553125 THz 3.125GHz spacing";
             }
             enum "1606.98" {
               description "1606.98 nm/186.556250 THz 3.125/6.25GHz spacing";
             }
             enum "1606.95" {
               description "1606.95 nm/186.559375 THz 3.125GHz spacing";
             }
             enum "1606.93" {
               description "1606.93 nm/186.562500 THz 3.125/6.25/12.5GHz spacing";
             }
             enum "1606.90" {
               description "1606.90 nm/186.565625 THz 3.125GHz spacing";
             }
             enum "1606.87" {
               description "1606.87 nm/186.568750 THz 3.125/6.25GHz spacing";
             }
             enum "1606.85" {
               description "1606.85 nm/186.571875 THz 3.125GHz spacing";
             }
             enum "1606.82" {
               description "1606.82 nm/186.575000 THz 3.125/6.25/12.5/75GHz spacing";
             }
             enum "1606.79" {
               description "1606.79 nm/186.578125 THz 3.125GHz spacing";
             }
             enum "1606.77" {
               description "1606.77 nm/186.581250 THz 3.125/6.25GHz spacing";
             }
             enum "1606.74" {
               description "1606.74 nm/186.584375 THz 3.125GHz spacing";
             }
             enum "1606.71" {
               description "1606.71 nm/186.587500 THz 3.125/6.25/12.5GHz spacing";
             }
             enum "1606.69" {
               description "1606.69 nm/186.590625 THz 3.125GHz spacing";
             }
             enum "1606.66" {
               description "1606.66 nm/186.593750 THz 3.125/6.25GHz spacing";
             }
             enum "1606.63" {
               description "1606.63 nm/186.596875 THz 3.125GHz spacing";
             }
             enum "1606.60" {
               description "1606.60 nm/186.600000 THz 3.125/6.25/12.5/50/75/100GHz spacing";
             }
             enum "1606.58" {
               description "1606.58 nm/186.603125 THz 3.125GHz spacing";
             }
             enum "1606.55" {
               description "1606.55 nm/186.606250 THz 3.125/6.25GHz spacing";
             }
             enum "1606.52" {
               description "1606.52 nm/186.609375 THz 3.125GHz spacing";
             }
             enum "1606.50" {
               description "1606.50 nm/186.612500 THz 3.125/6.25/12.5GHz spacing";
             }
             enum "1606.47" {
               description "1606.47 nm/186.615625 THz 3.125GHz spacing";
             }
             enum "1606.44" {
               description "1606.44 nm/186.618750 THz 3.125/6.25GHz spacing";
             }
             enum "1606.42" {
               description "1606.42 nm/186.621875 THz 3.125GHz spacing";
             }
             enum "1606.39" {
               description "1606.39 nm/186.625000 THz 3.125/6.25/12.5GHz spacing";
             }
             enum "1606.36" {
               description "1606.36 nm/186.628125 THz 3.125GHz spacing";
             }
             enum "1606.34" {
               description "1606.34 nm/186.631250 THz 3.125/6.25GHz spacing";
             }
             enum "1606.31" {
               description "1606.31 nm/186.634375 THz 3.125GHz spacing";
             }
             enum "1606.28" {
               description "1606.28 nm/186.637500 THz 3.125/6.25/12.5GHz spacing";
             }
             enum "1606.26" {
               description "1606.26 nm/186.640625 THz 3.125GHz spacing";
             }
             enum "1606.23" {
               description "1606.23 nm/186.643750 THz 3.125/6.25GHz spacing";
             }
             enum "1606.20" {
               description "1606.20 nm/186.646875 THz 3.125GHz spacing";
             }
             enum "1606.17" {
               description "1606.17 nm/186.650000 THz 3.125/6.25/12.5/50/75GHz spacing";
             }
             enum "1606.15" {
               description "1606.15 nm/186.653125 THz 3.125GHz spacing";
             }
             enum "1606.12" {
               description "1606.12 nm/186.656250 THz 3.125/6.25GHz spacing";
             }
             enum "1606.09" {
               description "1606.09 nm/186.659375 THz 3.125GHz spacing";
             }
             enum "1606.07" {
               description "1606.07 nm/186.662500 THz 3.125/6.25/12.5GHz spacing";
             }
             enum "1606.04" {
               description "1606.04 nm/186.665625 THz 3.125GHz spacing";
             }
             enum "1606.01" {
               description "1606.01 nm/186.668750 THz 3.125/6.25GHz spacing";
             }
             enum "1605.99" {
               description "1605.99 nm/186.671875 THz 3.125GHz spacing";
             }
             enum "1605.96" {
               description "1605.96 nm/186.675000 THz 3.125/6.25/12.5GHz spacing";
             }
             enum "1605.93" {
               description "1605.93 nm/186.678125 THz 3.125GHz spacing";
             }
             enum "1605.91" {
               description "1605.91 nm/186.681250 THz 3.125/6.25GHz spacing";
             }
             enum "1605.88" {
               description "1605.88 nm/186.684375 THz 3.125GHz spacing";
             }
             enum "1605.85" {
               description "1605.85 nm/186.687500 THz 3.125/6.25/12.5GHz spacing";
             }
             enum "1605.82" {
               description "1605.82 nm/186.690625 THz 3.125GHz spacing";
             }
             enum "1605.80" {
               description "1605.80 nm/186.693750 THz 3.125/6.25GHz spacing";
             }
             enum "1605.77" {
               description "1605.77 nm/186.696875 THz 3.125GHz spacing";
             }
             enum "1605.74" {
               description "1605.74 nm/186.700000 THz 3.125/6.25/12.5/100GHz spacing";
             }
             enum "1605.72" {
               description "1605.72 nm/186.703125 THz 3.125GHz spacing";
             }
             enum "1605.69" {
               description "1605.69 nm/186.706250 THz 3.125/6.25GHz spacing";
             }
             enum "1605.66" {
               description "1605.66 nm/186.709375 THz 3.125GHz spacing";
             }
             enum "1605.64" {
               description "1605.64 nm/186.712500 THz 3.125/6.25/12.5GHz spacing";
             }
             enum "1605.61" {
               description "1605.61 nm/186.715625 THz 3.125GHz spacing";
             }
             enum "1605.58" {
               description "1605.58 nm/186.718750 THz 3.125/6.25GHz spacing";
             }
             enum "1605.56" {
               description "1605.56 nm/186.721875 THz 3.125GHz spacing";
             }
             enum "1605.53" {
               description "1605.53 nm/186.725000 THz 3.125/6.25/12.5/75GHz spacing";
             }
             enum "1605.50" {
               description "1605.50 nm/186.728125 THz 3.125GHz spacing";
             }
             enum "1605.48" {
               description "1605.48 nm/186.731250 THz 3.125/6.25GHz spacing";
             }
             enum "1605.45" {
               description "1605.45 nm/186.734375 THz 3.125GHz spacing";
             }
             enum "1605.42" {
               description "1605.42 nm/186.737500 THz 3.125/6.25/12.5GHz spacing";
             }
             enum "1605.39" {
               description "1605.39 nm/186.740625 THz 3.125GHz spacing";
             }
             enum "1605.37" {
               description "1605.37 nm/186.743750 THz 3.125/6.25GHz spacing";
             }
             enum "1605.34" {
               description "1605.34 nm/186.746875 THz 3.125GHz spacing";
             }
             enum "1605.31" {
               description "1605.31 nm/186.750000 THz 3.125/6.25/12.5/50GHz spacing";
             }
             enum "1605.29" {
               description "1605.29 nm/186.753125 THz 3.125GHz spacing";
             }
             enum "1605.26" {
               description "1605.26 nm/186.756250 THz 3.125/6.25GHz spacing";
             }
             enum "1605.23" {
               description "1605.23 nm/186.759375 THz 3.125GHz spacing";
             }
             enum "1605.21" {
               description "1605.21 nm/186.762500 THz 3.125/6.25/12.5GHz spacing";
             }
             enum "1605.18" {
               description "1605.18 nm/186.765625 THz 3.125GHz spacing";
             }
             enum "1605.15" {
               description "1605.15 nm/186.768750 THz 3.125/6.25GHz spacing";
             }
             enum "1605.13" {
               description "1605.13 nm/186.771875 THz 3.125GHz spacing";
             }
             enum "1605.10" {
               description "1605.10 nm/186.775000 THz 3.125/6.25/12.5GHz spacing";
             }
             enum "1605.07" {
               description "1605.07 nm/186.778125 THz 3.125GHz spacing";
             }
             enum "1605.05" {
               description "1605.05 nm/186.781250 THz 3.125/6.25GHz spacing";
             }
             enum "1605.02" {
               description "1605.02 nm/186.784375 THz 3.125GHz spacing";
             }
             enum "1604.99" {
               description "1604.99 nm/186.787500 THz 3.125/6.25/12.5GHz spacing";
             }
             enum "1604.97" {
               description "1604.97 nm/186.790625 THz 3.125GHz spacing";
             }
             enum "1604.94" {
               description "1604.94 nm/186.793750 THz 3.125/6.25GHz spacing";
             }
             enum "1604.91" {
               description "1604.91 nm/186.796875 THz 3.125GHz spacing";
             }
             enum "1604.88" {
               description "1604.88 nm/186.800000 THz 3.125/6.25/12.5/100GHz spacing";
             }
             enum "1604.86" {
               description "1604.86 nm/186.803125 THz 3.125GHz spacing";
             }
             enum "1604.83" {
               description "1604.83 nm/186.806250 THz 3.125/6.25GHz spacing";
             }
             enum "1604.80" {
               description "1604.80 nm/186.809375 THz 3.125GHz spacing";
             }
             enum "1604.78" {
               description "1604.78 nm/186.812500 THz 3.125/6.25/12.5GHz spacing";
             }
             enum "1604.75" {
               description "1604.75 nm/186.815625 THz 3.125GHz spacing";
             }
             enum "1604.72" {
               description "1604.72 nm/186.818750 THz 3.125/6.25GHz spacing";
             }
             enum "1604.70" {
               description "1604.70 nm/186.821875 THz 3.125GHz spacing";
             }
             enum "1604.67" {
               description "1604.67 nm/186.825000 THz 3.125/6.25/12.5GHz spacing";
             }
             enum "1604.64" {
               description "1604.64 nm/186.828125 THz 3.125GHz spacing";
             }
             enum "1604.62" {
               description "1604.62 nm/186.831250 THz 3.125/6.25GHz spacing";
             }
             enum "1604.59" {
               description "1604.59 nm/186.834375 THz 3.125GHz spacing";
             }
             enum "1604.56" {
               description "1604.56 nm/186.837500 THz 3.125/6.25/12.5GHz spacing";
             }
             enum "1604.54" {
               description "1604.54 nm/186.840625 THz 3.125GHz spacing";
             }
             enum "1604.51" {
               description "1604.51 nm/186.843750 THz 3.125/6.25GHz spacing";
             }
             enum "1604.48" {
               description "1604.48 nm/186.846875 THz 3.125GHz spacing";
             }
             enum "1604.46" {
               description "1604.46 nm/186.850000 THz 3.125/6.25/12.5/50GHz spacing";
             }
             enum "1604.43" {
               description "1604.43 nm/186.853125 THz 3.125GHz spacing";
             }
             enum "1604.40" {
               description "1604.40 nm/186.856250 THz 3.125/6.25GHz spacing";
             }
             enum "1604.37" {
               description "1604.37 nm/186.859375 THz 3.125GHz spacing";
             }
             enum "1604.35" {
               description "1604.35 nm/186.862500 THz 3.125/6.25/12.5GHz spacing";
             }
             enum "1604.32" {
               description "1604.32 nm/186.865625 THz 3.125GHz spacing";
             }
             enum "1604.29" {
               description "1604.29 nm/186.868750 THz 3.125/6.25GHz spacing";
             }
             enum "1604.27" {
               description "1604.27 nm/186.871875 THz 3.125GHz spacing";
             }
             enum "1604.24" {
               description "1604.24 nm/186.875000 THz 3.125/6.25/12.5/75GHz spacing";
             }
             enum "1604.21" {
               description "1604.21 nm/186.878125 THz 3.125GHz spacing";
             }
             enum "1604.19" {
               description "1604.19 nm/186.881250 THz 3.125/6.25GHz spacing";
             }
             enum "1604.16" {
               description "1604.16 nm/186.884375 THz 3.125GHz spacing";
             }
             enum "1604.13" {
               description "1604.13 nm/186.887500 THz 3.125/6.25/12.5GHz spacing";
             }
             enum "1604.11" {
               description "1604.11 nm/186.890625 THz 3.125GHz spacing";
             }
             enum "1604.08" {
               description "1604.08 nm/186.893750 THz 3.125/6.25GHz spacing";
             }
             enum "1604.05" {
               description "1604.05 nm/186.896875 THz 3.125GHz spacing";
             }
             enum "1604.03" {
               description "1604.03 nm/186.900000 THz 3.125/6.25/12.5/50/75/100GHz spacing";
             }
             enum "1604.00" {
               description "1604.00 nm/186.903125 THz 3.125GHz spacing";
             }
             enum "1603.97" {
               description "1603.97 nm/186.906250 THz 3.125/6.25GHz spacing";
             }
             enum "1603.95" {
               description "1603.95 nm/186.909375 THz 3.125GHz spacing";
             }
             enum "1603.92" {
               description "1603.92 nm/186.912500 THz 3.125/6.25/12.5GHz spacing";
             }
             enum "1603.89" {
               description "1603.89 nm/186.915625 THz 3.125GHz spacing";
             }
             enum "1603.87" {
               description "1603.87 nm/186.918750 THz 3.125/6.25GHz spacing";
             }
             enum "1603.84" {
               description "1603.84 nm/186.921875 THz 3.125GHz spacing";
             }
             enum "1603.81" {
               description "1603.81 nm/186.925000 THz 3.125/6.25/12.5GHz spacing";
             }
             enum "1603.78" {
               description "1603.78 nm/186.928125 THz 3.125GHz spacing";
             }
             enum "1603.76" {
               description "1603.76 nm/186.931250 THz 3.125/6.25GHz spacing";
             }
             enum "1603.73" {
               description "1603.73 nm/186.934375 THz 3.125GHz spacing";
             }
             enum "1603.70" {
               description "1603.70 nm/186.937500 THz 3.125/6.25/12.5GHz spacing";
             }
             enum "1603.68" {
               description "1603.68 nm/186.940625 THz 3.125GHz spacing";
             }
             enum "1603.65" {
               description "1603.65 nm/186.943750 THz 3.125/6.25GHz spacing";
             }
             enum "1603.62" {
               description "1603.62 nm/186.946875 THz 3.125GHz spacing";
             }
             enum "1603.60" {
               description "1603.60 nm/186.950000 THz 3.125/6.25/12.5/50/75GHz spacing";
             }
             enum "1603.57" {
               description "1603.57 nm/186.953125 THz 3.125GHz spacing";
             }
             enum "1603.54" {
               description "1603.54 nm/186.956250 THz 3.125/6.25GHz spacing";
             }
             enum "1603.52" {
               description "1603.52 nm/186.959375 THz 3.125GHz spacing";
             }
             enum "1603.49" {
               description "1603.49 nm/186.962500 THz 3.125/6.25/12.5GHz spacing";
             }
             enum "1603.46" {
               description "1603.46 nm/186.965625 THz 3.125GHz spacing";
             }
             enum "1603.44" {
               description "1603.44 nm/186.968750 THz 3.125/6.25GHz spacing";
             }
             enum "1603.41" {
               description "1603.41 nm/186.971875 THz 3.125GHz spacing";
             }
             enum "1603.38" {
               description "1603.38 nm/186.975000 THz 3.125/6.25/12.5GHz spacing";
             }
             enum "1603.36" {
               description "1603.36 nm/186.978125 THz 3.125GHz spacing";
             }
             enum "1603.33" {
               description "1603.33 nm/186.981250 THz 3.125/6.25GHz spacing";
             }
             enum "1603.30" {
               description "1603.30 nm/186.984375 THz 3.125GHz spacing";
             }
             enum "1603.28" {
               description "1603.28 nm/186.987500 THz 3.125/6.25/12.5GHz spacing";
             }
             enum "1603.25" {
               description "1603.25 nm/186.990625 THz 3.125GHz spacing";
             }
             enum "1603.22" {
               description "1603.22 nm/186.993750 THz 3.125/6.25GHz spacing";
             }
             enum "1603.20" {
               description "1603.20 nm/186.996875 THz 3.125GHz spacing";
             }
             enum "1603.17" {
               description "1603.17 nm/187.000000 THz 3.125/6.25/12.5/100GHz spacing";
             }
             enum "1603.14" {
               description "1603.14 nm/187.003125 THz 3.125GHz spacing";
             }
             enum "1603.11" {
               description "1603.11 nm/187.006250 THz 3.125/6.25GHz spacing";
             }
             enum "1603.09" {
               description "1603.09 nm/187.009375 THz 3.125GHz spacing";
             }
             enum "1603.06" {
               description "1603.06 nm/187.012500 THz 3.125/6.25/12.5GHz spacing";
             }
             enum "1603.03" {
               description "1603.03 nm/187.015625 THz 3.125GHz spacing";
             }
             enum "1603.01" {
               description "1603.01 nm/187.018750 THz 3.125/6.25GHz spacing";
             }
             enum "1602.98" {
               description "1602.98 nm/187.021875 THz 3.125GHz spacing";
             }
             enum "1602.95" {
               description "1602.95 nm/187.025000 THz 3.125/6.25/12.5/75GHz spacing";
             }
             enum "1602.93" {
               description "1602.93 nm/187.028125 THz 3.125GHz spacing";
             }
             enum "1602.90" {
               description "1602.90 nm/187.031250 THz 3.125/6.25GHz spacing";
             }
             enum "1602.87" {
               description "1602.87 nm/187.034375 THz 3.125GHz spacing";
             }
             enum "1602.85" {
               description "1602.85 nm/187.037500 THz 3.125/6.25/12.5GHz spacing";
             }
             enum "1602.82" {
               description "1602.82 nm/187.040625 THz 3.125GHz spacing";
             }
             enum "1602.79" {
               description "1602.79 nm/187.043750 THz 3.125/6.25GHz spacing";
             }
             enum "1602.77" {
               description "1602.77 nm/187.046875 THz 3.125GHz spacing";
             }
             enum "1602.74" {
               description "1602.74 nm/187.050000 THz 3.125/6.25/12.5/50GHz spacing";
             }
             enum "1602.71" {
               description "1602.71 nm/187.053125 THz 3.125GHz spacing";
             }
             enum "1602.69" {
               description "1602.69 nm/187.056250 THz 3.125/6.25GHz spacing";
             }
             enum "1602.66" {
               description "1602.66 nm/187.059375 THz 3.125GHz spacing";
             }
             enum "1602.63" {
               description "1602.63 nm/187.062500 THz 3.125/6.25/12.5GHz spacing";
             }
             enum "1602.61" {
               description "1602.61 nm/187.065625 THz 3.125GHz spacing";
             }
             enum "1602.58" {
               description "1602.58 nm/187.068750 THz 3.125/6.25GHz spacing";
             }
             enum "1602.55" {
               description "1602.55 nm/187.071875 THz 3.125GHz spacing";
             }
             enum "1602.53" {
               description "1602.53 nm/187.075000 THz 3.125/6.25/12.5GHz spacing";
             }
             enum "1602.50" {
               description "1602.50 nm/187.078125 THz 3.125GHz spacing";
             }
             enum "1602.47" {
               description "1602.47 nm/187.081250 THz 3.125/6.25GHz spacing";
             }
             enum "1602.45" {
               description "1602.45 nm/187.084375 THz 3.125GHz spacing";
             }
             enum "1602.42" {
               description "1602.42 nm/187.087500 THz 3.125/6.25/12.5GHz spacing";
             }
             enum "1602.39" {
               description "1602.39 nm/187.090625 THz 3.125GHz spacing";
             }
             enum "1602.36" {
               description "1602.36 nm/187.093750 THz 3.125/6.25GHz spacing";
             }
             enum "1602.34" {
               description "1602.34 nm/187.096875 THz 3.125GHz spacing";
             }
             enum "1602.31" {
               description "1602.31 nm/187.100000 THz 3.125/6.25/12.5/100GHz spacing";
             }
             enum "1602.28" {
               description "1602.28 nm/187.103125 THz 3.125GHz spacing";
             }
             enum "1602.26" {
               description "1602.26 nm/187.106250 THz 3.125/6.25GHz spacing";
             }
             enum "1602.23" {
               description "1602.23 nm/187.109375 THz 3.125GHz spacing";
             }
             enum "1602.20" {
               description "1602.20 nm/187.112500 THz 3.125/6.25/12.5GHz spacing";
             }
             enum "1602.18" {
               description "1602.18 nm/187.115625 THz 3.125GHz spacing";
             }
             enum "1602.15" {
               description "1602.15 nm/187.118750 THz 3.125/6.25GHz spacing";
             }
             enum "1602.12" {
               description "1602.12 nm/187.121875 THz 3.125GHz spacing";
             }
             enum "1602.10" {
               description "1602.10 nm/187.125000 THz 3.125/6.25/12.5GHz spacing";
             }
             enum "1602.07" {
               description "1602.07 nm/187.128125 THz 3.125GHz spacing";
             }
             enum "1602.04" {
               description "1602.04 nm/187.131250 THz 3.125/6.25GHz spacing";
             }
             enum "1602.02" {
               description "1602.02 nm/187.134375 THz 3.125GHz spacing";
             }
             enum "1601.99" {
               description "1601.99 nm/187.137500 THz 3.125/6.25/12.5GHz spacing";
             }
             enum "1601.96" {
               description "1601.96 nm/187.140625 THz 3.125GHz spacing";
             }
             enum "1601.94" {
               description "1601.94 nm/187.143750 THz 3.125/6.25GHz spacing";
             }
             enum "1601.91" {
               description "1601.91 nm/187.146875 THz 3.125GHz spacing";
             }
             enum "1601.88" {
               description "1601.88 nm/187.150000 THz 3.125/6.25/12.5/50GHz spacing";
             }
             enum "1601.86" {
               description "1601.86 nm/187.153125 THz 3.125GHz spacing";
             }
             enum "1601.83" {
               description "1601.83 nm/187.156250 THz 3.125/6.25GHz spacing";
             }
             enum "1601.80" {
               description "1601.80 nm/187.159375 THz 3.125GHz spacing";
             }
             enum "1601.78" {
               description "1601.78 nm/187.162500 THz 3.125/6.25/12.5GHz spacing";
             }
             enum "1601.75" {
               description "1601.75 nm/187.165625 THz 3.125GHz spacing";
             }
             enum "1601.72" {
               description "1601.72 nm/187.168750 THz 3.125/6.25GHz spacing";
             }
             enum "1601.70" {
               description "1601.70 nm/187.171875 THz 3.125GHz spacing";
             }
             enum "1601.67" {
               description "1601.67 nm/187.175000 THz 3.125/6.25/12.5/75GHz spacing";
             }
             enum "1601.64" {
               description "1601.64 nm/187.178125 THz 3.125GHz spacing";
             }
             enum "1601.62" {
               description "1601.62 nm/187.181250 THz 3.125/6.25GHz spacing";
             }
             enum "1601.59" {
               description "1601.59 nm/187.184375 THz 3.125GHz spacing";
             }
             enum "1601.56" {
               description "1601.56 nm/187.187500 THz 3.125/6.25/12.5GHz spacing";
             }
             enum "1601.54" {
               description "1601.54 nm/187.190625 THz 3.125GHz spacing";
             }
             enum "1601.51" {
               description "1601.51 nm/187.193750 THz 3.125/6.25GHz spacing";
             }
             enum "1601.48" {
               description "1601.48 nm/187.196875 THz 3.125GHz spacing";
             }
             enum "1601.46" {
               description "1601.46 nm/187.200000 THz 3.125/6.25/12.5/50/75/100GHz spacing";
             }
             enum "1601.43" {
               description "1601.43 nm/187.203125 THz 3.125GHz spacing";
             }
             enum "1601.40" {
               description "1601.40 nm/187.206250 THz 3.125/6.25GHz spacing";
             }
             enum "1601.38" {
               description "1601.38 nm/187.209375 THz 3.125GHz spacing";
             }
             enum "1601.35" {
               description "1601.35 nm/187.212500 THz 3.125/6.25/12.5GHz spacing";
             }
             enum "1601.32" {
               description "1601.32 nm/187.215625 THz 3.125GHz spacing";
             }
             enum "1601.30" {
               description "1601.30 nm/187.218750 THz 3.125/6.25GHz spacing";
             }
             enum "1601.27" {
               description "1601.27 nm/187.221875 THz 3.125GHz spacing";
             }
             enum "1601.24" {
               description "1601.24 nm/187.225000 THz 3.125/6.25/12.5GHz spacing";
             }
             enum "1601.21" {
               description "1601.21 nm/187.228125 THz 3.125GHz spacing";
             }
             enum "1601.19" {
               description "1601.19 nm/187.231250 THz 3.125/6.25GHz spacing";
             }
             enum "1601.16" {
               description "1601.16 nm/187.234375 THz 3.125GHz spacing";
             }
             enum "1601.13" {
               description "1601.13 nm/187.237500 THz 3.125/6.25/12.5GHz spacing";
             }
             enum "1601.11" {
               description "1601.11 nm/187.240625 THz 3.125GHz spacing";
             }
             enum "1601.08" {
               description "1601.08 nm/187.243750 THz 3.125/6.25GHz spacing";
             }
             enum "1601.05" {
               description "1601.05 nm/187.246875 THz 3.125GHz spacing";
             }
             enum "1601.03" {
               description "1601.03 nm/187.250000 THz 3.125/6.25/12.5/50/75GHz spacing";
             }
             enum "1601.00" {
               description "1601.00 nm/187.253125 THz 3.125GHz spacing";
             }
             enum "1600.97" {
               description "1600.97 nm/187.256250 THz 3.125/6.25GHz spacing";
             }
             enum "1600.95" {
               description "1600.95 nm/187.259375 THz 3.125GHz spacing";
             }
             enum "1600.92" {
               description "1600.92 nm/187.262500 THz 3.125/6.25/12.5GHz spacing";
             }
             enum "1600.89" {
               description "1600.89 nm/187.265625 THz 3.125GHz spacing";
             }
             enum "1600.87" {
               description "1600.87 nm/187.268750 THz 3.125/6.25GHz spacing";
             }
             enum "1600.84" {
               description "1600.84 nm/187.271875 THz 3.125GHz spacing";
             }
             enum "1600.81" {
               description "1600.81 nm/187.275000 THz 3.125/6.25/12.5GHz spacing";
             }
             enum "1600.79" {
               description "1600.79 nm/187.278125 THz 3.125GHz spacing";
             }
             enum "1600.76" {
               description "1600.76 nm/187.281250 THz 3.125/6.25GHz spacing";
             }
             enum "1600.73" {
               description "1600.73 nm/187.284375 THz 3.125GHz spacing";
             }
             enum "1600.71" {
               description "1600.71 nm/187.287500 THz 3.125/6.25/12.5GHz spacing";
             }
             enum "1600.68" {
               description "1600.68 nm/187.290625 THz 3.125GHz spacing";
             }
             enum "1600.65" {
               description "1600.65 nm/187.293750 THz 3.125/6.25GHz spacing";
             }
             enum "1600.63" {
               description "1600.63 nm/187.296875 THz 3.125GHz spacing";
             }
             enum "1600.60" {
               description "1600.60 nm/187.300000 THz 3.125/6.25/12.5/100GHz spacing";
             }
             enum "1600.57" {
               description "1600.57 nm/187.303125 THz 3.125GHz spacing";
             }
             enum "1600.55" {
               description "1600.55 nm/187.306250 THz 3.125/6.25GHz spacing";
             }
             enum "1600.52" {
               description "1600.52 nm/187.309375 THz 3.125GHz spacing";
             }
             enum "1600.49" {
               description "1600.49 nm/187.312500 THz 3.125/6.25/12.5GHz spacing";
             }
             enum "1600.47" {
               description "1600.47 nm/187.315625 THz 3.125GHz spacing";
             }
             enum "1600.44" {
               description "1600.44 nm/187.318750 THz 3.125/6.25GHz spacing";
             }
             enum "1600.41" {
               description "1600.41 nm/187.321875 THz 3.125GHz spacing";
             }
             enum "1600.39" {
               description "1600.39 nm/187.325000 THz 3.125/6.25/12.5/75GHz spacing";
             }
             enum "1600.36" {
               description "1600.36 nm/187.328125 THz 3.125GHz spacing";
             }
             enum "1600.33" {
               description "1600.33 nm/187.331250 THz 3.125/6.25GHz spacing";
             }
             enum "1600.31" {
               description "1600.31 nm/187.334375 THz 3.125GHz spacing";
             }
             enum "1600.28" {
               description "1600.28 nm/187.337500 THz 3.125/6.25/12.5GHz spacing";
             }
             enum "1600.25" {
               description "1600.25 nm/187.340625 THz 3.125GHz spacing";
             }
             enum "1600.23" {
               description "1600.23 nm/187.343750 THz 3.125/6.25GHz spacing";
             }
             enum "1600.20" {
               description "1600.20 nm/187.346875 THz 3.125GHz spacing";
             }
             enum "1600.17" {
               description "1600.17 nm/187.350000 THz 3.125/6.25/12.5/50GHz spacing";
             }
             enum "1600.15" {
               description "1600.15 nm/187.353125 THz 3.125GHz spacing";
             }
             enum "1600.12" {
               description "1600.12 nm/187.356250 THz 3.125/6.25GHz spacing";
             }
             enum "1600.09" {
               description "1600.09 nm/187.359375 THz 3.125GHz spacing";
             }
             enum "1600.07" {
               description "1600.07 nm/187.362500 THz 3.125/6.25/12.5GHz spacing";
             }
             enum "1600.04" {
               description "1600.04 nm/187.365625 THz 3.125GHz spacing";
             }
             enum "1600.01" {
               description "1600.01 nm/187.368750 THz 3.125/6.25GHz spacing";
             }
             enum "1599.99" {
               description "1599.99 nm/187.371875 THz 3.125GHz spacing";
             }
             enum "1599.96" {
               description "1599.96 nm/187.375000 THz 3.125/6.25/12.5GHz spacing";
             }
             enum "1599.93" {
               description "1599.93 nm/187.378125 THz 3.125GHz spacing";
             }
             enum "1599.91" {
               description "1599.91 nm/187.381250 THz 3.125/6.25GHz spacing";
             }
             enum "1599.88" {
               description "1599.88 nm/187.384375 THz 3.125GHz spacing";
             }
             enum "1599.85" {
               description "1599.85 nm/187.387500 THz 3.125/6.25/12.5GHz spacing";
             }
             enum "1599.83" {
               description "1599.83 nm/187.390625 THz 3.125GHz spacing";
             }
             enum "1599.80" {
               description "1599.80 nm/187.393750 THz 3.125/6.25GHz spacing";
             }
             enum "1599.77" {
               description "1599.77 nm/187.396875 THz 3.125GHz spacing";
             }
             enum "1599.75" {
               description "1599.75 nm/187.400000 THz 3.125/6.25/12.5/100GHz spacing";
             }
             enum "1599.72" {
               description "1599.72 nm/187.403125 THz 3.125GHz spacing";
             }
             enum "1599.69" {
               description "1599.69 nm/187.406250 THz 3.125/6.25GHz spacing";
             }
             enum "1599.67" {
               description "1599.67 nm/187.409375 THz 3.125GHz spacing";
             }
             enum "1599.64" {
               description "1599.64 nm/187.412500 THz 3.125/6.25/12.5GHz spacing";
             }
             enum "1599.61" {
               description "1599.61 nm/187.415625 THz 3.125GHz spacing";
             }
             enum "1599.59" {
               description "1599.59 nm/187.418750 THz 3.125/6.25GHz spacing";
             }
             enum "1599.56" {
               description "1599.56 nm/187.421875 THz 3.125GHz spacing";
             }
             enum "1599.53" {
               description "1599.53 nm/187.425000 THz 3.125/6.25/12.5GHz spacing";
             }
             enum "1599.51" {
               description "1599.51 nm/187.428125 THz 3.125GHz spacing";
             }
             enum "1599.48" {
               description "1599.48 nm/187.431250 THz 3.125/6.25GHz spacing";
             }
             enum "1599.45" {
               description "1599.45 nm/187.434375 THz 3.125GHz spacing";
             }
             enum "1599.43" {
               description "1599.43 nm/187.437500 THz 3.125/6.25/12.5GHz spacing";
             }
             enum "1599.40" {
               description "1599.40 nm/187.440625 THz 3.125GHz spacing";
             }
             enum "1599.37" {
               description "1599.37 nm/187.443750 THz 3.125/6.25GHz spacing";
             }
             enum "1599.35" {
               description "1599.35 nm/187.446875 THz 3.125GHz spacing";
             }
             enum "1599.32" {
               description "1599.32 nm/187.450000 THz 3.125/6.25/12.5/50GHz spacing";
             }
             enum "1599.29" {
               description "1599.29 nm/187.453125 THz 3.125GHz spacing";
             }
             enum "1599.27" {
               description "1599.27 nm/187.456250 THz 3.125/6.25GHz spacing";
             }
             enum "1599.24" {
               description "1599.24 nm/187.459375 THz 3.125GHz spacing";
             }
             enum "1599.21" {
               description "1599.21 nm/187.462500 THz 3.125/6.25/12.5GHz spacing";
             }
             enum "1599.19" {
               description "1599.19 nm/187.465625 THz 3.125GHz spacing";
             }
             enum "1599.16" {
               description "1599.16 nm/187.468750 THz 3.125/6.25GHz spacing";
             }
             enum "1599.13" {
               description "1599.13 nm/187.471875 THz 3.125GHz spacing";
             }
             enum "1599.11" {
               description "1599.11 nm/187.475000 THz 3.125/6.25/12.5/75GHz spacing";
             }
             enum "1599.08" {
               description "1599.08 nm/187.478125 THz 3.125GHz spacing";
             }
             enum "1599.05" {
               description "1599.05 nm/187.481250 THz 3.125/6.25GHz spacing";
             }
             enum "1599.03" {
               description "1599.03 nm/187.484375 THz 3.125GHz spacing";
             }
             enum "1599.00" {
               description "1599.00 nm/187.487500 THz 3.125/6.25/12.5GHz spacing";
             }
             enum "1598.97" {
               description "1598.97 nm/187.490625 THz 3.125GHz spacing";
             }
             enum "1598.95" {
               description "1598.95 nm/187.493750 THz 3.125/6.25GHz spacing";
             }
             enum "1598.92" {
               description "1598.92 nm/187.496875 THz 3.125GHz spacing";
             }
             enum "1598.89" {
               description "1598.89 nm/187.500000 THz 3.125/6.25/12.5/50/75/100GHz spacing";
             }
             enum "1598.87" {
               description "1598.87 nm/187.503125 THz 3.125GHz spacing";
             }
             enum "1598.84" {
               description "1598.84 nm/187.506250 THz 3.125/6.25GHz spacing";
             }
             enum "1598.81" {
               description "1598.81 nm/187.509375 THz 3.125GHz spacing";
             }
             enum "1598.79" {
               description "1598.79 nm/187.512500 THz 3.125/6.25/12.5GHz spacing";
             }
             enum "1598.76" {
               description "1598.76 nm/187.515625 THz 3.125GHz spacing";
             }
             enum "1598.73" {
               description "1598.73 nm/187.518750 THz 3.125/6.25GHz spacing";
             }
             enum "1598.71" {
               description "1598.71 nm/187.521875 THz 3.125GHz spacing";
             }
             enum "1598.68" {
               description "1598.68 nm/187.525000 THz 3.125/6.25/12.5GHz spacing";
             }
             enum "1598.65" {
               description "1598.65 nm/187.528125 THz 3.125GHz spacing";
             }
             enum "1598.63" {
               description "1598.63 nm/187.531250 THz 3.125/6.25GHz spacing";
             }
             enum "1598.60" {
               description "1598.60 nm/187.534375 THz 3.125GHz spacing";
             }
             enum "1598.57" {
               description "1598.57 nm/187.537500 THz 3.125/6.25/12.5GHz spacing";
             }
             enum "1598.55" {
               description "1598.55 nm/187.540625 THz 3.125GHz spacing";
             }
             enum "1598.52" {
               description "1598.52 nm/187.543750 THz 3.125/6.25GHz spacing";
             }
             enum "1598.49" {
               description "1598.49 nm/187.546875 THz 3.125GHz spacing";
             }
             enum "1598.47" {
               description "1598.47 nm/187.550000 THz 3.125/6.25/12.5/50/75GHz spacing";
             }
             enum "1598.44" {
               description "1598.44 nm/187.553125 THz 3.125GHz spacing";
             }
             enum "1598.41" {
               description "1598.41 nm/187.556250 THz 3.125/6.25GHz spacing";
             }
             enum "1598.39" {
               description "1598.39 nm/187.559375 THz 3.125GHz spacing";
             }
             enum "1598.36" {
               description "1598.36 nm/187.562500 THz 3.125/6.25/12.5GHz spacing";
             }
             enum "1598.33" {
               description "1598.33 nm/187.565625 THz 3.125GHz spacing";
             }
             enum "1598.31" {
               description "1598.31 nm/187.568750 THz 3.125/6.25GHz spacing";
             }
             enum "1598.28" {
               description "1598.28 nm/187.571875 THz 3.125GHz spacing";
             }
             enum "1598.25" {
               description "1598.25 nm/187.575000 THz 3.125/6.25/12.5GHz spacing";
             }
             enum "1598.23" {
               description "1598.23 nm/187.578125 THz 3.125GHz spacing";
             }
             enum "1598.20" {
               description "1598.20 nm/187.581250 THz 3.125/6.25GHz spacing";
             }
             enum "1598.17" {
               description "1598.17 nm/187.584375 THz 3.125GHz spacing";
             }
             enum "1598.15" {
               description "1598.15 nm/187.587500 THz 3.125/6.25/12.5GHz spacing";
             }
             enum "1598.12" {
               description "1598.12 nm/187.590625 THz 3.125GHz spacing";
             }
             enum "1598.09" {
               description "1598.09 nm/187.593750 THz 3.125/6.25GHz spacing";
             }
             enum "1598.07" {
               description "1598.07 nm/187.596875 THz 3.125GHz spacing";
             }
             enum "1598.04" {
               description "1598.04 nm/187.600000 THz 3.125/6.25/12.5/100GHz spacing";
             }
             enum "1598.01" {
               description "1598.01 nm/187.603125 THz 3.125GHz spacing";
             }
             enum "1597.99" {
               description "1597.99 nm/187.606250 THz 3.125/6.25GHz spacing";
             }
             enum "1597.96" {
               description "1597.96 nm/187.609375 THz 3.125GHz spacing";
             }
             enum "1597.93" {
               description "1597.93 nm/187.612500 THz 3.125/6.25/12.5GHz spacing";
             }
             enum "1597.91" {
               description "1597.91 nm/187.615625 THz 3.125GHz spacing";
             }
             enum "1597.88" {
               description "1597.88 nm/187.618750 THz 3.125/6.25GHz spacing";
             }
             enum "1597.85" {
               description "1597.85 nm/187.621875 THz 3.125GHz spacing";
             }
             enum "1597.83" {
               description "1597.83 nm/187.625000 THz 3.125/6.25/12.5/75GHz spacing";
             }
             enum "1597.80" {
               description "1597.80 nm/187.628125 THz 3.125GHz spacing";
             }
             enum "1597.77" {
               description "1597.77 nm/187.631250 THz 3.125/6.25GHz spacing";
             }
             enum "1597.75" {
               description "1597.75 nm/187.634375 THz 3.125GHz spacing";
             }
             enum "1597.72" {
               description "1597.72 nm/187.637500 THz 3.125/6.25/12.5GHz spacing";
             }
             enum "1597.69" {
               description "1597.69 nm/187.640625 THz 3.125GHz spacing";
             }
             enum "1597.67" {
               description "1597.67 nm/187.643750 THz 3.125/6.25GHz spacing";
             }
             enum "1597.64" {
               description "1597.64 nm/187.646875 THz 3.125GHz spacing";
             }
             enum "1597.62" {
               description "1597.62 nm/187.650000 THz 3.125/6.25/12.5/50GHz spacing";
             }
             enum "1597.59" {
               description "1597.59 nm/187.653125 THz 3.125GHz spacing";
             }
             enum "1597.56" {
               description "1597.56 nm/187.656250 THz 3.125/6.25GHz spacing";
             }
             enum "1597.54" {
               description "1597.54 nm/187.659375 THz 3.125GHz spacing";
             }
             enum "1597.51" {
               description "1597.51 nm/187.662500 THz 3.125/6.25/12.5GHz spacing";
             }
             enum "1597.48" {
               description "1597.48 nm/187.665625 THz 3.125GHz spacing";
             }
             enum "1597.46" {
               description "1597.46 nm/187.668750 THz 3.125/6.25GHz spacing";
             }
             enum "1597.43" {
               description "1597.43 nm/187.671875 THz 3.125GHz spacing";
             }
             enum "1597.40" {
               description "1597.40 nm/187.675000 THz 3.125/6.25/12.5GHz spacing";
             }
             enum "1597.38" {
               description "1597.38 nm/187.678125 THz 3.125GHz spacing";
             }
             enum "1597.35" {
               description "1597.35 nm/187.681250 THz 3.125/6.25GHz spacing";
             }
             enum "1597.32" {
               description "1597.32 nm/187.684375 THz 3.125GHz spacing";
             }
             enum "1597.30" {
               description "1597.30 nm/187.687500 THz 3.125/6.25/12.5GHz spacing";
             }
             enum "1597.27" {
               description "1597.27 nm/187.690625 THz 3.125GHz spacing";
             }
             enum "1597.24" {
               description "1597.24 nm/187.693750 THz 3.125/6.25GHz spacing";
             }
             enum "1597.22" {
               description "1597.22 nm/187.696875 THz 3.125GHz spacing";
             }
             enum "1597.19" {
               description "1597.19 nm/187.700000 THz 3.125/6.25/12.5/100GHz spacing";
             }
             enum "1597.16" {
               description "1597.16 nm/187.703125 THz 3.125GHz spacing";
             }
             enum "1597.14" {
               description "1597.14 nm/187.706250 THz 3.125/6.25GHz spacing";
             }
             enum "1597.11" {
               description "1597.11 nm/187.709375 THz 3.125GHz spacing";
             }
             enum "1597.08" {
               description "1597.08 nm/187.712500 THz 3.125/6.25/12.5GHz spacing";
             }
             enum "1597.06" {
               description "1597.06 nm/187.715625 THz 3.125GHz spacing";
             }
             enum "1597.03" {
               description "1597.03 nm/187.718750 THz 3.125/6.25GHz spacing";
             }
             enum "1597.00" {
               description "1597.00 nm/187.721875 THz 3.125GHz spacing";
             }
             enum "1596.98" {
               description "1596.98 nm/187.725000 THz 3.125/6.25/12.5GHz spacing";
             }
             enum "1596.95" {
               description "1596.95 nm/187.728125 THz 3.125GHz spacing";
             }
             enum "1596.92" {
               description "1596.92 nm/187.731250 THz 3.125/6.25GHz spacing";
             }
             enum "1596.90" {
               description "1596.90 nm/187.734375 THz 3.125GHz spacing";
             }
             enum "1596.87" {
               description "1596.87 nm/187.737500 THz 3.125/6.25/12.5GHz spacing";
             }
             enum "1596.84" {
               description "1596.84 nm/187.740625 THz 3.125GHz spacing";
             }
             enum "1596.82" {
               description "1596.82 nm/187.743750 THz 3.125/6.25GHz spacing";
             }
             enum "1596.79" {
               description "1596.79 nm/187.746875 THz 3.125GHz spacing";
             }
             enum "1596.76" {
               description "1596.76 nm/187.750000 THz 3.125/6.25/12.5/50GHz spacing";
             }
             enum "1596.74" {
               description "1596.74 nm/187.753125 THz 3.125GHz spacing";
             }
             enum "1596.71" {
               description "1596.71 nm/187.756250 THz 3.125/6.25GHz spacing";
             }
             enum "1596.68" {
               description "1596.68 nm/187.759375 THz 3.125GHz spacing";
             }
             enum "1596.66" {
               description "1596.66 nm/187.762500 THz 3.125/6.25/12.5GHz spacing";
             }
             enum "1596.63" {
               description "1596.63 nm/187.765625 THz 3.125GHz spacing";
             }
             enum "1596.60" {
               description "1596.60 nm/187.768750 THz 3.125/6.25GHz spacing";
             }
             enum "1596.58" {
               description "1596.58 nm/187.771875 THz 3.125GHz spacing";
             }
             enum "1596.55" {
               description "1596.55 nm/187.775000 THz 3.125/6.25/12.5/75GHz spacing";
             }
             enum "1596.52" {
               description "1596.52 nm/187.778125 THz 3.125GHz spacing";
             }
             enum "1596.50" {
               description "1596.50 nm/187.781250 THz 3.125/6.25GHz spacing";
             }
             enum "1596.47" {
               description "1596.47 nm/187.784375 THz 3.125GHz spacing";
             }
             enum "1596.45" {
               description "1596.45 nm/187.787500 THz 3.125/6.25/12.5GHz spacing";
             }
             enum "1596.42" {
               description "1596.42 nm/187.790625 THz 3.125GHz spacing";
             }
             enum "1596.39" {
               description "1596.39 nm/187.793750 THz 3.125/6.25GHz spacing";
             }
             enum "1596.37" {
               description "1596.37 nm/187.796875 THz 3.125GHz spacing";
             }
             enum "1596.34" {
               description "1596.34 nm/187.800000 THz 3.125/6.25/12.5/50/75/100GHz spacing";
             }
             enum "1596.31" {
               description "1596.31 nm/187.803125 THz 3.125GHz spacing";
             }
             enum "1596.29" {
               description "1596.29 nm/187.806250 THz 3.125/6.25GHz spacing";
             }
             enum "1596.26" {
               description "1596.26 nm/187.809375 THz 3.125GHz spacing";
             }
             enum "1596.23" {
               description "1596.23 nm/187.812500 THz 3.125/6.25/12.5GHz spacing";
             }
             enum "1596.21" {
               description "1596.21 nm/187.815625 THz 3.125GHz spacing";
             }
             enum "1596.18" {
               description "1596.18 nm/187.818750 THz 3.125/6.25GHz spacing";
             }
             enum "1596.15" {
               description "1596.15 nm/187.821875 THz 3.125GHz spacing";
             }
             enum "1596.13" {
               description "1596.13 nm/187.825000 THz 3.125/6.25/12.5GHz spacing";
             }
             enum "1596.10" {
               description "1596.10 nm/187.828125 THz 3.125GHz spacing";
             }
             enum "1596.07" {
               description "1596.07 nm/187.831250 THz 3.125/6.25GHz spacing";
             }
             enum "1596.05" {
               description "1596.05 nm/187.834375 THz 3.125GHz spacing";
             }
             enum "1596.02" {
               description "1596.02 nm/187.837500 THz 3.125/6.25/12.5GHz spacing";
             }
             enum "1595.99" {
               description "1595.99 nm/187.840625 THz 3.125GHz spacing";
             }
             enum "1595.97" {
               description "1595.97 nm/187.843750 THz 3.125/6.25GHz spacing";
             }
             enum "1595.94" {
               description "1595.94 nm/187.846875 THz 3.125GHz spacing";
             }
             enum "1595.91" {
               description "1595.91 nm/187.850000 THz 3.125/6.25/12.5/50/75GHz spacing";
             }
             enum "1595.89" {
               description "1595.89 nm/187.853125 THz 3.125GHz spacing";
             }
             enum "1595.86" {
               description "1595.86 nm/187.856250 THz 3.125/6.25GHz spacing";
             }
             enum "1595.83" {
               description "1595.83 nm/187.859375 THz 3.125GHz spacing";
             }
             enum "1595.81" {
               description "1595.81 nm/187.862500 THz 3.125/6.25/12.5GHz spacing";
             }
             enum "1595.78" {
               description "1595.78 nm/187.865625 THz 3.125GHz spacing";
             }
             enum "1595.75" {
               description "1595.75 nm/187.868750 THz 3.125/6.25GHz spacing";
             }
             enum "1595.73" {
               description "1595.73 nm/187.871875 THz 3.125GHz spacing";
             }
             enum "1595.70" {
               description "1595.70 nm/187.875000 THz 3.125/6.25/12.5GHz spacing";
             }
             enum "1595.68" {
               description "1595.68 nm/187.878125 THz 3.125GHz spacing";
             }
             enum "1595.65" {
               description "1595.65 nm/187.881250 THz 3.125/6.25GHz spacing";
             }
             enum "1595.62" {
               description "1595.62 nm/187.884375 THz 3.125GHz spacing";
             }
             enum "1595.60" {
               description "1595.60 nm/187.887500 THz 3.125/6.25/12.5GHz spacing";
             }
             enum "1595.57" {
               description "1595.57 nm/187.890625 THz 3.125GHz spacing";
             }
             enum "1595.54" {
               description "1595.54 nm/187.893750 THz 3.125/6.25GHz spacing";
             }
             enum "1595.52" {
               description "1595.52 nm/187.896875 THz 3.125GHz spacing";
             }
             enum "1595.49" {
               description "1595.49 nm/187.900000 THz 3.125/6.25/12.5/100GHz spacing";
             }
             enum "1595.46" {
               description "1595.46 nm/187.903125 THz 3.125GHz spacing";
             }
             enum "1595.44" {
               description "1595.44 nm/187.906250 THz 3.125/6.25GHz spacing";
             }
             enum "1595.41" {
               description "1595.41 nm/187.909375 THz 3.125GHz spacing";
             }
             enum "1595.38" {
               description "1595.38 nm/187.912500 THz 3.125/6.25/12.5GHz spacing";
             }
             enum "1595.36" {
               description "1595.36 nm/187.915625 THz 3.125GHz spacing";
             }
             enum "1595.33" {
               description "1595.33 nm/187.918750 THz 3.125/6.25GHz spacing";
             }
             enum "1595.30" {
               description "1595.30 nm/187.921875 THz 3.125GHz spacing";
             }
             enum "1595.28" {
               description "1595.28 nm/187.925000 THz 3.125/6.25/12.5/75GHz spacing";
             }
             enum "1595.25" {
               description "1595.25 nm/187.928125 THz 3.125GHz spacing";
             }
             enum "1595.22" {
               description "1595.22 nm/187.931250 THz 3.125/6.25GHz spacing";
             }
             enum "1595.20" {
               description "1595.20 nm/187.934375 THz 3.125GHz spacing";
             }
             enum "1595.17" {
               description "1595.17 nm/187.937500 THz 3.125/6.25/12.5GHz spacing";
             }
             enum "1595.14" {
               description "1595.14 nm/187.940625 THz 3.125GHz spacing";
             }
             enum "1595.12" {
               description "1595.12 nm/187.943750 THz 3.125/6.25GHz spacing";
             }
             enum "1595.09" {
               description "1595.09 nm/187.946875 THz 3.125GHz spacing";
             }
             enum "1595.06" {
               description "1595.06 nm/187.950000 THz 3.125/6.25/12.5/50GHz spacing";
             }
             enum "1595.04" {
               description "1595.04 nm/187.953125 THz 3.125GHz spacing";
             }
             enum "1595.01" {
               description "1595.01 nm/187.956250 THz 3.125/6.25GHz spacing";
             }
             enum "1594.99" {
               description "1594.99 nm/187.959375 THz 3.125GHz spacing";
             }
             enum "1594.96" {
               description "1594.96 nm/187.962500 THz 3.125/6.25/12.5GHz spacing";
             }
             enum "1594.93" {
               description "1594.93 nm/187.965625 THz 3.125GHz spacing";
             }
             enum "1594.91" {
               description "1594.91 nm/187.968750 THz 3.125/6.25GHz spacing";
             }
             enum "1594.88" {
               description "1594.88 nm/187.971875 THz 3.125GHz spacing";
             }
             enum "1594.85" {
               description "1594.85 nm/187.975000 THz 3.125/6.25/12.5GHz spacing";
             }
             enum "1594.83" {
               description "1594.83 nm/187.978125 THz 3.125GHz spacing";
             }
             enum "1594.80" {
               description "1594.80 nm/187.981250 THz 3.125/6.25GHz spacing";
             }
             enum "1594.77" {
               description "1594.77 nm/187.984375 THz 3.125GHz spacing";
             }
             enum "1594.75" {
               description "1594.75 nm/187.987500 THz 3.125/6.25/12.5GHz spacing";
             }
             enum "1594.72" {
               description "1594.72 nm/187.990625 THz 3.125GHz spacing";
             }
             enum "1594.69" {
               description "1594.69 nm/187.993750 THz 3.125/6.25GHz spacing";
             }
             enum "1594.67" {
               description "1594.67 nm/187.996875 THz 3.125GHz spacing";
             }
             enum "1594.64" {
               description "1594.64 nm/188.000000 THz 3.125/6.25/12.5/100GHz spacing";
             }
             enum "1594.61" {
               description "1594.61 nm/188.003125 THz 3.125GHz spacing";
             }
             enum "1594.59" {
               description "1594.59 nm/188.006250 THz 3.125/6.25GHz spacing";
             }
             enum "1594.56" {
               description "1594.56 nm/188.009375 THz 3.125GHz spacing";
             }
             enum "1594.53" {
               description "1594.53 nm/188.012500 THz 3.125/6.25/12.5GHz spacing";
             }
             enum "1594.51" {
               description "1594.51 nm/188.015625 THz 3.125GHz spacing";
             }
             enum "1594.48" {
               description "1594.48 nm/188.018750 THz 3.125/6.25GHz spacing";
             }
             enum "1594.46" {
               description "1594.46 nm/188.021875 THz 3.125GHz spacing";
             }
             enum "1594.43" {
               description "1594.43 nm/188.025000 THz 3.125/6.25/12.5GHz spacing";
             }
             enum "1594.40" {
               description "1594.40 nm/188.028125 THz 3.125GHz spacing";
             }
             enum "1594.38" {
               description "1594.38 nm/188.031250 THz 3.125/6.25GHz spacing";
             }
             enum "1594.35" {
               description "1594.35 nm/188.034375 THz 3.125GHz spacing";
             }
             enum "1594.32" {
               description "1594.32 nm/188.037500 THz 3.125/6.25/12.5GHz spacing";
             }
             enum "1594.30" {
               description "1594.30 nm/188.040625 THz 3.125GHz spacing";
             }
             enum "1594.27" {
               description "1594.27 nm/188.043750 THz 3.125/6.25GHz spacing";
             }
             enum "1594.24" {
               description "1594.24 nm/188.046875 THz 3.125GHz spacing";
             }
             enum "1594.22" {
               description "1594.22 nm/188.050000 THz 3.125/6.25/12.5/50GHz spacing";
             }
             enum "1594.19" {
               description "1594.19 nm/188.053125 THz 3.125GHz spacing";
             }
             enum "1594.16" {
               description "1594.16 nm/188.056250 THz 3.125/6.25GHz spacing";
             }
             enum "1594.14" {
               description "1594.14 nm/188.059375 THz 3.125GHz spacing";
             }
             enum "1594.11" {
               description "1594.11 nm/188.062500 THz 3.125/6.25/12.5GHz spacing";
             }
             enum "1594.08" {
               description "1594.08 nm/188.065625 THz 3.125GHz spacing";
             }
             enum "1594.06" {
               description "1594.06 nm/188.068750 THz 3.125/6.25GHz spacing";
             }
             enum "1594.03" {
               description "1594.03 nm/188.071875 THz 3.125GHz spacing";
             }
             enum "1594.00" {
               description "1594.00 nm/188.075000 THz 3.125/6.25/12.5/75GHz spacing";
             }
             enum "1593.98" {
               description "1593.98 nm/188.078125 THz 3.125GHz spacing";
             }
             enum "1593.95" {
               description "1593.95 nm/188.081250 THz 3.125/6.25GHz spacing";
             }
             enum "1593.93" {
               description "1593.93 nm/188.084375 THz 3.125GHz spacing";
             }
             enum "1593.90" {
               description "1593.90 nm/188.087500 THz 3.125/6.25/12.5GHz spacing";
             }
             enum "1593.87" {
               description "1593.87 nm/188.090625 THz 3.125GHz spacing";
             }
             enum "1593.85" {
               description "1593.85 nm/188.093750 THz 3.125/6.25GHz spacing";
             }
             enum "1593.82" {
               description "1593.82 nm/188.096875 THz 3.125GHz spacing";
             }
             enum "1593.79" {
               description "1593.79 nm/188.100000 THz 3.125/6.25/12.5/50/75/100GHz spacing";
             }
             enum "1593.77" {
               description "1593.77 nm/188.103125 THz 3.125GHz spacing";
             }
             enum "1593.74" {
               description "1593.74 nm/188.106250 THz 3.125/6.25GHz spacing";
             }
             enum "1593.71" {
               description "1593.71 nm/188.109375 THz 3.125GHz spacing";
             }
             enum "1593.69" {
               description "1593.69 nm/188.112500 THz 3.125/6.25/12.5GHz spacing";
             }
             enum "1593.66" {
               description "1593.66 nm/188.115625 THz 3.125GHz spacing";
             }
             enum "1593.63" {
               description "1593.63 nm/188.118750 THz 3.125/6.25GHz spacing";
             }
             enum "1593.61" {
               description "1593.61 nm/188.121875 THz 3.125GHz spacing";
             }
             enum "1593.58" {
               description "1593.58 nm/188.125000 THz 3.125/6.25/12.5GHz spacing";
             }
             enum "1593.55" {
               description "1593.55 nm/188.128125 THz 3.125GHz spacing";
             }
             enum "1593.53" {
               description "1593.53 nm/188.131250 THz 3.125/6.25GHz spacing";
             }
             enum "1593.50" {
               description "1593.50 nm/188.134375 THz 3.125GHz spacing";
             }
             enum "1593.48" {
               description "1593.48 nm/188.137500 THz 3.125/6.25/12.5GHz spacing";
             }
             enum "1593.45" {
               description "1593.45 nm/188.140625 THz 3.125GHz spacing";
             }
             enum "1593.42" {
               description "1593.42 nm/188.143750 THz 3.125/6.25GHz spacing";
             }
             enum "1593.40" {
               description "1593.40 nm/188.146875 THz 3.125GHz spacing";
             }
             enum "1593.37" {
               description "1593.37 nm/188.150000 THz 3.125/6.25/12.5/50/75GHz spacing";
             }
             enum "1593.34" {
               description "1593.34 nm/188.153125 THz 3.125GHz spacing";
             }
             enum "1593.32" {
               description "1593.32 nm/188.156250 THz 3.125/6.25GHz spacing";
             }
             enum "1593.29" {
               description "1593.29 nm/188.159375 THz 3.125GHz spacing";
             }
             enum "1593.26" {
               description "1593.26 nm/188.162500 THz 3.125/6.25/12.5GHz spacing";
             }
             enum "1593.24" {
               description "1593.24 nm/188.165625 THz 3.125GHz spacing";
             }
             enum "1593.21" {
               description "1593.21 nm/188.168750 THz 3.125/6.25GHz spacing";
             }
             enum "1593.18" {
               description "1593.18 nm/188.171875 THz 3.125GHz spacing";
             }
             enum "1593.16" {
               description "1593.16 nm/188.175000 THz 3.125/6.25/12.5GHz spacing";
             }
             enum "1593.13" {
               description "1593.13 nm/188.178125 THz 3.125GHz spacing";
             }
             enum "1593.10" {
               description "1593.10 nm/188.181250 THz 3.125/6.25GHz spacing";
             }
             enum "1593.08" {
               description "1593.08 nm/188.184375 THz 3.125GHz spacing";
             }
             enum "1593.05" {
               description "1593.05 nm/188.187500 THz 3.125/6.25/12.5GHz spacing";
             }
             enum "1593.03" {
               description "1593.03 nm/188.190625 THz 3.125GHz spacing";
             }
             enum "1593.00" {
               description "1593.00 nm/188.193750 THz 3.125/6.25GHz spacing";
             }
             enum "1592.97" {
               description "1592.97 nm/188.196875 THz 3.125GHz spacing";
             }
             enum "1592.95" {
               description "1592.95 nm/188.200000 THz 3.125/6.25/12.5/100GHz spacing";
             }
             enum "1592.92" {
               description "1592.92 nm/188.203125 THz 3.125GHz spacing";
             }
             enum "1592.89" {
               description "1592.89 nm/188.206250 THz 3.125/6.25GHz spacing";
             }
             enum "1592.87" {
               description "1592.87 nm/188.209375 THz 3.125GHz spacing";
             }
             enum "1592.84" {
               description "1592.84 nm/188.212500 THz 3.125/6.25/12.5GHz spacing";
             }
             enum "1592.81" {
               description "1592.81 nm/188.215625 THz 3.125GHz spacing";
             }
             enum "1592.79" {
               description "1592.79 nm/188.218750 THz 3.125/6.25GHz spacing";
             }
             enum "1592.76" {
               description "1592.76 nm/188.221875 THz 3.125GHz spacing";
             }
             enum "1592.73" {
               description "1592.73 nm/188.225000 THz 3.125/6.25/12.5/75GHz spacing";
             }
             enum "1592.71" {
               description "1592.71 nm/188.228125 THz 3.125GHz spacing";
             }
             enum "1592.68" {
               description "1592.68 nm/188.231250 THz 3.125/6.25GHz spacing";
             }
             enum "1592.66" {
               description "1592.66 nm/188.234375 THz 3.125GHz spacing";
             }
             enum "1592.63" {
               description "1592.63 nm/188.237500 THz 3.125/6.25/12.5GHz spacing";
             }
             enum "1592.60" {
               description "1592.60 nm/188.240625 THz 3.125GHz spacing";
             }
             enum "1592.58" {
               description "1592.58 nm/188.243750 THz 3.125/6.25GHz spacing";
             }
             enum "1592.55" {
               description "1592.55 nm/188.246875 THz 3.125GHz spacing";
             }
             enum "1592.52" {
               description "1592.52 nm/188.250000 THz 3.125/6.25/12.5/50GHz spacing";
             }
             enum "1592.50" {
               description "1592.50 nm/188.253125 THz 3.125GHz spacing";
             }
             enum "1592.47" {
               description "1592.47 nm/188.256250 THz 3.125/6.25GHz spacing";
             }
             enum "1592.44" {
               description "1592.44 nm/188.259375 THz 3.125GHz spacing";
             }
             enum "1592.42" {
               description "1592.42 nm/188.262500 THz 3.125/6.25/12.5GHz spacing";
             }
             enum "1592.39" {
               description "1592.39 nm/188.265625 THz 3.125GHz spacing";
             }
             enum "1592.36" {
               description "1592.36 nm/188.268750 THz 3.125/6.25GHz spacing";
             }
             enum "1592.34" {
               description "1592.34 nm/188.271875 THz 3.125GHz spacing";
             }
             enum "1592.31" {
               description "1592.31 nm/188.275000 THz 3.125/6.25/12.5GHz spacing";
             }
             enum "1592.29" {
               description "1592.29 nm/188.278125 THz 3.125GHz spacing";
             }
             enum "1592.26" {
               description "1592.26 nm/188.281250 THz 3.125/6.25GHz spacing";
             }
             enum "1592.23" {
               description "1592.23 nm/188.284375 THz 3.125GHz spacing";
             }
             enum "1592.21" {
               description "1592.21 nm/188.287500 THz 3.125/6.25/12.5GHz spacing";
             }
             enum "1592.18" {
               description "1592.18 nm/188.290625 THz 3.125GHz spacing";
             }
             enum "1592.15" {
               description "1592.15 nm/188.293750 THz 3.125/6.25GHz spacing";
             }
             enum "1592.13" {
               description "1592.13 nm/188.296875 THz 3.125GHz spacing";
             }
             enum "1592.10" {
               description "1592.10 nm/188.300000 THz 3.125/6.25/12.5/100GHz spacing";
             }
             enum "1592.07" {
               description "1592.07 nm/188.303125 THz 3.125GHz spacing";
             }
             enum "1592.05" {
               description "1592.05 nm/188.306250 THz 3.125/6.25GHz spacing";
             }
             enum "1592.02" {
               description "1592.02 nm/188.309375 THz 3.125GHz spacing";
             }
             enum "1591.99" {
               description "1591.99 nm/188.312500 THz 3.125/6.25/12.5GHz spacing";
             }
             enum "1591.97" {
               description "1591.97 nm/188.315625 THz 3.125GHz spacing";
             }
             enum "1591.94" {
               description "1591.94 nm/188.318750 THz 3.125/6.25GHz spacing";
             }
             enum "1591.92" {
               description "1591.92 nm/188.321875 THz 3.125GHz spacing";
             }
             enum "1591.89" {
               description "1591.89 nm/188.325000 THz 3.125/6.25/12.5GHz spacing";
             }
             enum "1591.86" {
               description "1591.86 nm/188.328125 THz 3.125GHz spacing";
             }
             enum "1591.84" {
               description "1591.84 nm/188.331250 THz 3.125/6.25GHz spacing";
             }
             enum "1591.81" {
               description "1591.81 nm/188.334375 THz 3.125GHz spacing";
             }
             enum "1591.78" {
               description "1591.78 nm/188.337500 THz 3.125/6.25/12.5GHz spacing";
             }
             enum "1591.76" {
               description "1591.76 nm/188.340625 THz 3.125GHz spacing";
             }
             enum "1591.73" {
               description "1591.73 nm/188.343750 THz 3.125/6.25GHz spacing";
             }
             enum "1591.70" {
               description "1591.70 nm/188.346875 THz 3.125GHz spacing";
             }
             enum "1591.68" {
               description "1591.68 nm/188.350000 THz 3.125/6.25/12.5/50GHz spacing";
             }
             enum "1591.65" {
               description "1591.65 nm/188.353125 THz 3.125GHz spacing";
             }
             enum "1591.62" {
               description "1591.62 nm/188.356250 THz 3.125/6.25GHz spacing";
             }
             enum "1591.60" {
               description "1591.60 nm/188.359375 THz 3.125GHz spacing";
             }
             enum "1591.57" {
               description "1591.57 nm/188.362500 THz 3.125/6.25/12.5GHz spacing";
             }
             enum "1591.55" {
               description "1591.55 nm/188.365625 THz 3.125GHz spacing";
             }
             enum "1591.52" {
               description "1591.52 nm/188.368750 THz 3.125/6.25GHz spacing";
             }
             enum "1591.49" {
               description "1591.49 nm/188.371875 THz 3.125GHz spacing";
             }
             enum "1591.47" {
               description "1591.47 nm/188.375000 THz 3.125/6.25/12.5/75GHz spacing";
             }
             enum "1591.44" {
               description "1591.44 nm/188.378125 THz 3.125GHz spacing";
             }
             enum "1591.41" {
               description "1591.41 nm/188.381250 THz 3.125/6.25GHz spacing";
             }
             enum "1591.39" {
               description "1591.39 nm/188.384375 THz 3.125GHz spacing";
             }
             enum "1591.36" {
               description "1591.36 nm/188.387500 THz 3.125/6.25/12.5GHz spacing";
             }
             enum "1591.33" {
               description "1591.33 nm/188.390625 THz 3.125GHz spacing";
             }
             enum "1591.31" {
               description "1591.31 nm/188.393750 THz 3.125/6.25GHz spacing";
             }
             enum "1591.28" {
               description "1591.28 nm/188.396875 THz 3.125GHz spacing";
             }
             enum "1591.26" {
               description "1591.26 nm/188.400000 THz 3.125/6.25/12.5/50/75/100GHz spacing";
             }
             enum "1591.23" {
               description "1591.23 nm/188.403125 THz 3.125GHz spacing";
             }
             enum "1591.20" {
               description "1591.20 nm/188.406250 THz 3.125/6.25GHz spacing";
             }
             enum "1591.18" {
               description "1591.18 nm/188.409375 THz 3.125GHz spacing";
             }
             enum "1591.15" {
               description "1591.15 nm/188.412500 THz 3.125/6.25/12.5GHz spacing";
             }
             enum "1591.12" {
               description "1591.12 nm/188.415625 THz 3.125GHz spacing";
             }
             enum "1591.10" {
               description "1591.10 nm/188.418750 THz 3.125/6.25GHz spacing";
             }
             enum "1591.07" {
               description "1591.07 nm/188.421875 THz 3.125GHz spacing";
             }
             enum "1591.04" {
               description "1591.04 nm/188.425000 THz 3.125/6.25/12.5GHz spacing";
             }
             enum "1591.02" {
               description "1591.02 nm/188.428125 THz 3.125GHz spacing";
             }
             enum "1590.99" {
               description "1590.99 nm/188.431250 THz 3.125/6.25GHz spacing";
             }
             enum "1590.96" {
               description "1590.96 nm/188.434375 THz 3.125GHz spacing";
             }
             enum "1590.94" {
               description "1590.94 nm/188.437500 THz 3.125/6.25/12.5GHz spacing";
             }
             enum "1590.91" {
               description "1590.91 nm/188.440625 THz 3.125GHz spacing";
             }
             enum "1590.89" {
               description "1590.89 nm/188.443750 THz 3.125/6.25GHz spacing";
             }
             enum "1590.86" {
               description "1590.86 nm/188.446875 THz 3.125GHz spacing";
             }
             enum "1590.83" {
               description "1590.83 nm/188.450000 THz 3.125/6.25/12.5/50/75GHz spacing";
             }
             enum "1590.81" {
               description "1590.81 nm/188.453125 THz 3.125GHz spacing";
             }
             enum "1590.78" {
               description "1590.78 nm/188.456250 THz 3.125/6.25GHz spacing";
             }
             enum "1590.75" {
               description "1590.75 nm/188.459375 THz 3.125GHz spacing";
             }
             enum "1590.73" {
               description "1590.73 nm/188.462500 THz 3.125/6.25/12.5GHz spacing";
             }
             enum "1590.70" {
               description "1590.70 nm/188.465625 THz 3.125GHz spacing";
             }
             enum "1590.67" {
               description "1590.67 nm/188.468750 THz 3.125/6.25GHz spacing";
             }
             enum "1590.65" {
               description "1590.65 nm/188.471875 THz 3.125GHz spacing";
             }
             enum "1590.62" {
               description "1590.62 nm/188.475000 THz 3.125/6.25/12.5GHz spacing";
             }
             enum "1590.60" {
               description "1590.60 nm/188.478125 THz 3.125GHz spacing";
             }
             enum "1590.57" {
               description "1590.57 nm/188.481250 THz 3.125/6.25GHz spacing";
             }
             enum "1590.54" {
               description "1590.54 nm/188.484375 THz 3.125GHz spacing";
             }
             enum "1590.52" {
               description "1590.52 nm/188.487500 THz 3.125/6.25/12.5GHz spacing";
             }
             enum "1590.49" {
               description "1590.49 nm/188.490625 THz 3.125GHz spacing";
             }
             enum "1590.46" {
               description "1590.46 nm/188.493750 THz 3.125/6.25GHz spacing";
             }
             enum "1590.44" {
               description "1590.44 nm/188.496875 THz 3.125GHz spacing";
             }
             enum "1590.41" {
               description "1590.41 nm/188.500000 THz 3.125/6.25/12.5/100GHz spacing";
             }
             enum "1590.38" {
               description "1590.38 nm/188.503125 THz 3.125GHz spacing";
             }
             enum "1590.36" {
               description "1590.36 nm/188.506250 THz 3.125/6.25GHz spacing";
             }
             enum "1590.33" {
               description "1590.33 nm/188.509375 THz 3.125GHz spacing";
             }
             enum "1590.31" {
               description "1590.31 nm/188.512500 THz 3.125/6.25/12.5GHz spacing";
             }
             enum "1590.28" {
               description "1590.28 nm/188.515625 THz 3.125GHz spacing";
             }
             enum "1590.25" {
               description "1590.25 nm/188.518750 THz 3.125/6.25GHz spacing";
             }
             enum "1590.23" {
               description "1590.23 nm/188.521875 THz 3.125GHz spacing";
             }
             enum "1590.20" {
               description "1590.20 nm/188.525000 THz 3.125/6.25/12.5/75GHz spacing";
             }
             enum "1590.17" {
               description "1590.17 nm/188.528125 THz 3.125GHz spacing";
             }
             enum "1590.15" {
               description "1590.15 nm/188.531250 THz 3.125/6.25GHz spacing";
             }
             enum "1590.12" {
               description "1590.12 nm/188.534375 THz 3.125GHz spacing";
             }
             enum "1590.09" {
               description "1590.09 nm/188.537500 THz 3.125/6.25/12.5GHz spacing";
             }
             enum "1590.07" {
               description "1590.07 nm/188.540625 THz 3.125GHz spacing";
             }
             enum "1590.04" {
               description "1590.04 nm/188.543750 THz 3.125/6.25GHz spacing";
             }
             enum "1590.02" {
               description "1590.02 nm/188.546875 THz 3.125GHz spacing";
             }
             enum "1589.99" {
               description "1589.99 nm/188.550000 THz 3.125/6.25/12.5/50GHz spacing";
             }
             enum "1589.96" {
               description "1589.96 nm/188.553125 THz 3.125GHz spacing";
             }
             enum "1589.94" {
               description "1589.94 nm/188.556250 THz 3.125/6.25GHz spacing";
             }
             enum "1589.91" {
               description "1589.91 nm/188.559375 THz 3.125GHz spacing";
             }
             enum "1589.88" {
               description "1589.88 nm/188.562500 THz 3.125/6.25/12.5GHz spacing";
             }
             enum "1589.86" {
               description "1589.86 nm/188.565625 THz 3.125GHz spacing";
             }
             enum "1589.83" {
               description "1589.83 nm/188.568750 THz 3.125/6.25GHz spacing";
             }
             enum "1589.80" {
               description "1589.80 nm/188.571875 THz 3.125GHz spacing";
             }
             enum "1589.78" {
               description "1589.78 nm/188.575000 THz 3.125/6.25/12.5GHz spacing";
             }
             enum "1589.75" {
               description "1589.75 nm/188.578125 THz 3.125GHz spacing";
             }
             enum "1589.73" {
               description "1589.73 nm/188.581250 THz 3.125/6.25GHz spacing";
             }
             enum "1589.70" {
               description "1589.70 nm/188.584375 THz 3.125GHz spacing";
             }
             enum "1589.67" {
               description "1589.67 nm/188.587500 THz 3.125/6.25/12.5GHz spacing";
             }
             enum "1589.65" {
               description "1589.65 nm/188.590625 THz 3.125GHz spacing";
             }
             enum "1589.62" {
               description "1589.62 nm/188.593750 THz 3.125/6.25GHz spacing";
             }
             enum "1589.59" {
               description "1589.59 nm/188.596875 THz 3.125GHz spacing";
             }
             enum "1589.57" {
               description "1589.57 nm/188.600000 THz 3.125/6.25/12.5/100GHz spacing";
             }
             enum "1589.54" {
               description "1589.54 nm/188.603125 THz 3.125GHz spacing";
             }
             enum "1589.51" {
               description "1589.51 nm/188.606250 THz 3.125/6.25GHz spacing";
             }
             enum "1589.49" {
               description "1589.49 nm/188.609375 THz 3.125GHz spacing";
             }
             enum "1589.46" {
               description "1589.46 nm/188.612500 THz 3.125/6.25/12.5GHz spacing";
             }
             enum "1589.44" {
               description "1589.44 nm/188.615625 THz 3.125GHz spacing";
             }
             enum "1589.41" {
               description "1589.41 nm/188.618750 THz 3.125/6.25GHz spacing";
             }
             enum "1589.38" {
               description "1589.38 nm/188.621875 THz 3.125GHz spacing";
             }
             enum "1589.36" {
               description "1589.36 nm/188.625000 THz 3.125/6.25/12.5GHz spacing";
             }
             enum "1589.33" {
               description "1589.33 nm/188.628125 THz 3.125GHz spacing";
             }
             enum "1589.30" {
               description "1589.30 nm/188.631250 THz 3.125/6.25GHz spacing";
             }
             enum "1589.28" {
               description "1589.28 nm/188.634375 THz 3.125GHz spacing";
             }
             enum "1589.25" {
               description "1589.25 nm/188.637500 THz 3.125/6.25/12.5GHz spacing";
             }
             enum "1589.23" {
               description "1589.23 nm/188.640625 THz 3.125GHz spacing";
             }
             enum "1589.20" {
               description "1589.20 nm/188.643750 THz 3.125/6.25GHz spacing";
             }
             enum "1589.17" {
               description "1589.17 nm/188.646875 THz 3.125GHz spacing";
             }
             enum "1589.15" {
               description "1589.15 nm/188.650000 THz 3.125/6.25/12.5/50GHz spacing";
             }
             enum "1589.12" {
               description "1589.12 nm/188.653125 THz 3.125GHz spacing";
             }
             enum "1589.09" {
               description "1589.09 nm/188.656250 THz 3.125/6.25GHz spacing";
             }
             enum "1589.07" {
               description "1589.07 nm/188.659375 THz 3.125GHz spacing";
             }
             enum "1589.04" {
               description "1589.04 nm/188.662500 THz 3.125/6.25/12.5GHz spacing";
             }
             enum "1589.01" {
               description "1589.01 nm/188.665625 THz 3.125GHz spacing";
             }
             enum "1588.99" {
               description "1588.99 nm/188.668750 THz 3.125/6.25GHz spacing";
             }
             enum "1588.96" {
               description "1588.96 nm/188.671875 THz 3.125GHz spacing";
             }
             enum "1588.94" {
               description "1588.94 nm/188.675000 THz 3.125/6.25/12.5/75GHz spacing";
             }
             enum "1588.91" {
               description "1588.91 nm/188.678125 THz 3.125GHz spacing";
             }
             enum "1588.88" {
               description "1588.88 nm/188.681250 THz 3.125/6.25GHz spacing";
             }
             enum "1588.86" {
               description "1588.86 nm/188.684375 THz 3.125GHz spacing";
             }
             enum "1588.83" {
               description "1588.83 nm/188.687500 THz 3.125/6.25/12.5GHz spacing";
             }
             enum "1588.80" {
               description "1588.80 nm/188.690625 THz 3.125GHz spacing";
             }
             enum "1588.78" {
               description "1588.78 nm/188.693750 THz 3.125/6.25GHz spacing";
             }
             enum "1588.75" {
               description "1588.75 nm/188.696875 THz 3.125GHz spacing";
             }
             enum "1588.73" {
               description "1588.73 nm/188.700000 THz 3.125/6.25/12.5/50/75/100GHz spacing";
             }
             enum "1588.70" {
               description "1588.70 nm/188.703125 THz 3.125GHz spacing";
             }
             enum "1588.67" {
               description "1588.67 nm/188.706250 THz 3.125/6.25GHz spacing";
             }
             enum "1588.65" {
               description "1588.65 nm/188.709375 THz 3.125GHz spacing";
             }
             enum "1588.62" {
               description "1588.62 nm/188.712500 THz 3.125/6.25/12.5GHz spacing";
             }
             enum "1588.59" {
               description "1588.59 nm/188.715625 THz 3.125GHz spacing";
             }
             enum "1588.57" {
               description "1588.57 nm/188.718750 THz 3.125/6.25GHz spacing";
             }
             enum "1588.54" {
               description "1588.54 nm/188.721875 THz 3.125GHz spacing";
             }
             enum "1588.51" {
               description "1588.51 nm/188.725000 THz 3.125/6.25/12.5GHz spacing";
             }
             enum "1588.49" {
               description "1588.49 nm/188.728125 THz 3.125GHz spacing";
             }
             enum "1588.46" {
               description "1588.46 nm/188.731250 THz 3.125/6.25GHz spacing";
             }
             enum "1588.44" {
               description "1588.44 nm/188.734375 THz 3.125GHz spacing";
             }
             enum "1588.41" {
               description "1588.41 nm/188.737500 THz 3.125/6.25/12.5GHz spacing";
             }
             enum "1588.38" {
               description "1588.38 nm/188.740625 THz 3.125GHz spacing";
             }
             enum "1588.36" {
               description "1588.36 nm/188.743750 THz 3.125/6.25GHz spacing";
             }
             enum "1588.33" {
               description "1588.33 nm/188.746875 THz 3.125GHz spacing";
             }
             enum "1588.30" {
               description "1588.30 nm/188.750000 THz 3.125/6.25/12.5/50/75GHz spacing";
             }
             enum "1588.28" {
               description "1588.28 nm/188.753125 THz 3.125GHz spacing";
             }
             enum "1588.25" {
               description "1588.25 nm/188.756250 THz 3.125/6.25GHz spacing";
             }
             enum "1588.23" {
               description "1588.23 nm/188.759375 THz 3.125GHz spacing";
             }
             enum "1588.20" {
               description "1588.20 nm/188.762500 THz 3.125/6.25/12.5GHz spacing";
             }
             enum "1588.17" {
               description "1588.17 nm/188.765625 THz 3.125GHz spacing";
             }
             enum "1588.15" {
               description "1588.15 nm/188.768750 THz 3.125/6.25GHz spacing";
             }
             enum "1588.12" {
               description "1588.12 nm/188.771875 THz 3.125GHz spacing";
             }
             enum "1588.09" {
               description "1588.09 nm/188.775000 THz 3.125/6.25/12.5GHz spacing";
             }
             enum "1588.07" {
               description "1588.07 nm/188.778125 THz 3.125GHz spacing";
             }
             enum "1588.04" {
               description "1588.04 nm/188.781250 THz 3.125/6.25GHz spacing";
             }
             enum "1588.02" {
               description "1588.02 nm/188.784375 THz 3.125GHz spacing";
             }
             enum "1587.99" {
               description "1587.99 nm/188.787500 THz 3.125/6.25/12.5GHz spacing";
             }
             enum "1587.96" {
               description "1587.96 nm/188.790625 THz 3.125GHz spacing";
             }
             enum "1587.94" {
               description "1587.94 nm/188.793750 THz 3.125/6.25GHz spacing";
             }
             enum "1587.91" {
               description "1587.91 nm/188.796875 THz 3.125GHz spacing";
             }
             enum "1587.88" {
               description "1587.88 nm/188.800000 THz 3.125/6.25/12.5/100GHz spacing";
             }
             enum "1587.86" {
               description "1587.86 nm/188.803125 THz 3.125GHz spacing";
             }
             enum "1587.83" {
               description "1587.83 nm/188.806250 THz 3.125/6.25GHz spacing";
             }
             enum "1587.80" {
               description "1587.80 nm/188.809375 THz 3.125GHz spacing";
             }
             enum "1587.78" {
               description "1587.78 nm/188.812500 THz 3.125/6.25/12.5GHz spacing";
             }
             enum "1587.75" {
               description "1587.75 nm/188.815625 THz 3.125GHz spacing";
             }
             enum "1587.73" {
               description "1587.73 nm/188.818750 THz 3.125/6.25GHz spacing";
             }
             enum "1587.70" {
               description "1587.70 nm/188.821875 THz 3.125GHz spacing";
             }
             enum "1587.67" {
               description "1587.67 nm/188.825000 THz 3.125/6.25/12.5/75GHz spacing";
             }
             enum "1587.65" {
               description "1587.65 nm/188.828125 THz 3.125GHz spacing";
             }
             enum "1587.62" {
               description "1587.62 nm/188.831250 THz 3.125/6.25GHz spacing";
             }
             enum "1587.59" {
               description "1587.59 nm/188.834375 THz 3.125GHz spacing";
             }
             enum "1587.57" {
               description "1587.57 nm/188.837500 THz 3.125/6.25/12.5GHz spacing";
             }
             enum "1587.54" {
               description "1587.54 nm/188.840625 THz 3.125GHz spacing";
             }
             enum "1587.52" {
               description "1587.52 nm/188.843750 THz 3.125/6.25GHz spacing";
             }
             enum "1587.49" {
               description "1587.49 nm/188.846875 THz 3.125GHz spacing";
             }
             enum "1587.46" {
               description "1587.46 nm/188.850000 THz 3.125/6.25/12.5/50GHz spacing";
             }
             enum "1587.44" {
               description "1587.44 nm/188.853125 THz 3.125GHz spacing";
             }
             enum "1587.41" {
               description "1587.41 nm/188.856250 THz 3.125/6.25GHz spacing";
             }
             enum "1587.38" {
               description "1587.38 nm/188.859375 THz 3.125GHz spacing";
             }
             enum "1587.36" {
               description "1587.36 nm/188.862500 THz 3.125/6.25/12.5GHz spacing";
             }
             enum "1587.33" {
               description "1587.33 nm/188.865625 THz 3.125GHz spacing";
             }
             enum "1587.31" {
               description "1587.31 nm/188.868750 THz 3.125/6.25GHz spacing";
             }
             enum "1587.28" {
               description "1587.28 nm/188.871875 THz 3.125GHz spacing";
             }
             enum "1587.25" {
               description "1587.25 nm/188.875000 THz 3.125/6.25/12.5GHz spacing";
             }
             enum "1587.23" {
               description "1587.23 nm/188.878125 THz 3.125GHz spacing";
             }
             enum "1587.20" {
               description "1587.20 nm/188.881250 THz 3.125/6.25GHz spacing";
             }
             enum "1587.17" {
               description "1587.17 nm/188.884375 THz 3.125GHz spacing";
             }
             enum "1587.15" {
               description "1587.15 nm/188.887500 THz 3.125/6.25/12.5GHz spacing";
             }
             enum "1587.12" {
               description "1587.12 nm/188.890625 THz 3.125GHz spacing";
             }
             enum "1587.10" {
               description "1587.10 nm/188.893750 THz 3.125/6.25GHz spacing";
             }
             enum "1587.07" {
               description "1587.07 nm/188.896875 THz 3.125GHz spacing";
             }
             enum "1587.04" {
               description "1587.04 nm/188.900000 THz 3.125/6.25/12.5/100GHz spacing";
             }
             enum "1587.02" {
               description "1587.02 nm/188.903125 THz 3.125GHz spacing";
             }
             enum "1586.99" {
               description "1586.99 nm/188.906250 THz 3.125/6.25GHz spacing";
             }
             enum "1586.96" {
               description "1586.96 nm/188.909375 THz 3.125GHz spacing";
             }
             enum "1586.94" {
               description "1586.94 nm/188.912500 THz 3.125/6.25/12.5GHz spacing";
             }
             enum "1586.91" {
               description "1586.91 nm/188.915625 THz 3.125GHz spacing";
             }
             enum "1586.89" {
               description "1586.89 nm/188.918750 THz 3.125/6.25GHz spacing";
             }
             enum "1586.86" {
               description "1586.86 nm/188.921875 THz 3.125GHz spacing";
             }
             enum "1586.83" {
               description "1586.83 nm/188.925000 THz 3.125/6.25/12.5GHz spacing";
             }
             enum "1586.81" {
               description "1586.81 nm/188.928125 THz 3.125GHz spacing";
             }
             enum "1586.78" {
               description "1586.78 nm/188.931250 THz 3.125/6.25GHz spacing";
             }
             enum "1586.75" {
               description "1586.75 nm/188.934375 THz 3.125GHz spacing";
             }
             enum "1586.73" {
               description "1586.73 nm/188.937500 THz 3.125/6.25/12.5GHz spacing";
             }
             enum "1586.70" {
               description "1586.70 nm/188.940625 THz 3.125GHz spacing";
             }
             enum "1586.68" {
               description "1586.68 nm/188.943750 THz 3.125/6.25GHz spacing";
             }
             enum "1586.65" {
               description "1586.65 nm/188.946875 THz 3.125GHz spacing";
             }
             enum "1586.62" {
               description "1586.62 nm/188.950000 THz 3.125/6.25/12.5/50GHz spacing";
             }
             enum "1586.60" {
               description "1586.60 nm/188.953125 THz 3.125GHz spacing";
             }
             enum "1586.57" {
               description "1586.57 nm/188.956250 THz 3.125/6.25GHz spacing";
             }
             enum "1586.54" {
               description "1586.54 nm/188.959375 THz 3.125GHz spacing";
             }
             enum "1586.52" {
               description "1586.52 nm/188.962500 THz 3.125/6.25/12.5GHz spacing";
             }
             enum "1586.49" {
               description "1586.49 nm/188.965625 THz 3.125GHz spacing";
             }
             enum "1586.47" {
               description "1586.47 nm/188.968750 THz 3.125/6.25GHz spacing";
             }
             enum "1586.44" {
               description "1586.44 nm/188.971875 THz 3.125GHz spacing";
             }
             enum "1586.41" {
               description "1586.41 nm/188.975000 THz 3.125/6.25/12.5/75GHz spacing";
             }
             enum "1586.39" {
               description "1586.39 nm/188.978125 THz 3.125GHz spacing";
             }
             enum "1586.36" {
               description "1586.36 nm/188.981250 THz 3.125/6.25GHz spacing";
             }
             enum "1586.33" {
               description "1586.33 nm/188.984375 THz 3.125GHz spacing";
             }
             enum "1586.31" {
               description "1586.31 nm/188.987500 THz 3.125/6.25/12.5GHz spacing";
             }
             enum "1586.28" {
               description "1586.28 nm/188.990625 THz 3.125GHz spacing";
             }
             enum "1586.26" {
               description "1586.26 nm/188.993750 THz 3.125/6.25GHz spacing";
             }
             enum "1586.23" {
               description "1586.23 nm/188.996875 THz 3.125GHz spacing";
             }
             enum "1586.20" {
               description "1586.20 nm/189.000000 THz 3.125/6.25/12.5/50/75/100GHz spacing";
             }
             enum "1586.18" {
               description "1586.18 nm/189.003125 THz 3.125GHz spacing";
             }
             enum "1586.15" {
               description "1586.15 nm/189.006250 THz 3.125/6.25GHz spacing";
             }
             enum "1586.12" {
               description "1586.12 nm/189.009375 THz 3.125GHz spacing";
             }
             enum "1586.10" {
               description "1586.10 nm/189.012500 THz 3.125/6.25/12.5GHz spacing";
             }
             enum "1586.07" {
               description "1586.07 nm/189.015625 THz 3.125GHz spacing";
             }
             enum "1586.05" {
               description "1586.05 nm/189.018750 THz 3.125/6.25GHz spacing";
             }
             enum "1586.02" {
               description "1586.02 nm/189.021875 THz 3.125GHz spacing";
             }
             enum "1585.99" {
               description "1585.99 nm/189.025000 THz 3.125/6.25/12.5GHz spacing";
             }
             enum "1585.97" {
               description "1585.97 nm/189.028125 THz 3.125GHz spacing";
             }
             enum "1585.94" {
               description "1585.94 nm/189.031250 THz 3.125/6.25GHz spacing";
             }
             enum "1585.92" {
               description "1585.92 nm/189.034375 THz 3.125GHz spacing";
             }
             enum "1585.89" {
               description "1585.89 nm/189.037500 THz 3.125/6.25/12.5GHz spacing";
             }
             enum "1585.86" {
               description "1585.86 nm/189.040625 THz 3.125GHz spacing";
             }
             enum "1585.84" {
               description "1585.84 nm/189.043750 THz 3.125/6.25GHz spacing";
             }
             enum "1585.81" {
               description "1585.81 nm/189.046875 THz 3.125GHz spacing";
             }
             enum "1585.78" {
               description "1585.78 nm/189.050000 THz 3.125/6.25/12.5/50/75GHz spacing";
             }
             enum "1585.76" {
               description "1585.76 nm/189.053125 THz 3.125GHz spacing";
             }
             enum "1585.73" {
               description "1585.73 nm/189.056250 THz 3.125/6.25GHz spacing";
             }
             enum "1585.71" {
               description "1585.71 nm/189.059375 THz 3.125GHz spacing";
             }
             enum "1585.68" {
               description "1585.68 nm/189.062500 THz 3.125/6.25/12.5GHz spacing";
             }
             enum "1585.65" {
               description "1585.65 nm/189.065625 THz 3.125GHz spacing";
             }
             enum "1585.63" {
               description "1585.63 nm/189.068750 THz 3.125/6.25GHz spacing";
             }
             enum "1585.60" {
               description "1585.60 nm/189.071875 THz 3.125GHz spacing";
             }
             enum "1585.57" {
               description "1585.57 nm/189.075000 THz 3.125/6.25/12.5GHz spacing";
             }
             enum "1585.55" {
               description "1585.55 nm/189.078125 THz 3.125GHz spacing";
             }
             enum "1585.52" {
               description "1585.52 nm/189.081250 THz 3.125/6.25GHz spacing";
             }
             enum "1585.50" {
               description "1585.50 nm/189.084375 THz 3.125GHz spacing";
             }
             enum "1585.47" {
               description "1585.47 nm/189.087500 THz 3.125/6.25/12.5GHz spacing";
             }
             enum "1585.44" {
               description "1585.44 nm/189.090625 THz 3.125GHz spacing";
             }
             enum "1585.42" {
               description "1585.42 nm/189.093750 THz 3.125/6.25GHz spacing";
             }
             enum "1585.39" {
               description "1585.39 nm/189.096875 THz 3.125GHz spacing";
             }
             enum "1585.36" {
               description "1585.36 nm/189.100000 THz 3.125/6.25/12.5/100GHz spacing";
             }
             enum "1585.34" {
               description "1585.34 nm/189.103125 THz 3.125GHz spacing";
             }
             enum "1585.31" {
               description "1585.31 nm/189.106250 THz 3.125/6.25GHz spacing";
             }
             enum "1585.29" {
               description "1585.29 nm/189.109375 THz 3.125GHz spacing";
             }
             enum "1585.26" {
               description "1585.26 nm/189.112500 THz 3.125/6.25/12.5GHz spacing";
             }
             enum "1585.23" {
               description "1585.23 nm/189.115625 THz 3.125GHz spacing";
             }
             enum "1585.21" {
               description "1585.21 nm/189.118750 THz 3.125/6.25GHz spacing";
             }
             enum "1585.18" {
               description "1585.18 nm/189.121875 THz 3.125GHz spacing";
             }
             enum "1585.16" {
               description "1585.16 nm/189.125000 THz 3.125/6.25/12.5/75GHz spacing";
             }
             enum "1585.13" {
               description "1585.13 nm/189.128125 THz 3.125GHz spacing";
             }
             enum "1585.10" {
               description "1585.10 nm/189.131250 THz 3.125/6.25GHz spacing";
             }
             enum "1585.08" {
               description "1585.08 nm/189.134375 THz 3.125GHz spacing";
             }
             enum "1585.05" {
               description "1585.05 nm/189.137500 THz 3.125/6.25/12.5GHz spacing";
             }
             enum "1585.02" {
               description "1585.02 nm/189.140625 THz 3.125GHz spacing";
             }
             enum "1585.00" {
               description "1585.00 nm/189.143750 THz 3.125/6.25GHz spacing";
             }
             enum "1584.97" {
               description "1584.97 nm/189.146875 THz 3.125GHz spacing";
             }
             enum "1584.95" {
               description "1584.95 nm/189.150000 THz 3.125/6.25/12.5/50GHz spacing";
             }
             enum "1584.92" {
               description "1584.92 nm/189.153125 THz 3.125GHz spacing";
             }
             enum "1584.89" {
               description "1584.89 nm/189.156250 THz 3.125/6.25GHz spacing";
             }
             enum "1584.87" {
               description "1584.87 nm/189.159375 THz 3.125GHz spacing";
             }
             enum "1584.84" {
               description "1584.84 nm/189.162500 THz 3.125/6.25/12.5GHz spacing";
             }
             enum "1584.81" {
               description "1584.81 nm/189.165625 THz 3.125GHz spacing";
             }
             enum "1584.79" {
               description "1584.79 nm/189.168750 THz 3.125/6.25GHz spacing";
             }
             enum "1584.76" {
               description "1584.76 nm/189.171875 THz 3.125GHz spacing";
             }
             enum "1584.74" {
               description "1584.74 nm/189.175000 THz 3.125/6.25/12.5GHz spacing";
             }
             enum "1584.71" {
               description "1584.71 nm/189.178125 THz 3.125GHz spacing";
             }
             enum "1584.68" {
               description "1584.68 nm/189.181250 THz 3.125/6.25GHz spacing";
             }
             enum "1584.66" {
               description "1584.66 nm/189.184375 THz 3.125GHz spacing";
             }
             enum "1584.63" {
               description "1584.63 nm/189.187500 THz 3.125/6.25/12.5GHz spacing";
             }
             enum "1584.61" {
               description "1584.61 nm/189.190625 THz 3.125GHz spacing";
             }
             enum "1584.58" {
               description "1584.58 nm/189.193750 THz 3.125/6.25GHz spacing";
             }
             enum "1584.55" {
               description "1584.55 nm/189.196875 THz 3.125GHz spacing";
             }
             enum "1584.53" {
               description "1584.53 nm/189.200000 THz 3.125/6.25/12.5/100GHz spacing";
             }
             enum "1584.50" {
               description "1584.50 nm/189.203125 THz 3.125GHz spacing";
             }
             enum "1584.47" {
               description "1584.47 nm/189.206250 THz 3.125/6.25GHz spacing";
             }
             enum "1584.45" {
               description "1584.45 nm/189.209375 THz 3.125GHz spacing";
             }
             enum "1584.42" {
               description "1584.42 nm/189.212500 THz 3.125/6.25/12.5GHz spacing";
             }
             enum "1584.40" {
               description "1584.40 nm/189.215625 THz 3.125GHz spacing";
             }
             enum "1584.37" {
               description "1584.37 nm/189.218750 THz 3.125/6.25GHz spacing";
             }
             enum "1584.34" {
               description "1584.34 nm/189.221875 THz 3.125GHz spacing";
             }
             enum "1584.32" {
               description "1584.32 nm/189.225000 THz 3.125/6.25/12.5GHz spacing";
             }
             enum "1584.29" {
               description "1584.29 nm/189.228125 THz 3.125GHz spacing";
             }
             enum "1584.27" {
               description "1584.27 nm/189.231250 THz 3.125/6.25GHz spacing";
             }
             enum "1584.24" {
               description "1584.24 nm/189.234375 THz 3.125GHz spacing";
             }
             enum "1584.21" {
               description "1584.21 nm/189.237500 THz 3.125/6.25/12.5GHz spacing";
             }
             enum "1584.19" {
               description "1584.19 nm/189.240625 THz 3.125GHz spacing";
             }
             enum "1584.16" {
               description "1584.16 nm/189.243750 THz 3.125/6.25GHz spacing";
             }
             enum "1584.13" {
               description "1584.13 nm/189.246875 THz 3.125GHz spacing";
             }
             enum "1584.11" {
               description "1584.11 nm/189.250000 THz 3.125/6.25/12.5/50GHz spacing";
             }
             enum "1584.08" {
               description "1584.08 nm/189.253125 THz 3.125GHz spacing";
             }
             enum "1584.06" {
               description "1584.06 nm/189.256250 THz 3.125/6.25GHz spacing";
             }
             enum "1584.03" {
               description "1584.03 nm/189.259375 THz 3.125GHz spacing";
             }
             enum "1584.00" {
               description "1584.00 nm/189.262500 THz 3.125/6.25/12.5GHz spacing";
             }
             enum "1583.98" {
               description "1583.98 nm/189.265625 THz 3.125GHz spacing";
             }
             enum "1583.95" {
               description "1583.95 nm/189.268750 THz 3.125/6.25GHz spacing";
             }
             enum "1583.93" {
               description "1583.93 nm/189.271875 THz 3.125GHz spacing";
             }
             enum "1583.90" {
               description "1583.90 nm/189.275000 THz 3.125/6.25/12.5/75GHz spacing";
             }
             enum "1583.87" {
               description "1583.87 nm/189.278125 THz 3.125GHz spacing";
             }
             enum "1583.85" {
               description "1583.85 nm/189.281250 THz 3.125/6.25GHz spacing";
             }
             enum "1583.82" {
               description "1583.82 nm/189.284375 THz 3.125GHz spacing";
             }
             enum "1583.79" {
               description "1583.79 nm/189.287500 THz 3.125/6.25/12.5GHz spacing";
             }
             enum "1583.77" {
               description "1583.77 nm/189.290625 THz 3.125GHz spacing";
             }
             enum "1583.74" {
               description "1583.74 nm/189.293750 THz 3.125/6.25GHz spacing";
             }
             enum "1583.72" {
               description "1583.72 nm/189.296875 THz 3.125GHz spacing";
             }
             enum "1583.69" {
               description "1583.69 nm/189.300000 THz 3.125/6.25/12.5/50/75/100GHz spacing";
             }
             enum "1583.66" {
               description "1583.66 nm/189.303125 THz 3.125GHz spacing";
             }
             enum "1583.64" {
               description "1583.64 nm/189.306250 THz 3.125/6.25GHz spacing";
             }
             enum "1583.61" {
               description "1583.61 nm/189.309375 THz 3.125GHz spacing";
             }
             enum "1583.59" {
               description "1583.59 nm/189.312500 THz 3.125/6.25/12.5GHz spacing";
             }
             enum "1583.56" {
               description "1583.56 nm/189.315625 THz 3.125GHz spacing";
             }
             enum "1583.53" {
               description "1583.53 nm/189.318750 THz 3.125/6.25GHz spacing";
             }
             enum "1583.51" {
               description "1583.51 nm/189.321875 THz 3.125GHz spacing";
             }
             enum "1583.48" {
               description "1583.48 nm/189.325000 THz 3.125/6.25/12.5GHz spacing";
             }
             enum "1583.45" {
               description "1583.45 nm/189.328125 THz 3.125GHz spacing";
             }
             enum "1583.43" {
               description "1583.43 nm/189.331250 THz 3.125/6.25GHz spacing";
             }
             enum "1583.40" {
               description "1583.40 nm/189.334375 THz 3.125GHz spacing";
             }
             enum "1583.38" {
               description "1583.38 nm/189.337500 THz 3.125/6.25/12.5GHz spacing";
             }
             enum "1583.35" {
               description "1583.35 nm/189.340625 THz 3.125GHz spacing";
             }
             enum "1583.32" {
               description "1583.32 nm/189.343750 THz 3.125/6.25GHz spacing";
             }
             enum "1583.30" {
               description "1583.30 nm/189.346875 THz 3.125GHz spacing";
             }
             enum "1583.27" {
               description "1583.27 nm/189.350000 THz 3.125/6.25/12.5/50/75GHz spacing";
             }
             enum "1583.25" {
               description "1583.25 nm/189.353125 THz 3.125GHz spacing";
             }
             enum "1583.22" {
               description "1583.22 nm/189.356250 THz 3.125/6.25GHz spacing";
             }
             enum "1583.19" {
               description "1583.19 nm/189.359375 THz 3.125GHz spacing";
             }
             enum "1583.17" {
               description "1583.17 nm/189.362500 THz 3.125/6.25/12.5GHz spacing";
             }
             enum "1583.14" {
               description "1583.14 nm/189.365625 THz 3.125GHz spacing";
             }
             enum "1583.11" {
               description "1583.11 nm/189.368750 THz 3.125/6.25GHz spacing";
             }
             enum "1583.09" {
               description "1583.09 nm/189.371875 THz 3.125GHz spacing";
             }
             enum "1583.06" {
               description "1583.06 nm/189.375000 THz 3.125/6.25/12.5GHz spacing";
             }
             enum "1583.04" {
               description "1583.04 nm/189.378125 THz 3.125GHz spacing";
             }
             enum "1583.01" {
               description "1583.01 nm/189.381250 THz 3.125/6.25GHz spacing";
             }
             enum "1582.98" {
               description "1582.98 nm/189.384375 THz 3.125GHz spacing";
             }
             enum "1582.96" {
               description "1582.96 nm/189.387500 THz 3.125/6.25/12.5GHz spacing";
             }
             enum "1582.93" {
               description "1582.93 nm/189.390625 THz 3.125GHz spacing";
             }
             enum "1582.91" {
               description "1582.91 nm/189.393750 THz 3.125/6.25GHz spacing";
             }
             enum "1582.88" {
               description "1582.88 nm/189.396875 THz 3.125GHz spacing";
             }
             enum "1582.85" {
               description "1582.85 nm/189.400000 THz 3.125/6.25/12.5/100GHz spacing";
             }
             enum "1582.83" {
               description "1582.83 nm/189.403125 THz 3.125GHz spacing";
             }
             enum "1582.80" {
               description "1582.80 nm/189.406250 THz 3.125/6.25GHz spacing";
             }
             enum "1582.78" {
               description "1582.78 nm/189.409375 THz 3.125GHz spacing";
             }
             enum "1582.75" {
               description "1582.75 nm/189.412500 THz 3.125/6.25/12.5GHz spacing";
             }
             enum "1582.72" {
               description "1582.72 nm/189.415625 THz 3.125GHz spacing";
             }
             enum "1582.70" {
               description "1582.70 nm/189.418750 THz 3.125/6.25GHz spacing";
             }
             enum "1582.67" {
               description "1582.67 nm/189.421875 THz 3.125GHz spacing";
             }
             enum "1582.64" {
               description "1582.64 nm/189.425000 THz 3.125/6.25/12.5/75GHz spacing";
             }
             enum "1582.62" {
               description "1582.62 nm/189.428125 THz 3.125GHz spacing";
             }
             enum "1582.59" {
               description "1582.59 nm/189.431250 THz 3.125/6.25GHz spacing";
             }
             enum "1582.57" {
               description "1582.57 nm/189.434375 THz 3.125GHz spacing";
             }
             enum "1582.54" {
               description "1582.54 nm/189.437500 THz 3.125/6.25/12.5GHz spacing";
             }
             enum "1582.51" {
               description "1582.51 nm/189.440625 THz 3.125GHz spacing";
             }
             enum "1582.49" {
               description "1582.49 nm/189.443750 THz 3.125/6.25GHz spacing";
             }
             enum "1582.46" {
               description "1582.46 nm/189.446875 THz 3.125GHz spacing";
             }
             enum "1582.44" {
               description "1582.44 nm/189.450000 THz 3.125/6.25/12.5/50GHz spacing";
             }
             enum "1582.41" {
               description "1582.41 nm/189.453125 THz 3.125GHz spacing";
             }
             enum "1582.38" {
               description "1582.38 nm/189.456250 THz 3.125/6.25GHz spacing";
             }
             enum "1582.36" {
               description "1582.36 nm/189.459375 THz 3.125GHz spacing";
             }
             enum "1582.33" {
               description "1582.33 nm/189.462500 THz 3.125/6.25/12.5GHz spacing";
             }
             enum "1582.31" {
               description "1582.31 nm/189.465625 THz 3.125GHz spacing";
             }
             enum "1582.28" {
               description "1582.28 nm/189.468750 THz 3.125/6.25GHz spacing";
             }
             enum "1582.25" {
               description "1582.25 nm/189.471875 THz 3.125GHz spacing";
             }
             enum "1582.23" {
               description "1582.23 nm/189.475000 THz 3.125/6.25/12.5GHz spacing";
             }
             enum "1582.20" {
               description "1582.20 nm/189.478125 THz 3.125GHz spacing";
             }
             enum "1582.17" {
               description "1582.17 nm/189.481250 THz 3.125/6.25GHz spacing";
             }
             enum "1582.15" {
               description "1582.15 nm/189.484375 THz 3.125GHz spacing";
             }
             enum "1582.12" {
               description "1582.12 nm/189.487500 THz 3.125/6.25/12.5GHz spacing";
             }
             enum "1582.10" {
               description "1582.10 nm/189.490625 THz 3.125GHz spacing";
             }
             enum "1582.07" {
               description "1582.07 nm/189.493750 THz 3.125/6.25GHz spacing";
             }
             enum "1582.04" {
               description "1582.04 nm/189.496875 THz 3.125GHz spacing";
             }
             enum "1582.02" {
               description "1582.02 nm/189.500000 THz 3.125/6.25/12.5/100GHz spacing";
             }
             enum "1581.99" {
               description "1581.99 nm/189.503125 THz 3.125GHz spacing";
             }
             enum "1581.97" {
               description "1581.97 nm/189.506250 THz 3.125/6.25GHz spacing";
             }
             enum "1581.94" {
               description "1581.94 nm/189.509375 THz 3.125GHz spacing";
             }
             enum "1581.91" {
               description "1581.91 nm/189.512500 THz 3.125/6.25/12.5GHz spacing";
             }
             enum "1581.89" {
               description "1581.89 nm/189.515625 THz 3.125GHz spacing";
             }
             enum "1581.86" {
               description "1581.86 nm/189.518750 THz 3.125/6.25GHz spacing";
             }
             enum "1581.84" {
               description "1581.84 nm/189.521875 THz 3.125GHz spacing";
             }
             enum "1581.81" {
               description "1581.81 nm/189.525000 THz 3.125/6.25/12.5GHz spacing";
             }
             enum "1581.78" {
               description "1581.78 nm/189.528125 THz 3.125GHz spacing";
             }
             enum "1581.76" {
               description "1581.76 nm/189.531250 THz 3.125/6.25GHz spacing";
             }
             enum "1581.73" {
               description "1581.73 nm/189.534375 THz 3.125GHz spacing";
             }
             enum "1581.71" {
               description "1581.71 nm/189.537500 THz 3.125/6.25/12.5GHz spacing";
             }
             enum "1581.68" {
               description "1581.68 nm/189.540625 THz 3.125GHz spacing";
             }
             enum "1581.65" {
               description "1581.65 nm/189.543750 THz 3.125/6.25GHz spacing";
             }
             enum "1581.63" {
               description "1581.63 nm/189.546875 THz 3.125GHz spacing";
             }
             enum "1581.60" {
               description "1581.60 nm/189.550000 THz 3.125/6.25/12.5/50GHz spacing";
             }
             enum "1581.57" {
               description "1581.57 nm/189.553125 THz 3.125GHz spacing";
             }
             enum "1581.55" {
               description "1581.55 nm/189.556250 THz 3.125/6.25GHz spacing";
             }
             enum "1581.52" {
               description "1581.52 nm/189.559375 THz 3.125GHz spacing";
             }
             enum "1581.50" {
               description "1581.50 nm/189.562500 THz 3.125/6.25/12.5GHz spacing";
             }
             enum "1581.47" {
               description "1581.47 nm/189.565625 THz 3.125GHz spacing";
             }
             enum "1581.44" {
               description "1581.44 nm/189.568750 THz 3.125/6.25GHz spacing";
             }
             enum "1581.42" {
               description "1581.42 nm/189.571875 THz 3.125GHz spacing";
             }
             enum "1581.39" {
               description "1581.39 nm/189.575000 THz 3.125/6.25/12.5/75GHz spacing";
             }
             enum "1581.37" {
               description "1581.37 nm/189.578125 THz 3.125GHz spacing";
             }
             enum "1581.34" {
               description "1581.34 nm/189.581250 THz 3.125/6.25GHz spacing";
             }
             enum "1581.31" {
               description "1581.31 nm/189.584375 THz 3.125GHz spacing";
             }
             enum "1581.29" {
               description "1581.29 nm/189.587500 THz 3.125/6.25/12.5GHz spacing";
             }
             enum "1581.26" {
               description "1581.26 nm/189.590625 THz 3.125GHz spacing";
             }
             enum "1581.24" {
               description "1581.24 nm/189.593750 THz 3.125/6.25GHz spacing";
             }
             enum "1581.21" {
               description "1581.21 nm/189.596875 THz 3.125GHz spacing";
             }
             enum "1581.18" {
               description "1581.18 nm/189.600000 THz 3.125/6.25/12.5/50/75/100GHz spacing";
             }
             enum "1581.16" {
               description "1581.16 nm/189.603125 THz 3.125GHz spacing";
             }
             enum "1581.13" {
               description "1581.13 nm/189.606250 THz 3.125/6.25GHz spacing";
             }
             enum "1581.11" {
               description "1581.11 nm/189.609375 THz 3.125GHz spacing";
             }
             enum "1581.08" {
               description "1581.08 nm/189.612500 THz 3.125/6.25/12.5GHz spacing";
             }
             enum "1581.05" {
               description "1581.05 nm/189.615625 THz 3.125GHz spacing";
             }
             enum "1581.03" {
               description "1581.03 nm/189.618750 THz 3.125/6.25GHz spacing";
             }
             enum "1581.00" {
               description "1581.00 nm/189.621875 THz 3.125GHz spacing";
             }
             enum "1580.98" {
               description "1580.98 nm/189.625000 THz 3.125/6.25/12.5GHz spacing";
             }
             enum "1580.95" {
               description "1580.95 nm/189.628125 THz 3.125GHz spacing";
             }
             enum "1580.92" {
               description "1580.92 nm/189.631250 THz 3.125/6.25GHz spacing";
             }
             enum "1580.90" {
               description "1580.90 nm/189.634375 THz 3.125GHz spacing";
             }
             enum "1580.87" {
               description "1580.87 nm/189.637500 THz 3.125/6.25/12.5GHz spacing";
             }
             enum "1580.85" {
               description "1580.85 nm/189.640625 THz 3.125GHz spacing";
             }
             enum "1580.82" {
               description "1580.82 nm/189.643750 THz 3.125/6.25GHz spacing";
             }
             enum "1580.79" {
               description "1580.79 nm/189.646875 THz 3.125GHz spacing";
             }
             enum "1580.77" {
               description "1580.77 nm/189.650000 THz 3.125/6.25/12.5/50/75GHz spacing";
             }
             enum "1580.74" {
               description "1580.74 nm/189.653125 THz 3.125GHz spacing";
             }
             enum "1580.71" {
               description "1580.71 nm/189.656250 THz 3.125/6.25GHz spacing";
             }
             enum "1580.69" {
               description "1580.69 nm/189.659375 THz 3.125GHz spacing";
             }
             enum "1580.66" {
               description "1580.66 nm/189.662500 THz 3.125/6.25/12.5GHz spacing";
             }
             enum "1580.64" {
               description "1580.64 nm/189.665625 THz 3.125GHz spacing";
             }
             enum "1580.61" {
               description "1580.61 nm/189.668750 THz 3.125/6.25GHz spacing";
             }
             enum "1580.58" {
               description "1580.58 nm/189.671875 THz 3.125GHz spacing";
             }
             enum "1580.56" {
               description "1580.56 nm/189.675000 THz 3.125/6.25/12.5GHz spacing";
             }
             enum "1580.53" {
               description "1580.53 nm/189.678125 THz 3.125GHz spacing";
             }
             enum "1580.51" {
               description "1580.51 nm/189.681250 THz 3.125/6.25GHz spacing";
             }
             enum "1580.48" {
               description "1580.48 nm/189.684375 THz 3.125GHz spacing";
             }
             enum "1580.45" {
               description "1580.45 nm/189.687500 THz 3.125/6.25/12.5GHz spacing";
             }
             enum "1580.43" {
               description "1580.43 nm/189.690625 THz 3.125GHz spacing";
             }
             enum "1580.40" {
               description "1580.40 nm/189.693750 THz 3.125/6.25GHz spacing";
             }
             enum "1580.38" {
               description "1580.38 nm/189.696875 THz 3.125GHz spacing";
             }
             enum "1580.35" {
               description "1580.35 nm/189.700000 THz 3.125/6.25/12.5/100GHz spacing";
             }
             enum "1580.32" {
               description "1580.32 nm/189.703125 THz 3.125GHz spacing";
             }
             enum "1580.30" {
               description "1580.30 nm/189.706250 THz 3.125/6.25GHz spacing";
             }
             enum "1580.27" {
               description "1580.27 nm/189.709375 THz 3.125GHz spacing";
             }
             enum "1580.25" {
               description "1580.25 nm/189.712500 THz 3.125/6.25/12.5GHz spacing";
             }
             enum "1580.22" {
               description "1580.22 nm/189.715625 THz 3.125GHz spacing";
             }
             enum "1580.19" {
               description "1580.19 nm/189.718750 THz 3.125/6.25GHz spacing";
             }
             enum "1580.17" {
               description "1580.17 nm/189.721875 THz 3.125GHz spacing";
             }
             enum "1580.14" {
               description "1580.14 nm/189.725000 THz 3.125/6.25/12.5/75GHz spacing";
             }
             enum "1580.12" {
               description "1580.12 nm/189.728125 THz 3.125GHz spacing";
             }
             enum "1580.09" {
               description "1580.09 nm/189.731250 THz 3.125/6.25GHz spacing";
             }
             enum "1580.06" {
               description "1580.06 nm/189.734375 THz 3.125GHz spacing";
             }
             enum "1580.04" {
               description "1580.04 nm/189.737500 THz 3.125/6.25/12.5GHz spacing";
             }
             enum "1580.01" {
               description "1580.01 nm/189.740625 THz 3.125GHz spacing";
             }
             enum "1579.99" {
               description "1579.99 nm/189.743750 THz 3.125/6.25GHz spacing";
             }
             enum "1579.96" {
               description "1579.96 nm/189.746875 THz 3.125GHz spacing";
             }
             enum "1579.93" {
               description "1579.93 nm/189.750000 THz 3.125/6.25/12.5/50GHz spacing";
             }
             enum "1579.91" {
               description "1579.91 nm/189.753125 THz 3.125GHz spacing";
             }
             enum "1579.88" {
               description "1579.88 nm/189.756250 THz 3.125/6.25GHz spacing";
             }
             enum "1579.86" {
               description "1579.86 nm/189.759375 THz 3.125GHz spacing";
             }
             enum "1579.83" {
               description "1579.83 nm/189.762500 THz 3.125/6.25/12.5GHz spacing";
             }
             enum "1579.80" {
               description "1579.80 nm/189.765625 THz 3.125GHz spacing";
             }
             enum "1579.78" {
               description "1579.78 nm/189.768750 THz 3.125/6.25GHz spacing";
             }
             enum "1579.75" {
               description "1579.75 nm/189.771875 THz 3.125GHz spacing";
             }
             enum "1579.73" {
               description "1579.73 nm/189.775000 THz 3.125/6.25/12.5GHz spacing";
             }
             enum "1579.70" {
               description "1579.70 nm/189.778125 THz 3.125GHz spacing";
             }
             enum "1579.67" {
               description "1579.67 nm/189.781250 THz 3.125/6.25GHz spacing";
             }
             enum "1579.65" {
               description "1579.65 nm/189.784375 THz 3.125GHz spacing";
             }
             enum "1579.62" {
               description "1579.62 nm/189.787500 THz 3.125/6.25/12.5GHz spacing";
             }
             enum "1579.60" {
               description "1579.60 nm/189.790625 THz 3.125GHz spacing";
             }
             enum "1579.57" {
               description "1579.57 nm/189.793750 THz 3.125/6.25GHz spacing";
             }
             enum "1579.54" {
               description "1579.54 nm/189.796875 THz 3.125GHz spacing";
             }
             enum "1579.52" {
               description "1579.52 nm/189.800000 THz 3.125/6.25/12.5/100GHz spacing";
             }
             enum "1579.49" {
               description "1579.49 nm/189.803125 THz 3.125GHz spacing";
             }
             enum "1579.47" {
               description "1579.47 nm/189.806250 THz 3.125/6.25GHz spacing";
             }
             enum "1579.44" {
               description "1579.44 nm/189.809375 THz 3.125GHz spacing";
             }
             enum "1579.41" {
               description "1579.41 nm/189.812500 THz 3.125/6.25/12.5GHz spacing";
             }
             enum "1579.39" {
               description "1579.39 nm/189.815625 THz 3.125GHz spacing";
             }
             enum "1579.36" {
               description "1579.36 nm/189.818750 THz 3.125/6.25GHz spacing";
             }
             enum "1579.34" {
               description "1579.34 nm/189.821875 THz 3.125GHz spacing";
             }
             enum "1579.31" {
               description "1579.31 nm/189.825000 THz 3.125/6.25/12.5GHz spacing";
             }
             enum "1579.28" {
               description "1579.28 nm/189.828125 THz 3.125GHz spacing";
             }
             enum "1579.26" {
               description "1579.26 nm/189.831250 THz 3.125/6.25GHz spacing";
             }
             enum "1579.23" {
               description "1579.23 nm/189.834375 THz 3.125GHz spacing";
             }
             enum "1579.21" {
               description "1579.21 nm/189.837500 THz 3.125/6.25/12.5GHz spacing";
             }
             enum "1579.18" {
               description "1579.18 nm/189.840625 THz 3.125GHz spacing";
             }
             enum "1579.15" {
               description "1579.15 nm/189.843750 THz 3.125/6.25GHz spacing";
             }
             enum "1579.13" {
               description "1579.13 nm/189.846875 THz 3.125GHz spacing";
             }
             enum "1579.10" {
               description "1579.10 nm/189.850000 THz 3.125/6.25/12.5/50GHz spacing";
             }
             enum "1579.08" {
               description "1579.08 nm/189.853125 THz 3.125GHz spacing";
             }
             enum "1579.05" {
               description "1579.05 nm/189.856250 THz 3.125/6.25GHz spacing";
             }
             enum "1579.02" {
               description "1579.02 nm/189.859375 THz 3.125GHz spacing";
             }
             enum "1579.00" {
               description "1579.00 nm/189.862500 THz 3.125/6.25/12.5GHz spacing";
             }
             enum "1578.97" {
               description "1578.97 nm/189.865625 THz 3.125GHz spacing";
             }
             enum "1578.95" {
               description "1578.95 nm/189.868750 THz 3.125/6.25GHz spacing";
             }
             enum "1578.92" {
               description "1578.92 nm/189.871875 THz 3.125GHz spacing";
             }
             enum "1578.89" {
               description "1578.89 nm/189.875000 THz 3.125/6.25/12.5/75GHz spacing";
             }
             enum "1578.87" {
               description "1578.87 nm/189.878125 THz 3.125GHz spacing";
             }
             enum "1578.84" {
               description "1578.84 nm/189.881250 THz 3.125/6.25GHz spacing";
             }
             enum "1578.82" {
               description "1578.82 nm/189.884375 THz 3.125GHz spacing";
             }
             enum "1578.79" {
               description "1578.79 nm/189.887500 THz 3.125/6.25/12.5GHz spacing";
             }
             enum "1578.76" {
               description "1578.76 nm/189.890625 THz 3.125GHz spacing";
             }
             enum "1578.74" {
               description "1578.74 nm/189.893750 THz 3.125/6.25GHz spacing";
             }
             enum "1578.71" {
               description "1578.71 nm/189.896875 THz 3.125GHz spacing";
             }
             enum "1578.69" {
               description "1578.69 nm/189.900000 THz 3.125/6.25/12.5/50/75/100GHz spacing";
             }
             enum "1578.66" {
               description "1578.66 nm/189.903125 THz 3.125GHz spacing";
             }
             enum "1578.63" {
               description "1578.63 nm/189.906250 THz 3.125/6.25GHz spacing";
             }
             enum "1578.61" {
               description "1578.61 nm/189.909375 THz 3.125GHz spacing";
             }
             enum "1578.58" {
               description "1578.58 nm/189.912500 THz 3.125/6.25/12.5GHz spacing";
             }
             enum "1578.56" {
               description "1578.56 nm/189.915625 THz 3.125GHz spacing";
             }
             enum "1578.53" {
               description "1578.53 nm/189.918750 THz 3.125/6.25GHz spacing";
             }
             enum "1578.50" {
               description "1578.50 nm/189.921875 THz 3.125GHz spacing";
             }
             enum "1578.48" {
               description "1578.48 nm/189.925000 THz 3.125/6.25/12.5GHz spacing";
             }
             enum "1578.45" {
               description "1578.45 nm/189.928125 THz 3.125GHz spacing";
             }
             enum "1578.43" {
               description "1578.43 nm/189.931250 THz 3.125/6.25GHz spacing";
             }
             enum "1578.40" {
               description "1578.40 nm/189.934375 THz 3.125GHz spacing";
             }
             enum "1578.37" {
               description "1578.37 nm/189.937500 THz 3.125/6.25/12.5GHz spacing";
             }
             enum "1578.35" {
               description "1578.35 nm/189.940625 THz 3.125GHz spacing";
             }
             enum "1578.32" {
               description "1578.32 nm/189.943750 THz 3.125/6.25GHz spacing";
             }
             enum "1578.30" {
               description "1578.30 nm/189.946875 THz 3.125GHz spacing";
             }
             enum "1578.27" {
               description "1578.27 nm/189.950000 THz 3.125/6.25/12.5/50/75GHz spacing";
             }
             enum "1578.24" {
               description "1578.24 nm/189.953125 THz 3.125GHz spacing";
             }
             enum "1578.22" {
               description "1578.22 nm/189.956250 THz 3.125/6.25GHz spacing";
             }
             enum "1578.19" {
               description "1578.19 nm/189.959375 THz 3.125GHz spacing";
             }
             enum "1578.17" {
               description "1578.17 nm/189.962500 THz 3.125/6.25/12.5GHz spacing";
             }
             enum "1578.14" {
               description "1578.14 nm/189.965625 THz 3.125GHz spacing";
             }
             enum "1578.11" {
               description "1578.11 nm/189.968750 THz 3.125/6.25GHz spacing";
             }
             enum "1578.09" {
               description "1578.09 nm/189.971875 THz 3.125GHz spacing";
             }
             enum "1578.06" {
               description "1578.06 nm/189.975000 THz 3.125/6.25/12.5GHz spacing";
             }
             enum "1578.04" {
               description "1578.04 nm/189.978125 THz 3.125GHz spacing";
             }
             enum "1578.01" {
               description "1578.01 nm/189.981250 THz 3.125/6.25GHz spacing";
             }
             enum "1577.98" {
               description "1577.98 nm/189.984375 THz 3.125GHz spacing";
             }
             enum "1577.96" {
               description "1577.96 nm/189.987500 THz 3.125/6.25/12.5GHz spacing";
             }
             enum "1577.93" {
               description "1577.93 nm/189.990625 THz 3.125GHz spacing";
             }
             enum "1577.91" {
               description "1577.91 nm/189.993750 THz 3.125/6.25GHz spacing";
             }
             enum "1577.88" {
               description "1577.88 nm/189.996875 THz 3.125GHz spacing";
             }
             enum "1577.86" {
               description "1577.86 nm/190.000000 THz 3.125/6.25/12.5/100GHz spacing";
             }
             enum "1577.83" {
               description "1577.83 nm/190.003125 THz 3.125GHz spacing";
             }
             enum "1577.80" {
               description "1577.80 nm/190.006250 THz 3.125/6.25GHz spacing";
             }
             enum "1577.78" {
               description "1577.78 nm/190.009375 THz 3.125GHz spacing";
             }
             enum "1577.75" {
               description "1577.75 nm/190.012500 THz 3.125/6.25/12.5GHz spacing";
             }
             enum "1577.73" {
               description "1577.73 nm/190.015625 THz 3.125GHz spacing";
             }
             enum "1577.70" {
               description "1577.70 nm/190.018750 THz 3.125/6.25GHz spacing";
             }
             enum "1577.67" {
               description "1577.67 nm/190.021875 THz 3.125GHz spacing";
             }
             enum "1577.65" {
               description "1577.65 nm/190.025000 THz 3.125/6.25/12.5/75GHz spacing";
             }
             enum "1577.62" {
               description "1577.62 nm/190.028125 THz 3.125GHz spacing";
             }
             enum "1577.60" {
               description "1577.60 nm/190.031250 THz 3.125/6.25GHz spacing";
             }
             enum "1577.57" {
               description "1577.57 nm/190.034375 THz 3.125GHz spacing";
             }
             enum "1577.54" {
               description "1577.54 nm/190.037500 THz 3.125/6.25/12.5GHz spacing";
             }
             enum "1577.52" {
               description "1577.52 nm/190.040625 THz 3.125GHz spacing";
             }
             enum "1577.49" {
               description "1577.49 nm/190.043750 THz 3.125/6.25GHz spacing";
             }
             enum "1577.47" {
               description "1577.47 nm/190.046875 THz 3.125GHz spacing";
             }
             enum "1577.44" {
               description "1577.44 nm/190.050000 THz 3.125/6.25/12.5/50GHz spacing";
             }
             enum "1577.41" {
               description "1577.41 nm/190.053125 THz 3.125GHz spacing";
             }
             enum "1577.39" {
               description "1577.39 nm/190.056250 THz 3.125/6.25GHz spacing";
             }
             enum "1577.36" {
               description "1577.36 nm/190.059375 THz 3.125GHz spacing";
             }
             enum "1577.34" {
               description "1577.34 nm/190.062500 THz 3.125/6.25/12.5GHz spacing";
             }
             enum "1577.31" {
               description "1577.31 nm/190.065625 THz 3.125GHz spacing";
             }
             enum "1577.28" {
               description "1577.28 nm/190.068750 THz 3.125/6.25GHz spacing";
             }
             enum "1577.26" {
               description "1577.26 nm/190.071875 THz 3.125GHz spacing";
             }
             enum "1577.23" {
               description "1577.23 nm/190.075000 THz 3.125/6.25/12.5GHz spacing";
             }
             enum "1577.21" {
               description "1577.21 nm/190.078125 THz 3.125GHz spacing";
             }
             enum "1577.18" {
               description "1577.18 nm/190.081250 THz 3.125/6.25GHz spacing";
             }
             enum "1577.15" {
               description "1577.15 nm/190.084375 THz 3.125GHz spacing";
             }
             enum "1577.13" {
               description "1577.13 nm/190.087500 THz 3.125/6.25/12.5GHz spacing";
             }
             enum "1577.10" {
               description "1577.10 nm/190.090625 THz 3.125GHz spacing";
             }
             enum "1577.08" {
               description "1577.08 nm/190.093750 THz 3.125/6.25GHz spacing";
             }
             enum "1577.05" {
               description "1577.05 nm/190.096875 THz 3.125GHz spacing";
             }
             enum "1577.03" {
               description "1577.03 nm/190.100000 THz 3.125/6.25/12.5/100GHz spacing";
             }
             enum "1577.00" {
               description "1577.00 nm/190.103125 THz 3.125GHz spacing";
             }
             enum "1576.97" {
               description "1576.97 nm/190.106250 THz 3.125/6.25GHz spacing";
             }
             enum "1576.95" {
               description "1576.95 nm/190.109375 THz 3.125GHz spacing";
             }
             enum "1576.92" {
               description "1576.92 nm/190.112500 THz 3.125/6.25/12.5GHz spacing";
             }
             enum "1576.90" {
               description "1576.90 nm/190.115625 THz 3.125GHz spacing";
             }
             enum "1576.87" {
               description "1576.87 nm/190.118750 THz 3.125/6.25GHz spacing";
             }
             enum "1576.84" {
               description "1576.84 nm/190.121875 THz 3.125GHz spacing";
             }
             enum "1576.82" {
               description "1576.82 nm/190.125000 THz 3.125/6.25/12.5GHz spacing";
             }
             enum "1576.79" {
               description "1576.79 nm/190.128125 THz 3.125GHz spacing";
             }
             enum "1576.77" {
               description "1576.77 nm/190.131250 THz 3.125/6.25GHz spacing";
             }
             enum "1576.74" {
               description "1576.74 nm/190.134375 THz 3.125GHz spacing";
             }
             enum "1576.71" {
               description "1576.71 nm/190.137500 THz 3.125/6.25/12.5GHz spacing";
             }
             enum "1576.69" {
               description "1576.69 nm/190.140625 THz 3.125GHz spacing";
             }
             enum "1576.66" {
               description "1576.66 nm/190.143750 THz 3.125/6.25GHz spacing";
             }
             enum "1576.64" {
               description "1576.64 nm/190.146875 THz 3.125GHz spacing";
             }
             enum "1576.61" {
               description "1576.61 nm/190.150000 THz 3.125/6.25/12.5/50GHz spacing";
             }
             enum "1576.58" {
               description "1576.58 nm/190.153125 THz 3.125GHz spacing";
             }
             enum "1576.56" {
               description "1576.56 nm/190.156250 THz 3.125/6.25GHz spacing";
             }
             enum "1576.53" {
               description "1576.53 nm/190.159375 THz 3.125GHz spacing";
             }
             enum "1576.51" {
               description "1576.51 nm/190.162500 THz 3.125/6.25/12.5GHz spacing";
             }
             enum "1576.48" {
               description "1576.48 nm/190.165625 THz 3.125GHz spacing";
             }
             enum "1576.45" {
               description "1576.45 nm/190.168750 THz 3.125/6.25GHz spacing";
             }
             enum "1576.43" {
               description "1576.43 nm/190.171875 THz 3.125GHz spacing";
             }
             enum "1576.40" {
               description "1576.40 nm/190.175000 THz 3.125/6.25/12.5/75GHz spacing";
             }
             enum "1576.38" {
               description "1576.38 nm/190.178125 THz 3.125GHz spacing";
             }
             enum "1576.35" {
               description "1576.35 nm/190.181250 THz 3.125/6.25GHz spacing";
             }
             enum "1576.33" {
               description "1576.33 nm/190.184375 THz 3.125GHz spacing";
             }
             enum "1576.30" {
               description "1576.30 nm/190.187500 THz 3.125/6.25/12.5GHz spacing";
             }
             enum "1576.27" {
               description "1576.27 nm/190.190625 THz 3.125GHz spacing";
             }
             enum "1576.25" {
               description "1576.25 nm/190.193750 THz 3.125/6.25GHz spacing";
             }
             enum "1576.22" {
               description "1576.22 nm/190.196875 THz 3.125GHz spacing";
             }
             enum "1576.20" {
               description "1576.20 nm/190.200000 THz 3.125/6.25/12.5/50/75/100GHz spacing";
             }
             enum "1576.17" {
               description "1576.17 nm/190.203125 THz 3.125GHz spacing";
             }
             enum "1576.14" {
               description "1576.14 nm/190.206250 THz 3.125/6.25GHz spacing";
             }
             enum "1576.12" {
               description "1576.12 nm/190.209375 THz 3.125GHz spacing";
             }
             enum "1576.09" {
               description "1576.09 nm/190.212500 THz 3.125/6.25/12.5GHz spacing";
             }
             enum "1576.07" {
               description "1576.07 nm/190.215625 THz 3.125GHz spacing";
             }
             enum "1576.04" {
               description "1576.04 nm/190.218750 THz 3.125/6.25GHz spacing";
             }
             enum "1576.01" {
               description "1576.01 nm/190.221875 THz 3.125GHz spacing";
             }
             enum "1575.99" {
               description "1575.99 nm/190.225000 THz 3.125/6.25/12.5GHz spacing";
             }
             enum "1575.96" {
               description "1575.96 nm/190.228125 THz 3.125GHz spacing";
             }
             enum "1575.94" {
               description "1575.94 nm/190.231250 THz 3.125/6.25GHz spacing";
             }
             enum "1575.91" {
               description "1575.91 nm/190.234375 THz 3.125GHz spacing";
             }
             enum "1575.89" {
               description "1575.89 nm/190.237500 THz 3.125/6.25/12.5GHz spacing";
             }
             enum "1575.86" {
               description "1575.86 nm/190.240625 THz 3.125GHz spacing";
             }
             enum "1575.83" {
               description "1575.83 nm/190.243750 THz 3.125/6.25GHz spacing";
             }
             enum "1575.81" {
               description "1575.81 nm/190.246875 THz 3.125GHz spacing";
             }
             enum "1575.78" {
               description "1575.78 nm/190.250000 THz 3.125/6.25/12.5/50/75GHz spacing";
             }
             enum "1575.76" {
               description "1575.76 nm/190.253125 THz 3.125GHz spacing";
             }
             enum "1575.73" {
               description "1575.73 nm/190.256250 THz 3.125/6.25GHz spacing";
             }
             enum "1575.70" {
               description "1575.70 nm/190.259375 THz 3.125GHz spacing";
             }
             enum "1575.68" {
               description "1575.68 nm/190.262500 THz 3.125/6.25/12.5GHz spacing";
             }
             enum "1575.65" {
               description "1575.65 nm/190.265625 THz 3.125GHz spacing";
             }
             enum "1575.63" {
               description "1575.63 nm/190.268750 THz 3.125/6.25GHz spacing";
             }
             enum "1575.60" {
               description "1575.60 nm/190.271875 THz 3.125GHz spacing";
             }
             enum "1575.57" {
               description "1575.57 nm/190.275000 THz 3.125/6.25/12.5GHz spacing";
             }
             enum "1575.55" {
               description "1575.55 nm/190.278125 THz 3.125GHz spacing";
             }
             enum "1575.52" {
               description "1575.52 nm/190.281250 THz 3.125/6.25GHz spacing";
             }
             enum "1575.50" {
               description "1575.50 nm/190.284375 THz 3.125GHz spacing";
             }
             enum "1575.47" {
               description "1575.47 nm/190.287500 THz 3.125/6.25/12.5GHz spacing";
             }
             enum "1575.45" {
               description "1575.45 nm/190.290625 THz 3.125GHz spacing";
             }
             enum "1575.42" {
               description "1575.42 nm/190.293750 THz 3.125/6.25GHz spacing";
             }
             enum "1575.39" {
               description "1575.39 nm/190.296875 THz 3.125GHz spacing";
             }
             enum "1575.37" {
               description "1575.37 nm/190.300000 THz 3.125/6.25/12.5/100GHz spacing";
             }
             enum "1575.34" {
               description "1575.34 nm/190.303125 THz 3.125GHz spacing";
             }
             enum "1575.32" {
               description "1575.32 nm/190.306250 THz 3.125/6.25GHz spacing";
             }
             enum "1575.29" {
               description "1575.29 nm/190.309375 THz 3.125GHz spacing";
             }
             enum "1575.26" {
               description "1575.26 nm/190.312500 THz 3.125/6.25/12.5GHz spacing";
             }
             enum "1575.24" {
               description "1575.24 nm/190.315625 THz 3.125GHz spacing";
             }
             enum "1575.21" {
               description "1575.21 nm/190.318750 THz 3.125/6.25GHz spacing";
             }
             enum "1575.19" {
               description "1575.19 nm/190.321875 THz 3.125GHz spacing";
             }
             enum "1575.16" {
               description "1575.16 nm/190.325000 THz 3.125/6.25/12.5/75GHz spacing";
             }
             enum "1575.13" {
               description "1575.13 nm/190.328125 THz 3.125GHz spacing";
             }
             enum "1575.11" {
               description "1575.11 nm/190.331250 THz 3.125/6.25GHz spacing";
             }
             enum "1575.08" {
               description "1575.08 nm/190.334375 THz 3.125GHz spacing";
             }
             enum "1575.06" {
               description "1575.06 nm/190.337500 THz 3.125/6.25/12.5GHz spacing";
             }
             enum "1575.03" {
               description "1575.03 nm/190.340625 THz 3.125GHz spacing";
             }
             enum "1575.01" {
               description "1575.01 nm/190.343750 THz 3.125/6.25GHz spacing";
             }
             enum "1574.98" {
               description "1574.98 nm/190.346875 THz 3.125GHz spacing";
             }
             enum "1574.95" {
               description "1574.95 nm/190.350000 THz 3.125/6.25/12.5/50GHz spacing";
             }
             enum "1574.93" {
               description "1574.93 nm/190.353125 THz 3.125GHz spacing";
             }
             enum "1574.90" {
               description "1574.90 nm/190.356250 THz 3.125/6.25GHz spacing";
             }
             enum "1574.88" {
               description "1574.88 nm/190.359375 THz 3.125GHz spacing";
             }
             enum "1574.85" {
               description "1574.85 nm/190.362500 THz 3.125/6.25/12.5GHz spacing";
             }
             enum "1574.82" {
               description "1574.82 nm/190.365625 THz 3.125GHz spacing";
             }
             enum "1574.80" {
               description "1574.80 nm/190.368750 THz 3.125/6.25GHz spacing";
             }
             enum "1574.77" {
               description "1574.77 nm/190.371875 THz 3.125GHz spacing";
             }
             enum "1574.75" {
               description "1574.75 nm/190.375000 THz 3.125/6.25/12.5GHz spacing";
             }
             enum "1574.72" {
               description "1574.72 nm/190.378125 THz 3.125GHz spacing";
             }
             enum "1574.70" {
               description "1574.70 nm/190.381250 THz 3.125/6.25GHz spacing";
             }
             enum "1574.67" {
               description "1574.67 nm/190.384375 THz 3.125GHz spacing";
             }
             enum "1574.64" {
               description "1574.64 nm/190.387500 THz 3.125/6.25/12.5GHz spacing";
             }
             enum "1574.62" {
               description "1574.62 nm/190.390625 THz 3.125GHz spacing";
             }
             enum "1574.59" {
               description "1574.59 nm/190.393750 THz 3.125/6.25GHz spacing";
             }
             enum "1574.57" {
               description "1574.57 nm/190.396875 THz 3.125GHz spacing";
             }
             enum "1574.54" {
               description "1574.54 nm/190.400000 THz 3.125/6.25/12.5/100GHz spacing";
             }
             enum "1574.51" {
               description "1574.51 nm/190.403125 THz 3.125GHz spacing";
             }
             enum "1574.49" {
               description "1574.49 nm/190.406250 THz 3.125/6.25GHz spacing";
             }
             enum "1574.46" {
               description "1574.46 nm/190.409375 THz 3.125GHz spacing";
             }
             enum "1574.44" {
               description "1574.44 nm/190.412500 THz 3.125/6.25/12.5GHz spacing";
             }
             enum "1574.41" {
               description "1574.41 nm/190.415625 THz 3.125GHz spacing";
             }
             enum "1574.39" {
               description "1574.39 nm/190.418750 THz 3.125/6.25GHz spacing";
             }
             enum "1574.36" {
               description "1574.36 nm/190.421875 THz 3.125GHz spacing";
             }
             enum "1574.33" {
               description "1574.33 nm/190.425000 THz 3.125/6.25/12.5GHz spacing";
             }
             enum "1574.31" {
               description "1574.31 nm/190.428125 THz 3.125GHz spacing";
             }
             enum "1574.28" {
               description "1574.28 nm/190.431250 THz 3.125/6.25GHz spacing";
             }
             enum "1574.26" {
               description "1574.26 nm/190.434375 THz 3.125GHz spacing";
             }
             enum "1574.23" {
               description "1574.23 nm/190.437500 THz 3.125/6.25/12.5GHz spacing";
             }
             enum "1574.20" {
               description "1574.20 nm/190.440625 THz 3.125GHz spacing";
             }
             enum "1574.18" {
               description "1574.18 nm/190.443750 THz 3.125/6.25GHz spacing";
             }
             enum "1574.15" {
               description "1574.15 nm/190.446875 THz 3.125GHz spacing";
             }
             enum "1574.13" {
               description "1574.13 nm/190.450000 THz 3.125/6.25/12.5/50GHz spacing";
             }
             enum "1574.10" {
               description "1574.10 nm/190.453125 THz 3.125GHz spacing";
             }
             enum "1574.08" {
               description "1574.08 nm/190.456250 THz 3.125/6.25GHz spacing";
             }
             enum "1574.05" {
               description "1574.05 nm/190.459375 THz 3.125GHz spacing";
             }
             enum "1574.02" {
               description "1574.02 nm/190.462500 THz 3.125/6.25/12.5GHz spacing";
             }
             enum "1574.00" {
               description "1574.00 nm/190.465625 THz 3.125GHz spacing";
             }
             enum "1573.97" {
               description "1573.97 nm/190.468750 THz 3.125/6.25GHz spacing";
             }
             enum "1573.95" {
               description "1573.95 nm/190.471875 THz 3.125GHz spacing";
             }
             enum "1573.92" {
               description "1573.92 nm/190.475000 THz 3.125/6.25/12.5/75GHz spacing";
             }
             enum "1573.89" {
               description "1573.89 nm/190.478125 THz 3.125GHz spacing";
             }
             enum "1573.87" {
               description "1573.87 nm/190.481250 THz 3.125/6.25GHz spacing";
             }
             enum "1573.84" {
               description "1573.84 nm/190.484375 THz 3.125GHz spacing";
             }
             enum "1573.82" {
               description "1573.82 nm/190.487500 THz 3.125/6.25/12.5GHz spacing";
             }
             enum "1573.79" {
               description "1573.79 nm/190.490625 THz 3.125GHz spacing";
             }
             enum "1573.77" {
               description "1573.77 nm/190.493750 THz 3.125/6.25GHz spacing";
             }
             enum "1573.74" {
               description "1573.74 nm/190.496875 THz 3.125GHz spacing";
             }
             enum "1573.71" {
               description "1573.71 nm/190.500000 THz 3.125/6.25/12.5/50/75/100GHz spacing";
             }
             enum "1573.69" {
               description "1573.69 nm/190.503125 THz 3.125GHz spacing";
             }
             enum "1573.66" {
               description "1573.66 nm/190.506250 THz 3.125/6.25GHz spacing";
             }
             enum "1573.64" {
               description "1573.64 nm/190.509375 THz 3.125GHz spacing";
             }
             enum "1573.61" {
               description "1573.61 nm/190.512500 THz 3.125/6.25/12.5GHz spacing";
             }
             enum "1573.58" {
               description "1573.58 nm/190.515625 THz 3.125GHz spacing";
             }
             enum "1573.56" {
               description "1573.56 nm/190.518750 THz 3.125/6.25GHz spacing";
             }
             enum "1573.53" {
               description "1573.53 nm/190.521875 THz 3.125GHz spacing";
             }
             enum "1573.51" {
               description "1573.51 nm/190.525000 THz 3.125/6.25/12.5GHz spacing";
             }
             enum "1573.48" {
               description "1573.48 nm/190.528125 THz 3.125GHz spacing";
             }
             enum "1573.46" {
               description "1573.46 nm/190.531250 THz 3.125/6.25GHz spacing";
             }
             enum "1573.43" {
               description "1573.43 nm/190.534375 THz 3.125GHz spacing";
             }
             enum "1573.40" {
               description "1573.40 nm/190.537500 THz 3.125/6.25/12.5GHz spacing";
             }
             enum "1573.38" {
               description "1573.38 nm/190.540625 THz 3.125GHz spacing";
             }
             enum "1573.35" {
               description "1573.35 nm/190.543750 THz 3.125/6.25GHz spacing";
             }
             enum "1573.33" {
               description "1573.33 nm/190.546875 THz 3.125GHz spacing";
             }
             enum "1573.30" {
               description "1573.30 nm/190.550000 THz 3.125/6.25/12.5/50/75GHz spacing";
             }
             enum "1573.27" {
               description "1573.27 nm/190.553125 THz 3.125GHz spacing";
             }
             enum "1573.25" {
               description "1573.25 nm/190.556250 THz 3.125/6.25GHz spacing";
             }
             enum "1573.22" {
               description "1573.22 nm/190.559375 THz 3.125GHz spacing";
             }
             enum "1573.20" {
               description "1573.20 nm/190.562500 THz 3.125/6.25/12.5GHz spacing";
             }
             enum "1573.17" {
               description "1573.17 nm/190.565625 THz 3.125GHz spacing";
             }
             enum "1573.15" {
               description "1573.15 nm/190.568750 THz 3.125/6.25GHz spacing";
             }
             enum "1573.12" {
               description "1573.12 nm/190.571875 THz 3.125GHz spacing";
             }
             enum "1573.09" {
               description "1573.09 nm/190.575000 THz 3.125/6.25/12.5GHz spacing";
             }
             enum "1573.07" {
               description "1573.07 nm/190.578125 THz 3.125GHz spacing";
             }
             enum "1573.04" {
               description "1573.04 nm/190.581250 THz 3.125/6.25GHz spacing";
             }
             enum "1573.02" {
               description "1573.02 nm/190.584375 THz 3.125GHz spacing";
             }
             enum "1572.99" {
               description "1572.99 nm/190.587500 THz 3.125/6.25/12.5GHz spacing";
             }
             enum "1572.97" {
               description "1572.97 nm/190.590625 THz 3.125GHz spacing";
             }
             enum "1572.94" {
               description "1572.94 nm/190.593750 THz 3.125/6.25GHz spacing";
             }
             enum "1572.91" {
               description "1572.91 nm/190.596875 THz 3.125GHz spacing";
             }
             enum "1572.89" {
               description "1572.89 nm/190.600000 THz 3.125/6.25/12.5/100GHz spacing";
             }
             enum "1572.86" {
               description "1572.86 nm/190.603125 THz 3.125GHz spacing";
             }
             enum "1572.84" {
               description "1572.84 nm/190.606250 THz 3.125/6.25GHz spacing";
             }
             enum "1572.81" {
               description "1572.81 nm/190.609375 THz 3.125GHz spacing";
             }
             enum "1572.78" {
               description "1572.78 nm/190.612500 THz 3.125/6.25/12.5GHz spacing";
             }
             enum "1572.76" {
               description "1572.76 nm/190.615625 THz 3.125GHz spacing";
             }
             enum "1572.73" {
               description "1572.73 nm/190.618750 THz 3.125/6.25GHz spacing";
             }
             enum "1572.71" {
               description "1572.71 nm/190.621875 THz 3.125GHz spacing";
             }
             enum "1572.68" {
               description "1572.68 nm/190.625000 THz 3.125/6.25/12.5/75GHz spacing";
             }
             enum "1572.66" {
               description "1572.66 nm/190.628125 THz 3.125GHz spacing";
             }
             enum "1572.63" {
               description "1572.63 nm/190.631250 THz 3.125/6.25GHz spacing";
             }
             enum "1572.60" {
               description "1572.60 nm/190.634375 THz 3.125GHz spacing";
             }
             enum "1572.58" {
               description "1572.58 nm/190.637500 THz 3.125/6.25/12.5GHz spacing";
             }
             enum "1572.55" {
               description "1572.55 nm/190.640625 THz 3.125GHz spacing";
             }
             enum "1572.53" {
               description "1572.53 nm/190.643750 THz 3.125/6.25GHz spacing";
             }
             enum "1572.50" {
               description "1572.50 nm/190.646875 THz 3.125GHz spacing";
             }
             enum "1572.48" {
               description "1572.48 nm/190.650000 THz 3.125/6.25/12.5/50GHz spacing";
             }
             enum "1572.45" {
               description "1572.45 nm/190.653125 THz 3.125GHz spacing";
             }
             enum "1572.42" {
               description "1572.42 nm/190.656250 THz 3.125/6.25GHz spacing";
             }
             enum "1572.40" {
               description "1572.40 nm/190.659375 THz 3.125GHz spacing";
             }
             enum "1572.37" {
               description "1572.37 nm/190.662500 THz 3.125/6.25/12.5GHz spacing";
             }
             enum "1572.35" {
               description "1572.35 nm/190.665625 THz 3.125GHz spacing";
             }
             enum "1572.32" {
               description "1572.32 nm/190.668750 THz 3.125/6.25GHz spacing";
             }
             enum "1572.30" {
               description "1572.30 nm/190.671875 THz 3.125GHz spacing";
             }
             enum "1572.27" {
               description "1572.27 nm/190.675000 THz 3.125/6.25/12.5GHz spacing";
             }
             enum "1572.24" {
               description "1572.24 nm/190.678125 THz 3.125GHz spacing";
             }
             enum "1572.22" {
               description "1572.22 nm/190.681250 THz 3.125/6.25GHz spacing";
             }
             enum "1572.19" {
               description "1572.19 nm/190.684375 THz 3.125GHz spacing";
             }
             enum "1572.17" {
               description "1572.17 nm/190.687500 THz 3.125/6.25/12.5GHz spacing";
             }
             enum "1572.14" {
               description "1572.14 nm/190.690625 THz 3.125GHz spacing";
             }
             enum "1572.11" {
               description "1572.11 nm/190.693750 THz 3.125/6.25GHz spacing";
             }
             enum "1572.09" {
               description "1572.09 nm/190.696875 THz 3.125GHz spacing";
             }
             enum "1572.06" {
               description "1572.06 nm/190.700000 THz 3.125/6.25/12.5/100GHz spacing";
             }
             enum "1572.04" {
               description "1572.04 nm/190.703125 THz 3.125GHz spacing";
             }
             enum "1572.01" {
               description "1572.01 nm/190.706250 THz 3.125/6.25GHz spacing";
             }
             enum "1571.99" {
               description "1571.99 nm/190.709375 THz 3.125GHz spacing";
             }
             enum "1571.96" {
               description "1571.96 nm/190.712500 THz 3.125/6.25/12.5GHz spacing";
             }
             enum "1571.93" {
               description "1571.93 nm/190.715625 THz 3.125GHz spacing";
             }
             enum "1571.91" {
               description "1571.91 nm/190.718750 THz 3.125/6.25GHz spacing";
             }
             enum "1571.88" {
               description "1571.88 nm/190.721875 THz 3.125GHz spacing";
             }
             enum "1571.86" {
               description "1571.86 nm/190.725000 THz 3.125/6.25/12.5GHz spacing";
             }
             enum "1571.83" {
               description "1571.83 nm/190.728125 THz 3.125GHz spacing";
             }
             enum "1571.81" {
               description "1571.81 nm/190.731250 THz 3.125/6.25GHz spacing";
             }
             enum "1571.78" {
               description "1571.78 nm/190.734375 THz 3.125GHz spacing";
             }
             enum "1571.75" {
               description "1571.75 nm/190.737500 THz 3.125/6.25/12.5GHz spacing";
             }
             enum "1571.73" {
               description "1571.73 nm/190.740625 THz 3.125GHz spacing";
             }
             enum "1571.70" {
               description "1571.70 nm/190.743750 THz 3.125/6.25GHz spacing";
             }
             enum "1571.68" {
               description "1571.68 nm/190.746875 THz 3.125GHz spacing";
             }
             enum "1571.65" {
               description "1571.65 nm/190.750000 THz 3.125/6.25/12.5/50GHz spacing";
             }
             enum "1571.63" {
               description "1571.63 nm/190.753125 THz 3.125GHz spacing";
             }
             enum "1571.60" {
               description "1571.60 nm/190.756250 THz 3.125/6.25GHz spacing";
             }
             enum "1571.57" {
               description "1571.57 nm/190.759375 THz 3.125GHz spacing";
             }
             enum "1571.55" {
               description "1571.55 nm/190.762500 THz 3.125/6.25/12.5GHz spacing";
             }
             enum "1571.52" {
               description "1571.52 nm/190.765625 THz 3.125GHz spacing";
             }
             enum "1571.50" {
               description "1571.50 nm/190.768750 THz 3.125/6.25GHz spacing";
             }
             enum "1571.47" {
               description "1571.47 nm/190.771875 THz 3.125GHz spacing";
             }
             enum "1571.45" {
               description "1571.45 nm/190.775000 THz 3.125/6.25/12.5/75GHz spacing";
             }
             enum "1571.42" {
               description "1571.42 nm/190.778125 THz 3.125GHz spacing";
             }
             enum "1571.39" {
               description "1571.39 nm/190.781250 THz 3.125/6.25GHz spacing";
             }
             enum "1571.37" {
               description "1571.37 nm/190.784375 THz 3.125GHz spacing";
             }
             enum "1571.34" {
               description "1571.34 nm/190.787500 THz 3.125/6.25/12.5GHz spacing";
             }
             enum "1571.32" {
               description "1571.32 nm/190.790625 THz 3.125GHz spacing";
             }
             enum "1571.29" {
               description "1571.29 nm/190.793750 THz 3.125/6.25GHz spacing";
             }
             enum "1571.27" {
               description "1571.27 nm/190.796875 THz 3.125GHz spacing";
             }
             enum "1571.24" {
               description "1571.24 nm/190.800000 THz 3.125/6.25/12.5/50/75/100GHz spacing";
             }
             enum "1571.21" {
               description "1571.21 nm/190.803125 THz 3.125GHz spacing";
             }
             enum "1571.19" {
               description "1571.19 nm/190.806250 THz 3.125/6.25GHz spacing";
             }
             enum "1571.16" {
               description "1571.16 nm/190.809375 THz 3.125GHz spacing";
             }
             enum "1571.14" {
               description "1571.14 nm/190.812500 THz 3.125/6.25/12.5GHz spacing";
             }
             enum "1571.11" {
               description "1571.11 nm/190.815625 THz 3.125GHz spacing";
             }
             enum "1571.08" {
               description "1571.08 nm/190.818750 THz 3.125/6.25GHz spacing";
             }
             enum "1571.06" {
               description "1571.06 nm/190.821875 THz 3.125GHz spacing";
             }
             enum "1571.03" {
               description "1571.03 nm/190.825000 THz 3.125/6.25/12.5GHz spacing";
             }
             enum "1571.01" {
               description "1571.01 nm/190.828125 THz 3.125GHz spacing";
             }
             enum "1570.98" {
               description "1570.98 nm/190.831250 THz 3.125/6.25GHz spacing";
             }
             enum "1570.96" {
               description "1570.96 nm/190.834375 THz 3.125GHz spacing";
             }
             enum "1570.93" {
               description "1570.93 nm/190.837500 THz 3.125/6.25/12.5GHz spacing";
             }
             enum "1570.90" {
               description "1570.90 nm/190.840625 THz 3.125GHz spacing";
             }
             enum "1570.88" {
               description "1570.88 nm/190.843750 THz 3.125/6.25GHz spacing";
             }
             enum "1570.85" {
               description "1570.85 nm/190.846875 THz 3.125GHz spacing";
             }
             enum "1570.83" {
               description "1570.83 nm/190.850000 THz 3.125/6.25/12.5/50/75GHz spacing";
             }
             enum "1570.80" {
               description "1570.80 nm/190.853125 THz 3.125GHz spacing";
             }
             enum "1570.78" {
               description "1570.78 nm/190.856250 THz 3.125/6.25GHz spacing";
             }
             enum "1570.75" {
               description "1570.75 nm/190.859375 THz 3.125GHz spacing";
             }
             enum "1570.72" {
               description "1570.72 nm/190.862500 THz 3.125/6.25/12.5GHz spacing";
             }
             enum "1570.70" {
               description "1570.70 nm/190.865625 THz 3.125GHz spacing";
             }
             enum "1570.67" {
               description "1570.67 nm/190.868750 THz 3.125/6.25GHz spacing";
             }
             enum "1570.65" {
               description "1570.65 nm/190.871875 THz 3.125GHz spacing";
             }
             enum "1570.62" {
               description "1570.62 nm/190.875000 THz 3.125/6.25/12.5GHz spacing";
             }
             enum "1570.60" {
               description "1570.60 nm/190.878125 THz 3.125GHz spacing";
             }
             enum "1570.57" {
               description "1570.57 nm/190.881250 THz 3.125/6.25GHz spacing";
             }
             enum "1570.54" {
               description "1570.54 nm/190.884375 THz 3.125GHz spacing";
             }
             enum "1570.52" {
               description "1570.52 nm/190.887500 THz 3.125/6.25/12.5GHz spacing";
             }
             enum "1570.49" {
               description "1570.49 nm/190.890625 THz 3.125GHz spacing";
             }
             enum "1570.47" {
               description "1570.47 nm/190.893750 THz 3.125/6.25GHz spacing";
             }
             enum "1570.44" {
               description "1570.44 nm/190.896875 THz 3.125GHz spacing";
             }
             enum "1570.42" {
               description "1570.42 nm/190.900000 THz 3.125/6.25/12.5/100GHz spacing";
             }
             enum "1570.39" {
               description "1570.39 nm/190.903125 THz 3.125GHz spacing";
             }
             enum "1570.36" {
               description "1570.36 nm/190.906250 THz 3.125/6.25GHz spacing";
             }
             enum "1570.34" {
               description "1570.34 nm/190.909375 THz 3.125GHz spacing";
             }
             enum "1570.31" {
               description "1570.31 nm/190.912500 THz 3.125/6.25/12.5GHz spacing";
             }
             enum "1570.29" {
               description "1570.29 nm/190.915625 THz 3.125GHz spacing";
             }
             enum "1570.26" {
               description "1570.26 nm/190.918750 THz 3.125/6.25GHz spacing";
             }
             enum "1570.24" {
               description "1570.24 nm/190.921875 THz 3.125GHz spacing";
             }
             enum "1570.21" {
               description "1570.21 nm/190.925000 THz 3.125/6.25/12.5/75GHz spacing";
             }
             enum "1570.18" {
               description "1570.18 nm/190.928125 THz 3.125GHz spacing";
             }
             enum "1570.16" {
               description "1570.16 nm/190.931250 THz 3.125/6.25GHz spacing";
             }
             enum "1570.13" {
               description "1570.13 nm/190.934375 THz 3.125GHz spacing";
             }
             enum "1570.11" {
               description "1570.11 nm/190.937500 THz 3.125/6.25/12.5GHz spacing";
             }
             enum "1570.08" {
               description "1570.08 nm/190.940625 THz 3.125GHz spacing";
             }
             enum "1570.06" {
               description "1570.06 nm/190.943750 THz 3.125/6.25GHz spacing";
             }
             enum "1570.03" {
               description "1570.03 nm/190.946875 THz 3.125GHz spacing";
             }
             enum "1570.01" {
               description "1570.01 nm/190.950000 THz 3.125/6.25/12.5/50GHz spacing";
             }
             enum "1569.98" {
               description "1569.98 nm/190.953125 THz 3.125GHz spacing";
             }
             enum "1569.95" {
               description "1569.95 nm/190.956250 THz 3.125/6.25GHz spacing";
             }
             enum "1569.93" {
               description "1569.93 nm/190.959375 THz 3.125GHz spacing";
             }
             enum "1569.90" {
               description "1569.90 nm/190.962500 THz 3.125/6.25/12.5GHz spacing";
             }
             enum "1569.88" {
               description "1569.88 nm/190.965625 THz 3.125GHz spacing";
             }
             enum "1569.85" {
               description "1569.85 nm/190.968750 THz 3.125/6.25GHz spacing";
             }
             enum "1569.83" {
               description "1569.83 nm/190.971875 THz 3.125GHz spacing";
             }
             enum "1569.80" {
               description "1569.80 nm/190.975000 THz 3.125/6.25/12.5GHz spacing";
             }
             enum "1569.77" {
               description "1569.77 nm/190.978125 THz 3.125GHz spacing";
             }
             enum "1569.75" {
               description "1569.75 nm/190.981250 THz 3.125/6.25GHz spacing";
             }
             enum "1569.72" {
               description "1569.72 nm/190.984375 THz 3.125GHz spacing";
             }
             enum "1569.70" {
               description "1569.70 nm/190.987500 THz 3.125/6.25/12.5GHz spacing";
             }
             enum "1569.67" {
               description "1569.67 nm/190.990625 THz 3.125GHz spacing";
             }
             enum "1569.65" {
               description "1569.65 nm/190.993750 THz 3.125/6.25GHz spacing";
             }
             enum "1569.62" {
               description "1569.62 nm/190.996875 THz 3.125GHz spacing";
             }
             enum "1569.59" {
               description "1569.59 nm/191.000000 THz 3.125/6.25/12.5/100GHz spacing";
             }
             enum "1568.77" {
               description "1568.77 nm/191.1003 THz 50/100Ghz spacing";
             }
             enum "1568.36" {
               description "1568.36 nm/191.150000 THz 3.125/6.25/12.5/50/75GHz spacing";
             }
             enum "1568.34" {
               description "1568.34 nm/191.153125 THz 3.125GHz spacing";
             }
             enum "1568.31" {
               description "1568.31 nm/191.156250 THz 3.125/6.25GHz spacing";
             }
             enum "1568.29" {
               description "1568.29 nm/191.159375 THz 3.125GHz spacing";
             }
             enum "1568.26" {
               description "1568.26 nm/191.162500 THz 3.125/6.25/12.5GHz spacing";
             }
             enum "1568.23" {
               description "1568.23 nm/191.165625 THz 3.125GHz spacing";
             }
             enum "1568.21" {
               description "1568.21 nm/191.168750 THz 3.125/6.25GHz spacing";
             }
             enum "1568.18" {
               description "1568.18 nm/191.171875 THz 3.125GHz spacing";
             }
             enum "1568.16" {
               description "1568.16 nm/191.175000 THz 3.125/6.25/12.5/75GHz spacing";
             }
             enum "1568.13" {
               description "1568.13 nm/191.178125 THz 3.125GHz spacing";
             }
             enum "1568.11" {
               description "1568.11 nm/191.181250 THz 3.125/6.25GHz spacing";
             }
             enum "1568.08" {
               description "1568.08 nm/191.184375 THz 3.125GHz spacing";
             }
             enum "1568.05" {
               description "1568.05 nm/191.187500 THz 3.125/6.25/12.5GHz spacing";
             }
             enum "1568.03" {
               description "1568.03 nm/191.190625 THz 3.125GHz spacing";
             }
             enum "1568.00" {
               description "1568.00 nm/191.193750 THz 3.125/6.25GHz spacing";
             }
             enum "1567.98" {
               description "1567.98 nm/191.196875 THz 3.125GHz spacing";
             }
             enum "1567.95" {
               description "1567.95 nm/191.200000 THz 3.125/6.25/12.5/100GHz spacing";
             }
             enum "1567.93" {
               description "1567.93 nm/191.203125 THz 3.125GHz spacing";
             }
             enum "1567.90" {
               description "1567.90 nm/191.206250 THz 3.125/6.25GHz spacing";
             }
             enum "1567.88" {
               description "1567.88 nm/191.209375 THz 3.125GHz spacing";
             }
             enum "1567.85" {
               description "1567.85 nm/191.212500 THz 3.125/6.25/12.5GHz spacing";
             }
             enum "1567.82" {
               description "1567.82 nm/191.215625 THz 3.125GHz spacing";
             }
             enum "1567.80" {
               description "1567.80 nm/191.218750 THz 3.125/6.25GHz spacing";
             }
             enum "1567.77" {
               description "1567.77 nm/191.221875 THz 3.125GHz spacing";
             }
             enum "1567.75" {
               description "1567.75 nm/191.225000 THz 3.125/6.25/12.5/75GHz spacing";
             }
             enum "1567.72" {
               description "1567.72 nm/191.228125 THz 3.125GHz spacing";
             }
             enum "1567.70" {
               description "1567.70 nm/191.231250 THz 3.125/6.25GHz spacing";
             }
             enum "1567.67" {
               description "1567.67 nm/191.234375 THz 3.125GHz spacing";
             }
             enum "1567.64" {
               description "1567.64 nm/191.237500 THz 3.125/6.25/12.5GHz spacing";
             }
             enum "1567.62" {
               description "1567.62 nm/191.240625 THz 3.125GHz spacing";
             }
             enum "1567.59" {
               description "1567.59 nm/191.243750 THz 3.125/6.25GHz spacing";
             }
             enum "1567.57" {
               description "1567.57 nm/191.246875 THz 3.125GHz spacing";
             }
             enum "1567.54" {
               description "1567.54 nm/191.250000 THz 3.125/6.25/12.5/50/75GHz spacing";
             }
             enum "1567.52" {
               description "1567.52 nm/191.253125 THz 3.125GHz spacing";
             }
             enum "1567.49" {
               description "1567.49 nm/191.256250 THz 3.125/6.25GHz spacing";
             }
             enum "1567.47" {
               description "1567.47 nm/191.259375 THz 3.125GHz spacing";
             }
             enum "1567.44" {
               description "1567.44 nm/191.262500 THz 3.125/6.25/12.5GHz spacing";
             }
             enum "1567.41" {
               description "1567.41 nm/191.265625 THz 3.125GHz spacing";
             }
             enum "1567.39" {
               description "1567.39 nm/191.268750 THz 3.125/6.25GHz spacing";
             }
             enum "1567.36" {
               description "1567.36 nm/191.271875 THz 3.125GHz spacing";
             }
             enum "1567.34" {
               description "1567.34 nm/191.275000 THz 3.125/6.25/12.5GHz spacing";
             }
             enum "1567.31" {
               description "1567.31 nm/191.278125 THz 3.125GHz spacing";
             }
             enum "1567.29" {
               description "1567.29 nm/191.281250 THz 3.125/6.25GHz spacing";
             }
             enum "1567.26" {
               description "1567.26 nm/191.284375 THz 3.125GHz spacing";
             }
             enum "1567.23" {
               description "1567.23 nm/191.287500 THz 3.125/6.25/12.5GHz spacing";
             }
             enum "1567.21" {
               description "1567.21 nm/191.290625 THz 3.125GHz spacing";
             }
             enum "1567.18" {
               description "1567.18 nm/191.293750 THz 3.125/6.25GHz spacing";
             }
             enum "1567.16" {
               description "1567.16 nm/191.296875 THz 3.125GHz spacing";
             }
             enum "1567.13" {
               description "1567.13 nm/191.300000 THz 3.125/6.25/12.5/100GHz spacing";
             }
             enum "1567.11" {
               description "1567.11 nm/191.303125 THz 3.125GHz spacing";
             }
             enum "1567.08" {
               description "1567.08 nm/191.306250 THz 3.125/6.25GHz spacing";
             }
             enum "1567.06" {
               description "1567.06 nm/191.309375 THz 3.125GHz spacing";
             }
             enum "1567.03" {
               description "1567.03 nm/191.312500 THz 3.125/6.25/12.5GHz spacing";
             }
             enum "1567.00" {
               description "1567.00 nm/191.315625 THz 3.125GHz spacing";
             }
             enum "1566.98" {
               description "1566.98 nm/191.318750 THz 3.125/6.25GHz spacing";
             }
             enum "1566.95" {
               description "1566.95 nm/191.321875 THz 3.125GHz spacing";
             }
             enum "1566.93" {
               description "1566.93 nm/191.325000 THz 3.125/6.25/12.5/75GHz spacing";
             }
             enum "1566.90" {
               description "1566.90 nm/191.328125 THz 3.125GHz spacing";
             }
             enum "1566.88" {
               description "1566.88 nm/191.331250 THz 3.125/6.25GHz spacing";
             }
             enum "1566.85" {
               description "1566.85 nm/191.334375 THz 3.125GHz spacing";
             }
             enum "1566.83" {
               description "1566.83 nm/191.337500 THz 3.125/6.25/12.5GHz spacing";
             }
             enum "1566.80" {
               description "1566.80 nm/191.340625 THz 3.125GHz spacing";
             }
             enum "1566.77" {
               description "1566.77 nm/191.343750 THz 3.125/6.25GHz spacing";
             }
             enum "1566.75" {
               description "1566.75 nm/191.346875 THz 3.125GHz spacing";
             }
             enum "1566.72" {
               description "1566.72 nm/191.350000 THz 3.125/6.25/12.5/50GHz spacing";
             }
             enum "1566.70" {
               description "1566.70 nm/191.353125 THz 3.125GHz spacing";
             }
             enum "1566.67" {
               description "1566.67 nm/191.356250 THz 3.125/6.25GHz spacing";
             }
             enum "1566.65" {
               description "1566.65 nm/191.359375 THz 3.125GHz spacing";
             }
             enum "1566.62" {
               description "1566.62 nm/191.362500 THz 3.125/6.25/12.5GHz spacing";
             }
             enum "1566.60" {
               description "1566.60 nm/191.365625 THz 3.125GHz spacing";
             }
             enum "1566.57" {
               description "1566.57 nm/191.368750 THz 3.125/6.25GHz spacing";
             }
             enum "1566.54" {
               description "1566.54 nm/191.371875 THz 3.125GHz spacing";
             }
             enum "1566.52" {
               description "1566.52 nm/191.375000 THz 3.125/6.25/12.5GHz spacing";
             }
             enum "1566.49" {
               description "1566.49 nm/191.378125 THz 3.125GHz spacing";
             }
             enum "1566.47" {
               description "1566.47 nm/191.381250 THz 3.125/6.25GHz spacing";
             }
             enum "1566.44" {
               description "1566.44 nm/191.384375 THz 3.125GHz spacing";
             }
             enum "1566.42" {
               description "1566.42 nm/191.387500 THz 3.125/6.25/12.5GHz spacing";
             }
             enum "1566.39" {
               description "1566.39 nm/191.390625 THz 3.125GHz spacing";
             }
             enum "1566.36" {
               description "1566.36 nm/191.393750 THz 3.125/6.25GHz spacing";
             }
             enum "1566.34" {
               description "1566.34 nm/191.396875 THz 3.125GHz spacing";
             }
             enum "1566.31" {
               description "1566.31 nm/191.400000 THz 3.125/6.25/12.5/50/75/100GHz spacing";
             }
             enum "1566.29" {
               description "1566.29 nm/191.403125 THz 3.125GHz spacing";
             }
             enum "1566.26" {
               description "1566.26 nm/191.406250 THz 3.125/6.25GHz spacing";
             }
             enum "1566.24" {
               description "1566.24 nm/191.409375 THz 3.125GHz spacing";
             }
             enum "1566.21" {
               description "1566.21 nm/191.412500 THz 3.125/6.25/12.5GHz spacing";
             }
             enum "1566.19" {
               description "1566.19 nm/191.415625 THz 3.125GHz spacing";
             }
             enum "1566.16" {
               description "1566.16 nm/191.418750 THz 3.125/6.25GHz spacing";
             }
             enum "1566.13" {
               description "1566.13 nm/191.421875 THz 3.125GHz spacing";
             }
             enum "1566.11" {
               description "1566.11 nm/191.425000 THz 3.125/6.25/12.5GHz spacing";
             }
             enum "1566.08" {
               description "1566.08 nm/191.428125 THz 3.125GHz spacing";
             }
             enum "1566.06" {
               description "1566.06 nm/191.431250 THz 3.125/6.25GHz spacing";
             }
             enum "1566.03" {
               description "1566.03 nm/191.434375 THz 3.125GHz spacing";
             }
             enum "1566.01" {
               description "1566.01 nm/191.437500 THz 3.125/6.25/12.5GHz spacing";
             }
             enum "1565.98" {
               description "1565.98 nm/191.440625 THz 3.125GHz spacing";
             }
             enum "1565.96" {
               description "1565.96 nm/191.443750 THz 3.125/6.25GHz spacing";
             }
             enum "1565.93" {
               description "1565.93 nm/191.446875 THz 3.125GHz spacing";
             }
             enum "1565.90" {
               description "1565.90 nm/191.450000 THz 3.125/6.25/12.5/50GHz spacing";
             }
             enum "1565.88" {
               description "1565.88 nm/191.453125 THz 3.125GHz spacing";
             }
             enum "1565.85" {
               description "1565.85 nm/191.456250 THz 3.125/6.25GHz spacing";
             }
             enum "1565.83" {
               description "1565.83 nm/191.459375 THz 3.125GHz spacing";
             }
             enum "1565.80" {
               description "1565.80 nm/191.462500 THz 3.125/6.25/12.5GHz spacing";
             }
             enum "1565.78" {
               description "1565.78 nm/191.465625 THz 3.125GHz spacing";
             }
             enum "1565.75" {
               description "1565.75 nm/191.468750 THz 3.125/6.25GHz spacing";
             }
             enum "1565.73" {
               description "1565.73 nm/191.471875 THz 3.125GHz spacing";
             }
             enum "1565.70" {
               description "1565.70 nm/191.475000 THz 3.125/6.25/12.5/75GHz spacing";
             }
             enum "1565.67" {
               description "1565.67 nm/191.478125 THz 3.125GHz spacing";
             }
             enum "1565.65" {
               description "1565.65 nm/191.481250 THz 3.125/6.25GHz spacing";
             }
             enum "1565.62" {
               description "1565.62 nm/191.484375 THz 3.125GHz spacing";
             }
             enum "1565.60" {
               description "1565.60 nm/191.487500 THz 3.125/6.25/12.5GHz spacing";
             }
             enum "1565.57" {
               description "1565.57 nm/191.490625 THz 3.125GHz spacing";
             }
             enum "1565.55" {
               description "1565.55 nm/191.493750 THz 3.125/6.25GHz spacing";
             }
             enum "1565.52" {
               description "1565.52 nm/191.496875 THz 3.125GHz spacing";
             }
             enum "1565.50" {
               description "1565.50 nm/191.500000 THz 3.125/6.25/12.5/100GHz spacing";
             }
             enum "1565.47" {
               description "1565.47 nm/191.503125 THz 3.125GHz spacing";
             }
             enum "1565.44" {
               description "1565.44 nm/191.506250 THz 3.125/6.25GHz spacing";
             }
             enum "1565.42" {
               description "1565.42 nm/191.509375 THz 3.125GHz spacing";
             }
             enum "1565.39" {
               description "1565.39 nm/191.512500 THz 3.125/6.25/12.5GHz spacing";
             }
             enum "1565.37" {
               description "1565.37 nm/191.515625 THz 3.125GHz spacing";
             }
             enum "1565.34" {
               description "1565.34 nm/191.518750 THz 3.125/6.25GHz spacing";
             }
             enum "1565.32" {
               description "1565.32 nm/191.521875 THz 3.125GHz spacing";
             }
             enum "1565.29" {
               description "1565.29 nm/191.525000 THz 3.125/6.25/12.5GHz spacing";
             }
             enum "1565.27" {
               description "1565.27 nm/191.528125 THz 3.125GHz spacing";
             }
             enum "1565.24" {
               description "1565.24 nm/191.531250 THz 3.125/6.25GHz spacing";
             }
             enum "1565.21" {
               description "1565.21 nm/191.534375 THz 3.125GHz spacing";
             }
             enum "1565.19" {
               description "1565.19 nm/191.537500 THz 3.125/6.25/12.5GHz spacing";
             }
             enum "1565.16" {
               description "1565.16 nm/191.540625 THz 3.125GHz spacing";
             }
             enum "1565.14" {
               description "1565.14 nm/191.543750 THz 3.125/6.25GHz spacing";
             }
             enum "1565.11" {
               description "1565.11 nm/191.546875 THz 3.125GHz spacing";
             }
             enum "1565.09" {
               description "1565.09 nm/191.550000 THz 3.125/6.25/12.5/50/75GHz spacing";
             }
             enum "1565.06" {
               description "1565.06 nm/191.553125 THz 3.125GHz spacing";
             }
             enum "1565.04" {
               description "1565.04 nm/191.556250 THz 3.125/6.25GHz spacing";
             }
             enum "1565.01" {
               description "1565.01 nm/191.559375 THz 3.125GHz spacing";
             }
             enum "1564.99" {
               description "1564.99 nm/191.562500 THz 3.125/6.25/12.5GHz spacing";
             }
             enum "1564.96" {
               description "1564.96 nm/191.565625 THz 3.125GHz spacing";
             }
             enum "1564.93" {
               description "1564.93 nm/191.568750 THz 3.125/6.25GHz spacing";
             }
             enum "1564.91" {
               description "1564.91 nm/191.571875 THz 3.125GHz spacing";
             }
             enum "1564.88" {
               description "1564.88 nm/191.575000 THz 3.125/6.25/12.5GHz spacing";
             }
             enum "1564.86" {
               description "1564.86 nm/191.578125 THz 3.125GHz spacing";
             }
             enum "1564.83" {
               description "1564.83 nm/191.581250 THz 3.125/6.25GHz spacing";
             }
             enum "1564.81" {
               description "1564.81 nm/191.584375 THz 3.125GHz spacing";
             }
             enum "1564.78" {
               description "1564.78 nm/191.587500 THz 3.125/6.25/12.5GHz spacing";
             }
             enum "1564.76" {
               description "1564.76 nm/191.590625 THz 3.125GHz spacing";
             }
             enum "1564.73" {
               description "1564.73 nm/191.593750 THz 3.125/6.25GHz spacing";
             }
             enum "1564.70" {
               description "1564.70 nm/191.596875 THz 3.125GHz spacing";
             }
             enum "1564.68" {
               description "1564.68 nm/191.600000 THz 3.125/6.25/12.5/100GHz spacing";
             }
             enum "1564.65" {
               description "1564.65 nm/191.603125 THz 3.125GHz spacing";
             }
             enum "1564.63" {
               description "1564.63 nm/191.606250 THz 3.125/6.25GHz spacing";
             }
             enum "1564.60" {
               description "1564.60 nm/191.609375 THz 3.125GHz spacing";
             }
             enum "1564.58" {
               description "1564.58 nm/191.612500 THz 3.125/6.25/12.5GHz spacing";
             }
             enum "1564.55" {
               description "1564.55 nm/191.615625 THz 3.125GHz spacing";
             }
             enum "1564.53" {
               description "1564.53 nm/191.618750 THz 3.125/6.25GHz spacing";
             }
             enum "1564.50" {
               description "1564.50 nm/191.621875 THz 3.125GHz spacing";
             }
             enum "1564.47" {
               description "1564.47 nm/191.625000 THz 3.125/6.25/12.5/75GHz spacing";
             }
             enum "1564.45" {
               description "1564.45 nm/191.628125 THz 3.125GHz spacing";
             }
             enum "1564.42" {
               description "1564.42 nm/191.631250 THz 3.125/6.25GHz spacing";
             }
             enum "1564.40" {
               description "1564.40 nm/191.634375 THz 3.125GHz spacing";
             }
             enum "1564.37" {
               description "1564.37 nm/191.637500 THz 3.125/6.25/12.5GHz spacing";
             }
             enum "1564.35" {
               description "1564.35 nm/191.640625 THz 3.125GHz spacing";
             }
             enum "1564.32" {
               description "1564.32 nm/191.643750 THz 3.125/6.25GHz spacing";
             }
             enum "1564.30" {
               description "1564.30 nm/191.646875 THz 3.125GHz spacing";
             }
             enum "1564.27" {
               description "1564.27 nm/191.650000 THz 3.125/6.25/12.5/50GHz spacing";
             }
             enum "1564.25" {
               description "1564.25 nm/191.653125 THz 3.125GHz spacing";
             }
             enum "1564.22" {
               description "1564.22 nm/191.656250 THz 3.125/6.25GHz spacing";
             }
             enum "1564.19" {
               description "1564.19 nm/191.659375 THz 3.125GHz spacing";
             }
             enum "1564.17" {
               description "1564.17 nm/191.662500 THz 3.125/6.25/12.5GHz spacing";
             }
             enum "1564.14" {
               description "1564.14 nm/191.665625 THz 3.125GHz spacing";
             }
             enum "1564.12" {
               description "1564.12 nm/191.668750 THz 3.125/6.25GHz spacing";
             }
             enum "1564.09" {
               description "1564.09 nm/191.671875 THz 3.125GHz spacing";
             }
             enum "1564.07" {
               description "1564.07 nm/191.675000 THz 3.125/6.25/12.5GHz spacing";
             }
             enum "1564.04" {
               description "1564.04 nm/191.678125 THz 3.125GHz spacing";
             }
             enum "1564.02" {
               description "1564.02 nm/191.681250 THz 3.125/6.25GHz spacing";
             }
             enum "1563.99" {
               description "1563.99 nm/191.684375 THz 3.125GHz spacing";
             }
             enum "1563.96" {
               description "1563.96 nm/191.687500 THz 3.125/6.25/12.5GHz spacing";
             }
             enum "1563.94" {
               description "1563.94 nm/191.690625 THz 3.125GHz spacing";
             }
             enum "1563.91" {
               description "1563.91 nm/191.693750 THz 3.125/6.25GHz spacing";
             }
             enum "1563.89" {
               description "1563.89 nm/191.696875 THz 3.125GHz spacing";
             }
             enum "1563.86" {
               description "1563.86 nm/191.700000 THz 3.125/6.25/12.5/50/75/100GHz spacing";
             }
             enum "1563.84" {
               description "1563.84 nm/191.703125 THz 3.125GHz spacing";
             }
             enum "1563.81" {
               description "1563.81 nm/191.706250 THz 3.125/6.25GHz spacing";
             }
             enum "1563.79" {
               description "1563.79 nm/191.709375 THz 3.125GHz spacing";
             }
             enum "1563.76" {
               description "1563.76 nm/191.712500 THz 3.125/6.25/12.5GHz spacing";
             }
             enum "1563.74" {
               description "1563.74 nm/191.715625 THz 3.125GHz spacing";
             }
             enum "1563.71" {
               description "1563.71 nm/191.718750 THz 3.125/6.25GHz spacing";
             }
             enum "1563.68" {
               description "1563.68 nm/191.721875 THz 3.125GHz spacing";
             }
             enum "1563.66" {
               description "1563.66 nm/191.725000 THz 3.125/6.25/12.5GHz spacing";
             }
             enum "1563.63" {
               description "1563.63 nm/191.728125 THz 3.125GHz spacing";
             }
             enum "1563.61" {
               description "1563.61 nm/191.731250 THz 3.125/6.25GHz spacing";
             }
             enum "1563.58" {
               description "1563.58 nm/191.734375 THz 3.125GHz spacing";
             }
             enum "1563.56" {
               description "1563.56 nm/191.737500 THz 3.125/6.25/12.5GHz spacing";
             }
             enum "1563.53" {
               description "1563.53 nm/191.740625 THz 3.125GHz spacing";
             }
             enum "1563.51" {
               description "1563.51 nm/191.743750 THz 3.125/6.25GHz spacing";
             }
             enum "1563.48" {
               description "1563.48 nm/191.746875 THz 3.125GHz spacing";
             }
             enum "1563.45" {
               description "1563.45 nm/191.750000 THz 3.125/6.25/12.5/50GHz spacing";
             }
             enum "1563.43" {
               description "1563.43 nm/191.753125 THz 3.125GHz spacing";
             }
             enum "1563.40" {
               description "1563.40 nm/191.756250 THz 3.125/6.25GHz spacing";
             }
             enum "1563.38" {
               description "1563.38 nm/191.759375 THz 3.125GHz spacing";
             }
             enum "1563.35" {
               description "1563.35 nm/191.762500 THz 3.125/6.25/12.5GHz spacing";
             }
             enum "1563.33" {
               description "1563.33 nm/191.765625 THz 3.125GHz spacing";
             }
             enum "1563.30" {
               description "1563.30 nm/191.768750 THz 3.125/6.25GHz spacing";
             }
             enum "1563.28" {
               description "1563.28 nm/191.771875 THz 3.125GHz spacing";
             }
             enum "1563.25" {
               description "1563.25 nm/191.775000 THz 3.125/6.25/12.5/75GHz spacing";
             }
             enum "1563.23" {
               description "1563.23 nm/191.778125 THz 3.125GHz spacing";
             }
             enum "1563.20" {
               description "1563.20 nm/191.781250 THz 3.125/6.25GHz spacing";
             }
             enum "1563.17" {
               description "1563.17 nm/191.784375 THz 3.125GHz spacing";
             }
             enum "1563.15" {
               description "1563.15 nm/191.787500 THz 3.125/6.25/12.5GHz spacing";
             }
             enum "1563.12" {
               description "1563.12 nm/191.790625 THz 3.125GHz spacing";
             }
             enum "1563.10" {
               description "1563.10 nm/191.793750 THz 3.125/6.25GHz spacing";
             }
             enum "1563.07" {
               description "1563.07 nm/191.796875 THz 3.125GHz spacing";
             }
             enum "1563.05" {
               description "1563.05 nm/191.800000 THz 3.125/6.25/12.5/100GHz spacing";
             }
             enum "1563.02" {
               description "1563.02 nm/191.803125 THz 3.125GHz spacing";
             }
             enum "1563.00" {
               description "1563.00 nm/191.806250 THz 3.125/6.25GHz spacing";
             }
             enum "1562.97" {
               description "1562.97 nm/191.809375 THz 3.125GHz spacing";
             }
             enum "1562.95" {
               description "1562.95 nm/191.812500 THz 3.125/6.25/12.5GHz spacing";
             }
             enum "1562.92" {
               description "1562.92 nm/191.815625 THz 3.125GHz spacing";
             }
             enum "1562.89" {
               description "1562.89 nm/191.818750 THz 3.125/6.25GHz spacing";
             }
             enum "1562.87" {
               description "1562.87 nm/191.821875 THz 3.125GHz spacing";
             }
             enum "1562.84" {
               description "1562.84 nm/191.825000 THz 3.125/6.25/12.5GHz spacing";
             }
             enum "1562.82" {
               description "1562.82 nm/191.828125 THz 3.125GHz spacing";
             }
             enum "1562.79" {
               description "1562.79 nm/191.831250 THz 3.125/6.25GHz spacing";
             }
             enum "1562.77" {
               description "1562.77 nm/191.834375 THz 3.125GHz spacing";
             }
             enum "1562.74" {
               description "1562.74 nm/191.837500 THz 3.125/6.25/12.5GHz spacing";
             }
             enum "1562.72" {
               description "1562.72 nm/191.840625 THz 3.125GHz spacing";
             }
             enum "1562.69" {
               description "1562.69 nm/191.843750 THz 3.125/6.25GHz spacing";
             }
             enum "1562.67" {
               description "1562.67 nm/191.846875 THz 3.125GHz spacing";
             }
             enum "1562.64" {
               description "1562.64 nm/191.850000 THz 3.125/6.25/12.5/50/75GHz spacing";
             }
             enum "1562.61" {
               description "1562.61 nm/191.853125 THz 3.125GHz spacing";
             }
             enum "1562.59" {
               description "1562.59 nm/191.856250 THz 3.125/6.25GHz spacing";
             }
             enum "1562.56" {
               description "1562.56 nm/191.859375 THz 3.125GHz spacing";
             }
             enum "1562.54" {
               description "1562.54 nm/191.862500 THz 3.125/6.25/12.5GHz spacing";
             }
             enum "1562.51" {
               description "1562.51 nm/191.865625 THz 3.125GHz spacing";
             }
             enum "1562.49" {
               description "1562.49 nm/191.868750 THz 3.125/6.25GHz spacing";
             }
             enum "1562.46" {
               description "1562.46 nm/191.871875 THz 3.125GHz spacing";
             }
             enum "1562.44" {
               description "1562.44 nm/191.875000 THz 3.125/6.25/12.5GHz spacing";
             }
             enum "1562.41" {
               description "1562.41 nm/191.878125 THz 3.125GHz spacing";
             }
             enum "1562.39" {
               description "1562.39 nm/191.881250 THz 3.125/6.25GHz spacing";
             }
             enum "1562.36" {
               description "1562.36 nm/191.884375 THz 3.125GHz spacing";
             }
             enum "1562.33" {
               description "1562.33 nm/191.887500 THz 3.125/6.25/12.5GHz spacing";
             }
             enum "1562.31" {
               description "1562.31 nm/191.890625 THz 3.125GHz spacing";
             }
             enum "1562.28" {
               description "1562.28 nm/191.893750 THz 3.125/6.25GHz spacing";
             }
             enum "1562.26" {
               description "1562.26 nm/191.896875 THz 3.125GHz spacing";
             }
             enum "1562.23" {
               description "1562.23 nm/191.900000 THz 3.125/6.25/12.5/100GHz spacing";
             }
             enum "1562.21" {
               description "1562.21 nm/191.903125 THz 3.125GHz spacing";
             }
             enum "1562.18" {
               description "1562.18 nm/191.906250 THz 3.125/6.25GHz spacing";
             }
             enum "1562.16" {
               description "1562.16 nm/191.909375 THz 3.125GHz spacing";
             }
             enum "1562.13" {
               description "1562.13 nm/191.912500 THz 3.125/6.25/12.5GHz spacing";
             }
             enum "1562.11" {
               description "1562.11 nm/191.915625 THz 3.125GHz spacing";
             }
             enum "1562.08" {
               description "1562.08 nm/191.918750 THz 3.125/6.25GHz spacing";
             }
             enum "1562.05" {
               description "1562.05 nm/191.921875 THz 3.125GHz spacing";
             }
             enum "1562.03" {
               description "1562.03 nm/191.925000 THz 3.125/6.25/12.5/75GHz spacing";
             }
             enum "1562.00" {
               description "1562.00 nm/191.928125 THz 3.125GHz spacing";
             }
             enum "1561.98" {
               description "1561.98 nm/191.931250 THz 3.125/6.25GHz spacing";
             }
             enum "1561.95" {
               description "1561.95 nm/191.934375 THz 3.125GHz spacing";
             }
             enum "1561.93" {
               description "1561.93 nm/191.937500 THz 3.125/6.25/12.5GHz spacing";
             }
             enum "1561.90" {
               description "1561.90 nm/191.940625 THz 3.125GHz spacing";
             }
             enum "1561.88" {
               description "1561.88 nm/191.943750 THz 3.125/6.25GHz spacing";
             }
             enum "1561.85" {
               description "1561.85 nm/191.946875 THz 3.125GHz spacing";
             }
             enum "1561.83" {
               description "1561.83 nm/191.950000 THz 3.125/6.25/12.5/50GHz spacing";
             }
             enum "1561.80" {
               description "1561.80 nm/191.953125 THz 3.125GHz spacing";
             }
             enum "1561.77" {
               description "1561.77 nm/191.956250 THz 3.125/6.25GHz spacing";
             }
             enum "1561.75" {
               description "1561.75 nm/191.959375 THz 3.125GHz spacing";
             }
             enum "1561.72" {
               description "1561.72 nm/191.962500 THz 3.125/6.25/12.5GHz spacing";
             }
             enum "1561.70" {
               description "1561.70 nm/191.965625 THz 3.125GHz spacing";
             }
             enum "1561.67" {
               description "1561.67 nm/191.968750 THz 3.125/6.25GHz spacing";
             }
             enum "1561.65" {
               description "1561.65 nm/191.971875 THz 3.125GHz spacing";
             }
             enum "1561.62" {
               description "1561.62 nm/191.975000 THz 3.125/6.25/12.5GHz spacing";
             }
             enum "1561.60" {
               description "1561.60 nm/191.978125 THz 3.125GHz spacing";
             }
             enum "1561.57" {
               description "1561.57 nm/191.981250 THz 3.125/6.25GHz spacing";
             }
             enum "1561.55" {
               description "1561.55 nm/191.984375 THz 3.125GHz spacing";
             }
             enum "1561.52" {
               description "1561.52 nm/191.987500 THz 3.125/6.25/12.5GHz spacing";
             }
             enum "1561.50" {
               description "1561.50 nm/191.990625 THz 3.125GHz spacing";
             }
             enum "1561.47" {
               description "1561.47 nm/191.993750 THz 3.125/6.25GHz spacing";
             }
             enum "1561.44" {
               description "1561.44 nm/191.996875 THz 3.125GHz spacing";
             }
             enum "1561.42" {
               description "1561.42 nm/192.000000 THz 3.125/6.25/12.5/50/75/100GHz spacing";
             }
             enum "1561.39" {
               description "1561.39 nm/192.003125 THz 3.125GHz spacing";
             }
             enum "1561.37" {
               description "1561.37 nm/192.006250 THz 3.125/6.25GHz spacing";
             }
             enum "1561.34" {
               description "1561.34 nm/192.009375 THz 3.125GHz spacing";
             }
             enum "1561.32" {
               description "1561.32 nm/192.012500 THz 3.125/6.25/12.5GHz spacing";
             }
             enum "1561.29" {
               description "1561.29 nm/192.015625 THz 3.125GHz spacing";
             }
             enum "1561.27" {
               description "1561.27 nm/192.018750 THz 3.125/6.25GHz spacing";
             }
             enum "1561.24" {
               description "1561.24 nm/192.021875 THz 3.125GHz spacing";
             }
             enum "1561.22" {
               description "1561.22 nm/192.025000 THz 3.125/6.25/12.5GHz spacing";
             }
             enum "1561.19" {
               description "1561.19 nm/192.028125 THz 3.125GHz spacing";
             }
             enum "1561.16" {
               description "1561.16 nm/192.031250 THz 3.125/6.25GHz spacing";
             }
             enum "1561.14" {
               description "1561.14 nm/192.034375 THz 3.125GHz spacing";
             }
             enum "1561.11" {
               description "1561.11 nm/192.037500 THz 3.125/6.25/12.5GHz spacing";
             }
             enum "1561.09" {
               description "1561.09 nm/192.040625 THz 3.125GHz spacing";
             }
             enum "1561.06" {
               description "1561.06 nm/192.043750 THz 3.125/6.25GHz spacing";
             }
             enum "1561.04" {
               description "1561.04 nm/192.046875 THz 3.125GHz spacing";
             }
             enum "1561.01" {
               description "1561.01 nm/192.050000 THz 3.125/6.25/12.5/50GHz spacing";
             }
             enum "1560.99" {
               description "1560.99 nm/192.053125 THz 3.125GHz spacing";
             }
             enum "1560.96" {
               description "1560.96 nm/192.056250 THz 3.125/6.25GHz spacing";
             }
             enum "1560.94" {
               description "1560.94 nm/192.059375 THz 3.125GHz spacing";
             }
             enum "1560.91" {
               description "1560.91 nm/192.062500 THz 3.125/6.25/12.5GHz spacing";
             }
             enum "1560.89" {
               description "1560.89 nm/192.065625 THz 3.125GHz spacing";
             }
             enum "1560.86" {
               description "1560.86 nm/192.068750 THz 3.125/6.25GHz spacing";
             }
             enum "1560.83" {
               description "1560.83 nm/192.071875 THz 3.125GHz spacing";
             }
             enum "1560.81" {
               description "1560.81 nm/192.075000 THz 3.125/6.25/12.5/75GHz spacing";
             }
             enum "1560.78" {
               description "1560.78 nm/192.078125 THz 3.125GHz spacing";
             }
             enum "1560.76" {
               description "1560.76 nm/192.081250 THz 3.125/6.25GHz spacing";
             }
             enum "1560.73" {
               description "1560.73 nm/192.084375 THz 3.125GHz spacing";
             }
             enum "1560.71" {
               description "1560.71 nm/192.087500 THz 3.125/6.25/12.5GHz spacing";
             }
             enum "1560.68" {
               description "1560.68 nm/192.090625 THz 3.125GHz spacing";
             }
             enum "1560.66" {
               description "1560.66 nm/192.093750 THz 3.125/6.25GHz spacing";
             }
             enum "1560.63" {
               description "1560.63 nm/192.096875 THz 3.125GHz spacing";
             }
             enum "1560.61" {
               description "1560.61 nm/192.100000 THz 3.125/6.25/12.5/100GHz spacing";
             }
             enum "1560.58" {
               description "1560.58 nm/192.103125 THz 3.125GHz spacing";
             }
             enum "1560.56" {
               description "1560.56 nm/192.106250 THz 3.125/6.25GHz spacing";
             }
             enum "1560.53" {
               description "1560.53 nm/192.109375 THz 3.125GHz spacing";
             }
             enum "1560.50" {
               description "1560.50 nm/192.112500 THz 3.125/6.25/12.5GHz spacing";
             }
             enum "1560.48" {
               description "1560.48 nm/192.115625 THz 3.125GHz spacing";
             }
             enum "1560.45" {
               description "1560.45 nm/192.118750 THz 3.125/6.25GHz spacing";
             }
             enum "1560.43" {
               description "1560.43 nm/192.121875 THz 3.125GHz spacing";
             }
             enum "1560.40" {
               description "1560.40 nm/192.125000 THz 3.125/6.25/12.5GHz spacing";
             }
             enum "1560.38" {
               description "1560.38 nm/192.128125 THz 3.125GHz spacing";
             }
             enum "1560.35" {
               description "1560.35 nm/192.131250 THz 3.125/6.25GHz spacing";
             }
             enum "1560.33" {
               description "1560.33 nm/192.134375 THz 3.125GHz spacing";
             }
             enum "1560.30" {
               description "1560.30 nm/192.137500 THz 3.125/6.25/12.5GHz spacing";
             }
             enum "1560.28" {
               description "1560.28 nm/192.140625 THz 3.125GHz spacing";
             }
             enum "1560.25" {
               description "1560.25 nm/192.143750 THz 3.125/6.25GHz spacing";
             }
             enum "1560.23" {
               description "1560.23 nm/192.146875 THz 3.125GHz spacing";
             }
             enum "1560.20" {
               description "1560.20 nm/192.150000 THz 3.125/6.25/12.5/50/75GHz spacing";
             }
             enum "1560.17" {
               description "1560.17 nm/192.153125 THz 3.125GHz spacing";
             }
             enum "1560.15" {
               description "1560.15 nm/192.156250 THz 3.125/6.25GHz spacing";
             }
             enum "1560.12" {
               description "1560.12 nm/192.159375 THz 3.125GHz spacing";
             }
             enum "1560.10" {
               description "1560.10 nm/192.162500 THz 3.125/6.25/12.5GHz spacing";
             }
             enum "1560.07" {
               description "1560.07 nm/192.165625 THz 3.125GHz spacing";
             }
             enum "1560.05" {
               description "1560.05 nm/192.168750 THz 3.125/6.25GHz spacing";
             }
             enum "1560.02" {
               description "1560.02 nm/192.171875 THz 3.125GHz spacing";
             }
             enum "1560.00" {
               description "1560.00 nm/192.175000 THz 3.125/6.25/12.5GHz spacing";
             }
             enum "1559.97" {
               description "1559.97 nm/192.178125 THz 3.125GHz spacing";
             }
             enum "1559.95" {
               description "1559.95 nm/192.181250 THz 3.125/6.25GHz spacing";
             }
             enum "1559.92" {
               description "1559.92 nm/192.184375 THz 3.125GHz spacing";
             }
             enum "1559.90" {
               description "1559.90 nm/192.187500 THz 3.125/6.25/12.5GHz spacing";
             }
             enum "1559.87" {
               description "1559.87 nm/192.190625 THz 3.125GHz spacing";
             }
             enum "1559.84" {
               description "1559.84 nm/192.193750 THz 3.125/6.25GHz spacing";
             }
             enum "1559.82" {
               description "1559.82 nm/192.196875 THz 3.125GHz spacing";
             }
             enum "1559.79" {
               description "1559.79 nm/192.200000 THz 3.125/6.25/12.5/100GHz spacing";
             }
             enum "1559.77" {
               description "1559.77 nm/192.203125 THz 3.125GHz spacing";
             }
             enum "1559.74" {
               description "1559.74 nm/192.206250 THz 3.125/6.25GHz spacing";
             }
             enum "1559.72" {
               description "1559.72 nm/192.209375 THz 3.125GHz spacing";
             }
             enum "1559.69" {
               description "1559.69 nm/192.212500 THz 3.125/6.25/12.5GHz spacing";
             }
             enum "1559.67" {
               description "1559.67 nm/192.215625 THz 3.125GHz spacing";
             }
             enum "1559.64" {
               description "1559.64 nm/192.218750 THz 3.125/6.25GHz spacing";
             }
             enum "1559.62" {
               description "1559.62 nm/192.221875 THz 3.125GHz spacing";
             }
             enum "1559.59" {
               description "1559.59 nm/192.225000 THz 3.125/6.25/12.5/75GHz spacing";
             }
             enum "1559.57" {
               description "1559.57 nm/192.228125 THz 3.125GHz spacing";
             }
             enum "1559.54" {
               description "1559.54 nm/192.231250 THz 3.125/6.25GHz spacing";
             }
             enum "1559.52" {
               description "1559.52 nm/192.234375 THz 3.125GHz spacing";
             }
             enum "1559.49" {
               description "1559.49 nm/192.237500 THz 3.125/6.25/12.5GHz spacing";
             }
             enum "1559.46" {
               description "1559.46 nm/192.240625 THz 3.125GHz spacing";
             }
             enum "1559.44" {
               description "1559.44 nm/192.243750 THz 3.125/6.25GHz spacing";
             }
             enum "1559.41" {
               description "1559.41 nm/192.246875 THz 3.125GHz spacing";
             }
             enum "1559.39" {
               description "1559.39 nm/192.250000 THz 3.125/6.25/12.5/50GHz spacing";
             }
             enum "1559.36" {
               description "1559.36 nm/192.253125 THz 3.125GHz spacing";
             }
             enum "1559.34" {
               description "1559.34 nm/192.256250 THz 3.125/6.25GHz spacing";
             }
             enum "1559.31" {
               description "1559.31 nm/192.259375 THz 3.125GHz spacing";
             }
             enum "1559.29" {
               description "1559.29 nm/192.262500 THz 3.125/6.25/12.5GHz spacing";
             }
             enum "1559.26" {
               description "1559.26 nm/192.265625 THz 3.125GHz spacing";
             }
             enum "1559.24" {
               description "1559.24 nm/192.268750 THz 3.125/6.25GHz spacing";
             }
             enum "1559.21" {
               description "1559.21 nm/192.271875 THz 3.125GHz spacing";
             }
             enum "1559.19" {
               description "1559.19 nm/192.275000 THz 3.125/6.25/12.5GHz spacing";
             }
             enum "1559.16" {
               description "1559.16 nm/192.278125 THz 3.125GHz spacing";
             }
             enum "1559.14" {
               description "1559.14 nm/192.281250 THz 3.125/6.25GHz spacing";
             }
             enum "1559.11" {
               description "1559.11 nm/192.284375 THz 3.125GHz spacing";
             }
             enum "1559.08" {
               description "1559.08 nm/192.287500 THz 3.125/6.25/12.5GHz spacing";
             }
             enum "1559.06" {
               description "1559.06 nm/192.290625 THz 3.125GHz spacing";
             }
             enum "1559.03" {
               description "1559.03 nm/192.293750 THz 3.125/6.25GHz spacing";
             }
             enum "1559.01" {
               description "1559.01 nm/192.296875 THz 3.125GHz spacing";
             }
             enum "1558.98" {
               description "1558.98 nm/192.300000 THz 3.125/6.25/12.5/50/75/100GHz spacing";
             }
             enum "1558.96" {
               description "1558.96 nm/192.303125 THz 3.125GHz spacing";
             }
             enum "1558.93" {
               description "1558.93 nm/192.306250 THz 3.125/6.25GHz spacing";
             }
             enum "1558.91" {
               description "1558.91 nm/192.309375 THz 3.125GHz spacing";
             }
             enum "1558.88" {
               description "1558.88 nm/192.312500 THz 3.125/6.25/12.5GHz spacing";
             }
             enum "1558.86" {
               description "1558.86 nm/192.315625 THz 3.125GHz spacing";
             }
             enum "1558.83" {
               description "1558.83 nm/192.318750 THz 3.125/6.25GHz spacing";
             }
             enum "1558.81" {
               description "1558.81 nm/192.321875 THz 3.125GHz spacing";
             }
             enum "1558.78" {
               description "1558.78 nm/192.325000 THz 3.125/6.25/12.5GHz spacing";
             }
             enum "1558.76" {
               description "1558.76 nm/192.328125 THz 3.125GHz spacing";
             }
             enum "1558.73" {
               description "1558.73 nm/192.331250 THz 3.125/6.25GHz spacing";
             }
             enum "1558.70" {
               description "1558.70 nm/192.334375 THz 3.125GHz spacing";
             }
             enum "1558.68" {
               description "1558.68 nm/192.337500 THz 3.125/6.25/12.5GHz spacing";
             }
             enum "1558.65" {
               description "1558.65 nm/192.340625 THz 3.125GHz spacing";
             }
             enum "1558.63" {
               description "1558.63 nm/192.343750 THz 3.125/6.25GHz spacing";
             }
             enum "1558.60" {
               description "1558.60 nm/192.346875 THz 3.125GHz spacing";
             }
             enum "1558.58" {
               description "1558.58 nm/192.350000 THz 3.125/6.25/12.5/50GHz spacing";
             }
             enum "1558.55" {
               description "1558.55 nm/192.353125 THz 3.125GHz spacing";
             }
             enum "1558.53" {
               description "1558.53 nm/192.356250 THz 3.125/6.25GHz spacing";
             }
             enum "1558.50" {
               description "1558.50 nm/192.359375 THz 3.125GHz spacing";
             }
             enum "1558.48" {
               description "1558.48 nm/192.362500 THz 3.125/6.25/12.5GHz spacing";
             }
             enum "1558.45" {
               description "1558.45 nm/192.365625 THz 3.125GHz spacing";
             }
             enum "1558.43" {
               description "1558.43 nm/192.368750 THz 3.125/6.25GHz spacing";
             }
             enum "1558.40" {
               description "1558.40 nm/192.371875 THz 3.125GHz spacing";
             }
             enum "1558.38" {
               description "1558.38 nm/192.375000 THz 3.125/6.25/12.5/75GHz spacing";
             }
             enum "1558.35" {
               description "1558.35 nm/192.378125 THz 3.125GHz spacing";
             }
             enum "1558.32" {
               description "1558.32 nm/192.381250 THz 3.125/6.25GHz spacing";
             }
             enum "1558.30" {
               description "1558.30 nm/192.384375 THz 3.125GHz spacing";
             }
             enum "1558.27" {
               description "1558.27 nm/192.387500 THz 3.125/6.25/12.5GHz spacing";
             }
             enum "1558.25" {
               description "1558.25 nm/192.390625 THz 3.125GHz spacing";
             }
             enum "1558.22" {
               description "1558.22 nm/192.393750 THz 3.125/6.25GHz spacing";
             }
             enum "1558.20" {
               description "1558.20 nm/192.396875 THz 3.125GHz spacing";
             }
             enum "1558.17" {
               description "1558.17 nm/192.400000 THz 3.125/6.25/12.5/100GHz spacing";
             }
             enum "1558.15" {
               description "1558.15 nm/192.403125 THz 3.125GHz spacing";
             }
             enum "1558.12" {
               description "1558.12 nm/192.406250 THz 3.125/6.25GHz spacing";
             }
             enum "1558.10" {
               description "1558.10 nm/192.409375 THz 3.125GHz spacing";
             }
             enum "1558.07" {
               description "1558.07 nm/192.412500 THz 3.125/6.25/12.5GHz spacing";
             }
             enum "1558.05" {
               description "1558.05 nm/192.415625 THz 3.125GHz spacing";
             }
             enum "1558.02" {
               description "1558.02 nm/192.418750 THz 3.125/6.25GHz spacing";
             }
             enum "1558.00" {
               description "1558.00 nm/192.421875 THz 3.125GHz spacing";
             }
             enum "1557.97" {
               description "1557.97 nm/192.425000 THz 3.125/6.25/12.5GHz spacing";
             }
             enum "1557.95" {
               description "1557.95 nm/192.428125 THz 3.125GHz spacing";
             }
             enum "1557.92" {
               description "1557.92 nm/192.431250 THz 3.125/6.25GHz spacing";
             }
             enum "1557.89" {
               description "1557.89 nm/192.434375 THz 3.125GHz spacing";
             }
             enum "1557.87" {
               description "1557.87 nm/192.437500 THz 3.125/6.25/12.5GHz spacing";
             }
             enum "1557.84" {
               description "1557.84 nm/192.440625 THz 3.125GHz spacing";
             }
             enum "1557.82" {
               description "1557.82 nm/192.443750 THz 3.125/6.25GHz spacing";
             }
             enum "1557.79" {
               description "1557.79 nm/192.446875 THz 3.125GHz spacing";
             }
             enum "1557.77" {
               description "1557.77 nm/192.450000 THz 3.125/6.25/12.5/50/75GHz spacing";
             }
             enum "1557.74" {
               description "1557.74 nm/192.453125 THz 3.125GHz spacing";
             }
             enum "1557.72" {
               description "1557.72 nm/192.456250 THz 3.125/6.25GHz spacing";
             }
             enum "1557.69" {
               description "1557.69 nm/192.459375 THz 3.125GHz spacing";
             }
             enum "1557.67" {
               description "1557.67 nm/192.462500 THz 3.125/6.25/12.5GHz spacing";
             }
             enum "1557.64" {
               description "1557.64 nm/192.465625 THz 3.125GHz spacing";
             }
             enum "1557.62" {
               description "1557.62 nm/192.468750 THz 3.125/6.25GHz spacing";
             }
             enum "1557.59" {
               description "1557.59 nm/192.471875 THz 3.125GHz spacing";
             }
             enum "1557.57" {
               description "1557.57 nm/192.475000 THz 3.125/6.25/12.5GHz spacing";
             }
             enum "1557.54" {
               description "1557.54 nm/192.478125 THz 3.125GHz spacing";
             }
             enum "1557.52" {
               description "1557.52 nm/192.481250 THz 3.125/6.25GHz spacing";
             }
             enum "1557.49" {
               description "1557.49 nm/192.484375 THz 3.125GHz spacing";
             }
             enum "1557.46" {
               description "1557.46 nm/192.487500 THz 3.125/6.25/12.5GHz spacing";
             }
             enum "1557.44" {
               description "1557.44 nm/192.490625 THz 3.125GHz spacing";
             }
             enum "1557.41" {
               description "1557.41 nm/192.493750 THz 3.125/6.25GHz spacing";
             }
             enum "1557.39" {
               description "1557.39 nm/192.496875 THz 3.125GHz spacing";
             }
             enum "1557.36" {
               description "1557.36 nm/192.500000 THz 3.125/6.25/12.5/100GHz spacing";
             }
             enum "1557.34" {
               description "1557.34 nm/192.503125 THz 3.125GHz spacing";
             }
             enum "1557.31" {
               description "1557.31 nm/192.506250 THz 3.125/6.25GHz spacing";
             }
             enum "1557.29" {
               description "1557.29 nm/192.509375 THz 3.125GHz spacing";
             }
             enum "1557.26" {
               description "1557.26 nm/192.512500 THz 3.125/6.25/12.5GHz spacing";
             }
             enum "1557.24" {
               description "1557.24 nm/192.515625 THz 3.125GHz spacing";
             }
             enum "1557.21" {
               description "1557.21 nm/192.518750 THz 3.125/6.25GHz spacing";
             }
             enum "1557.19" {
               description "1557.19 nm/192.521875 THz 3.125GHz spacing";
             }
             enum "1557.16" {
               description "1557.16 nm/192.525000 THz 3.125/6.25/12.5/75GHz spacing";
             }
             enum "1557.14" {
               description "1557.14 nm/192.528125 THz 3.125GHz spacing";
             }
             enum "1557.11" {
               description "1557.11 nm/192.531250 THz 3.125/6.25GHz spacing";
             }
             enum "1557.09" {
               description "1557.09 nm/192.534375 THz 3.125GHz spacing";
             }
             enum "1557.06" {
               description "1557.06 nm/192.537500 THz 3.125/6.25/12.5GHz spacing";
             }
             enum "1557.03" {
               description "1557.03 nm/192.540625 THz 3.125GHz spacing";
             }
             enum "1557.01" {
               description "1557.01 nm/192.543750 THz 3.125/6.25GHz spacing";
             }
             enum "1556.98" {
               description "1556.98 nm/192.546875 THz 3.125GHz spacing";
             }
             enum "1556.96" {
               description "1556.96 nm/192.550000 THz 3.125/6.25/12.5/50GHz spacing";
             }
             enum "1556.93" {
               description "1556.93 nm/192.553125 THz 3.125GHz spacing";
             }
             enum "1556.91" {
               description "1556.91 nm/192.556250 THz 3.125/6.25GHz spacing";
             }
             enum "1556.88" {
               description "1556.88 nm/192.559375 THz 3.125GHz spacing";
             }
             enum "1556.86" {
               description "1556.86 nm/192.562500 THz 3.125/6.25/12.5GHz spacing";
             }
             enum "1556.83" {
               description "1556.83 nm/192.565625 THz 3.125GHz spacing";
             }
             enum "1556.81" {
               description "1556.81 nm/192.568750 THz 3.125/6.25GHz spacing";
             }
             enum "1556.78" {
               description "1556.78 nm/192.571875 THz 3.125GHz spacing";
             }
             enum "1556.76" {
               description "1556.76 nm/192.575000 THz 3.125/6.25/12.5GHz spacing";
             }
             enum "1556.73" {
               description "1556.73 nm/192.578125 THz 3.125GHz spacing";
             }
             enum "1556.71" {
               description "1556.71 nm/192.581250 THz 3.125/6.25GHz spacing";
             }
             enum "1556.68" {
               description "1556.68 nm/192.584375 THz 3.125GHz spacing";
             }
             enum "1556.66" {
               description "1556.66 nm/192.587500 THz 3.125/6.25/12.5GHz spacing";
             }
             enum "1556.63" {
               description "1556.63 nm/192.590625 THz 3.125GHz spacing";
             }
             enum "1556.61" {
               description "1556.61 nm/192.593750 THz 3.125/6.25GHz spacing";
             }
             enum "1556.58" {
               description "1556.58 nm/192.596875 THz 3.125GHz spacing";
             }
             enum "1556.55" {
               description "1556.55 nm/192.600000 THz 3.125/6.25/12.5/50/75/100GHz spacing";
             }
             enum "1556.53" {
               description "1556.53 nm/192.603125 THz 3.125GHz spacing";
             }
             enum "1556.50" {
               description "1556.50 nm/192.606250 THz 3.125/6.25GHz spacing";
             }
             enum "1556.48" {
               description "1556.48 nm/192.609375 THz 3.125GHz spacing";
             }
             enum "1556.45" {
               description "1556.45 nm/192.612500 THz 3.125/6.25/12.5GHz spacing";
             }
             enum "1556.43" {
               description "1556.43 nm/192.615625 THz 3.125GHz spacing";
             }
             enum "1556.40" {
               description "1556.40 nm/192.618750 THz 3.125/6.25GHz spacing";
             }
             enum "1556.38" {
               description "1556.38 nm/192.621875 THz 3.125GHz spacing";
             }
             enum "1556.35" {
               description "1556.35 nm/192.625000 THz 3.125/6.25/12.5GHz spacing";
             }
             enum "1556.33" {
               description "1556.33 nm/192.628125 THz 3.125GHz spacing";
             }
             enum "1556.30" {
               description "1556.30 nm/192.631250 THz 3.125/6.25GHz spacing";
             }
             enum "1556.28" {
               description "1556.28 nm/192.634375 THz 3.125GHz spacing";
             }
             enum "1556.25" {
               description "1556.25 nm/192.637500 THz 3.125/6.25/12.5GHz spacing";
             }
             enum "1556.23" {
               description "1556.23 nm/192.640625 THz 3.125GHz spacing";
             }
             enum "1556.20" {
               description "1556.20 nm/192.643750 THz 3.125/6.25GHz spacing";
             }
             enum "1556.18" {
               description "1556.18 nm/192.646875 THz 3.125GHz spacing";
             }
             enum "1556.15" {
               description "1556.15 nm/192.650000 THz 3.125/6.25/12.5/50GHz spacing";
             }
             enum "1556.13" {
               description "1556.13 nm/192.653125 THz 3.125GHz spacing";
             }
             enum "1556.10" {
               description "1556.10 nm/192.656250 THz 3.125/6.25GHz spacing";
             }
             enum "1556.08" {
               description "1556.08 nm/192.659375 THz 3.125GHz spacing";
             }
             enum "1556.05" {
               description "1556.05 nm/192.662500 THz 3.125/6.25/12.5GHz spacing";
             }
             enum "1556.02" {
               description "1556.02 nm/192.665625 THz 3.125GHz spacing";
             }
             enum "1556.00" {
               description "1556.00 nm/192.668750 THz 3.125/6.25GHz spacing";
             }
             enum "1555.97" {
               description "1555.97 nm/192.671875 THz 3.125GHz spacing";
             }
             enum "1555.95" {
               description "1555.95 nm/192.675000 THz 3.125/6.25/12.5/75GHz spacing";
             }
             enum "1555.92" {
               description "1555.92 nm/192.678125 THz 3.125GHz spacing";
             }
             enum "1555.90" {
               description "1555.90 nm/192.681250 THz 3.125/6.25GHz spacing";
             }
             enum "1555.87" {
               description "1555.87 nm/192.684375 THz 3.125GHz spacing";
             }
             enum "1555.85" {
               description "1555.85 nm/192.687500 THz 3.125/6.25/12.5GHz spacing";
             }
             enum "1555.82" {
               description "1555.82 nm/192.690625 THz 3.125GHz spacing";
             }
             enum "1555.80" {
               description "1555.80 nm/192.693750 THz 3.125/6.25GHz spacing";
             }
             enum "1555.77" {
               description "1555.77 nm/192.696875 THz 3.125GHz spacing";
             }
             enum "1555.75" {
               description "1555.75 nm/192.700000 THz 3.125/6.25/12.5/100GHz spacing";
             }
             enum "1555.72" {
               description "1555.72 nm/192.703125 THz 3.125GHz spacing";
             }
             enum "1555.70" {
               description "1555.70 nm/192.706250 THz 3.125/6.25GHz spacing";
             }
             enum "1555.67" {
               description "1555.67 nm/192.709375 THz 3.125GHz spacing";
             }
             enum "1555.65" {
               description "1555.65 nm/192.712500 THz 3.125/6.25/12.5GHz spacing";
             }
             enum "1555.62" {
               description "1555.62 nm/192.715625 THz 3.125GHz spacing";
             }
             enum "1555.60" {
               description "1555.60 nm/192.718750 THz 3.125/6.25GHz spacing";
             }
             enum "1555.57" {
               description "1555.57 nm/192.721875 THz 3.125GHz spacing";
             }
             enum "1555.55" {
               description "1555.55 nm/192.725000 THz 3.125/6.25/12.5GHz spacing";
             }
             enum "1555.52" {
               description "1555.52 nm/192.728125 THz 3.125GHz spacing";
             }
             enum "1555.49" {
               description "1555.49 nm/192.731250 THz 3.125/6.25GHz spacing";
             }
             enum "1555.47" {
               description "1555.47 nm/192.734375 THz 3.125GHz spacing";
             }
             enum "1555.44" {
               description "1555.44 nm/192.737500 THz 3.125/6.25/12.5GHz spacing";
             }
             enum "1555.42" {
               description "1555.42 nm/192.740625 THz 3.125GHz spacing";
             }
             enum "1555.39" {
               description "1555.39 nm/192.743750 THz 3.125/6.25GHz spacing";
             }
             enum "1555.37" {
               description "1555.37 nm/192.746875 THz 3.125GHz spacing";
             }
             enum "1555.34" {
               description "1555.34 nm/192.750000 THz 3.125/6.25/12.5/50/75GHz spacing";
             }
             enum "1555.32" {
               description "1555.32 nm/192.753125 THz 3.125GHz spacing";
             }
             enum "1555.29" {
               description "1555.29 nm/192.756250 THz 3.125/6.25GHz spacing";
             }
             enum "1555.27" {
               description "1555.27 nm/192.759375 THz 3.125GHz spacing";
             }
             enum "1555.24" {
               description "1555.24 nm/192.762500 THz 3.125/6.25/12.5GHz spacing";
             }
             enum "1555.22" {
               description "1555.22 nm/192.765625 THz 3.125GHz spacing";
             }
             enum "1555.19" {
               description "1555.19 nm/192.768750 THz 3.125/6.25GHz spacing";
             }
             enum "1555.17" {
               description "1555.17 nm/192.771875 THz 3.125GHz spacing";
             }
             enum "1555.14" {
               description "1555.14 nm/192.775000 THz 3.125/6.25/12.5GHz spacing";
             }
             enum "1555.12" {
               description "1555.12 nm/192.778125 THz 3.125GHz spacing";
             }
             enum "1555.09" {
               description "1555.09 nm/192.781250 THz 3.125/6.25GHz spacing";
             }
             enum "1555.07" {
               description "1555.07 nm/192.784375 THz 3.125GHz spacing";
             }
             enum "1555.04" {
               description "1555.04 nm/192.787500 THz 3.125/6.25/12.5GHz spacing";
             }
             enum "1555.02" {
               description "1555.02 nm/192.790625 THz 3.125GHz spacing";
             }
             enum "1554.99" {
               description "1554.99 nm/192.793750 THz 3.125/6.25GHz spacing";
             }
             enum "1554.97" {
               description "1554.97 nm/192.796875 THz 3.125GHz spacing";
             }
             enum "1554.94" {
               description "1554.94 nm/192.800000 THz 3.125/6.25/12.5/100GHz spacing";
             }
             enum "1554.91" {
               description "1554.91 nm/192.803125 THz 3.125GHz spacing";
             }
             enum "1554.89" {
               description "1554.89 nm/192.806250 THz 3.125/6.25GHz spacing";
             }
             enum "1554.86" {
               description "1554.86 nm/192.809375 THz 3.125GHz spacing";
             }
             enum "1554.84" {
               description "1554.84 nm/192.812500 THz 3.125/6.25/12.5GHz spacing";
             }
             enum "1554.81" {
               description "1554.81 nm/192.815625 THz 3.125GHz spacing";
             }
             enum "1554.79" {
               description "1554.79 nm/192.818750 THz 3.125/6.25GHz spacing";
             }
             enum "1554.76" {
               description "1554.76 nm/192.821875 THz 3.125GHz spacing";
             }
             enum "1554.74" {
               description "1554.74 nm/192.825000 THz 3.125/6.25/12.5/75GHz spacing";
             }
             enum "1554.71" {
               description "1554.71 nm/192.828125 THz 3.125GHz spacing";
             }
             enum "1554.69" {
               description "1554.69 nm/192.831250 THz 3.125/6.25GHz spacing";
             }
             enum "1554.66" {
               description "1554.66 nm/192.834375 THz 3.125GHz spacing";
             }
             enum "1554.64" {
               description "1554.64 nm/192.837500 THz 3.125/6.25/12.5GHz spacing";
             }
             enum "1554.61" {
               description "1554.61 nm/192.840625 THz 3.125GHz spacing";
             }
             enum "1554.59" {
               description "1554.59 nm/192.843750 THz 3.125/6.25GHz spacing";
             }
             enum "1554.56" {
               description "1554.56 nm/192.846875 THz 3.125GHz spacing";
             }
             enum "1554.54" {
               description "1554.54 nm/192.850000 THz 3.125/6.25/12.5/50GHz spacing";
             }
             enum "1554.51" {
               description "1554.51 nm/192.853125 THz 3.125GHz spacing";
             }
             enum "1554.49" {
               description "1554.49 nm/192.856250 THz 3.125/6.25GHz spacing";
             }
             enum "1554.46" {
               description "1554.46 nm/192.859375 THz 3.125GHz spacing";
             }
             enum "1554.44" {
               description "1554.44 nm/192.862500 THz 3.125/6.25/12.5GHz spacing";
             }
             enum "1554.41" {
               description "1554.41 nm/192.865625 THz 3.125GHz spacing";
             }
             enum "1554.39" {
               description "1554.39 nm/192.868750 THz 3.125/6.25GHz spacing";
             }
             enum "1554.36" {
               description "1554.36 nm/192.871875 THz 3.125GHz spacing";
             }
             enum "1554.34" {
               description "1554.34 nm/192.875000 THz 3.125/6.25/12.5GHz spacing";
             }
             enum "1554.31" {
               description "1554.31 nm/192.878125 THz 3.125GHz spacing";
             }
             enum "1554.29" {
               description "1554.29 nm/192.881250 THz 3.125/6.25GHz spacing";
             }
             enum "1554.26" {
               description "1554.26 nm/192.884375 THz 3.125GHz spacing";
             }
             enum "1554.23" {
               description "1554.23 nm/192.887500 THz 3.125/6.25/12.5GHz spacing";
             }
             enum "1554.21" {
               description "1554.21 nm/192.890625 THz 3.125GHz spacing";
             }
             enum "1554.18" {
               description "1554.18 nm/192.893750 THz 3.125/6.25GHz spacing";
             }
             enum "1554.16" {
               description "1554.16 nm/192.896875 THz 3.125GHz spacing";
             }
             enum "1554.13" {
               description "1554.13 nm/192.900000 THz 3.125/6.25/12.5/50/75/100GHz spacing";
             }
             enum "1554.11" {
               description "1554.11 nm/192.903125 THz 3.125GHz spacing";
             }
             enum "1554.08" {
               description "1554.08 nm/192.906250 THz 3.125/6.25GHz spacing";
             }
             enum "1554.06" {
               description "1554.06 nm/192.909375 THz 3.125GHz spacing";
             }
             enum "1554.03" {
               description "1554.03 nm/192.912500 THz 3.125/6.25/12.5GHz spacing";
             }
             enum "1554.01" {
               description "1554.01 nm/192.915625 THz 3.125GHz spacing";
             }
             enum "1553.98" {
               description "1553.98 nm/192.918750 THz 3.125/6.25GHz spacing";
             }
             enum "1553.96" {
               description "1553.96 nm/192.921875 THz 3.125GHz spacing";
             }
             enum "1553.93" {
               description "1553.93 nm/192.925000 THz 3.125/6.25/12.5GHz spacing";
             }
             enum "1553.91" {
               description "1553.91 nm/192.928125 THz 3.125GHz spacing";
             }
             enum "1553.88" {
               description "1553.88 nm/192.931250 THz 3.125/6.25GHz spacing";
             }
             enum "1553.86" {
               description "1553.86 nm/192.934375 THz 3.125GHz spacing";
             }
             enum "1553.83" {
               description "1553.83 nm/192.937500 THz 3.125/6.25/12.5GHz spacing";
             }
             enum "1553.81" {
               description "1553.81 nm/192.940625 THz 3.125GHz spacing";
             }
             enum "1553.78" {
               description "1553.78 nm/192.943750 THz 3.125/6.25GHz spacing";
             }
             enum "1553.76" {
               description "1553.76 nm/192.946875 THz 3.125GHz spacing";
             }
             enum "1553.73" {
               description "1553.73 nm/192.950000 THz 3.125/6.25/12.5/50GHz spacing";
             }
             enum "1553.71" {
               description "1553.71 nm/192.953125 THz 3.125GHz spacing";
             }
             enum "1553.68" {
               description "1553.68 nm/192.956250 THz 3.125/6.25GHz spacing";
             }
             enum "1553.66" {
               description "1553.66 nm/192.959375 THz 3.125GHz spacing";
             }
             enum "1553.63" {
               description "1553.63 nm/192.962500 THz 3.125/6.25/12.5GHz spacing";
             }
             enum "1553.61" {
               description "1553.61 nm/192.965625 THz 3.125GHz spacing";
             }
             enum "1553.58" {
               description "1553.58 nm/192.968750 THz 3.125/6.25GHz spacing";
             }
             enum "1553.56" {
               description "1553.56 nm/192.971875 THz 3.125GHz spacing";
             }
             enum "1553.53" {
               description "1553.53 nm/192.975000 THz 3.125/6.25/12.5/75GHz spacing";
             }
             enum "1553.50" {
               description "1553.50 nm/192.978125 THz 3.125GHz spacing";
             }
             enum "1553.48" {
               description "1553.48 nm/192.981250 THz 3.125/6.25GHz spacing";
             }
             enum "1553.45" {
               description "1553.45 nm/192.984375 THz 3.125GHz spacing";
             }
             enum "1553.43" {
               description "1553.43 nm/192.987500 THz 3.125/6.25/12.5GHz spacing";
             }
             enum "1553.40" {
               description "1553.40 nm/192.990625 THz 3.125GHz spacing";
             }
             enum "1553.38" {
               description "1553.38 nm/192.993750 THz 3.125/6.25GHz spacing";
             }
             enum "1553.35" {
               description "1553.35 nm/192.996875 THz 3.125GHz spacing";
             }
             enum "1553.33" {
               description "1553.33 nm/193.000000 THz 3.125/6.25/12.5/100GHz spacing";
             }
             enum "1553.30" {
               description "1553.30 nm/193.003125 THz 3.125GHz spacing";
             }
             enum "1553.28" {
               description "1553.28 nm/193.006250 THz 3.125/6.25GHz spacing";
             }
             enum "1553.25" {
               description "1553.25 nm/193.009375 THz 3.125GHz spacing";
             }
             enum "1553.23" {
               description "1553.23 nm/193.012500 THz 3.125/6.25/12.5GHz spacing";
             }
             enum "1553.20" {
               description "1553.20 nm/193.015625 THz 3.125GHz spacing";
             }
             enum "1553.18" {
               description "1553.18 nm/193.018750 THz 3.125/6.25GHz spacing";
             }
             enum "1553.15" {
               description "1553.15 nm/193.021875 THz 3.125GHz spacing";
             }
             enum "1553.13" {
               description "1553.13 nm/193.025000 THz 3.125/6.25/12.5GHz spacing";
             }
             enum "1553.10" {
               description "1553.10 nm/193.028125 THz 3.125GHz spacing";
             }
             enum "1553.08" {
               description "1553.08 nm/193.031250 THz 3.125/6.25GHz spacing";
             }
             enum "1553.05" {
               description "1553.05 nm/193.034375 THz 3.125GHz spacing";
             }
             enum "1553.03" {
               description "1553.03 nm/193.037500 THz 3.125/6.25/12.5GHz spacing";
             }
             enum "1553.00" {
               description "1553.00 nm/193.040625 THz 3.125GHz spacing";
             }
             enum "1552.98" {
               description "1552.98 nm/193.043750 THz 3.125/6.25GHz spacing";
             }
             enum "1552.95" {
               description "1552.95 nm/193.046875 THz 3.125GHz spacing";
             }
             enum "1552.93" {
               description "1552.93 nm/193.050000 THz 3.125/6.25/12.5/50/75GHz spacing";
             }
             enum "1552.90" {
               description "1552.90 nm/193.053125 THz 3.125GHz spacing";
             }
             enum "1552.88" {
               description "1552.88 nm/193.056250 THz 3.125/6.25GHz spacing";
             }
             enum "1552.85" {
               description "1552.85 nm/193.059375 THz 3.125GHz spacing";
             }
             enum "1552.83" {
               description "1552.83 nm/193.062500 THz 3.125/6.25/12.5GHz spacing";
             }
             enum "1552.80" {
               description "1552.80 nm/193.065625 THz 3.125GHz spacing";
             }
             enum "1552.78" {
               description "1552.78 nm/193.068750 THz 3.125/6.25GHz spacing";
             }
             enum "1552.75" {
               description "1552.75 nm/193.071875 THz 3.125GHz spacing";
             }
             enum "1552.73" {
               description "1552.73 nm/193.075000 THz 3.125/6.25/12.5GHz spacing";
             }
             enum "1552.70" {
               description "1552.70 nm/193.078125 THz 3.125GHz spacing";
             }
             enum "1552.68" {
               description "1552.68 nm/193.081250 THz 3.125/6.25GHz spacing";
             }
             enum "1552.65" {
               description "1552.65 nm/193.084375 THz 3.125GHz spacing";
             }
             enum "1552.62" {
               description "1552.62 nm/193.087500 THz 3.125/6.25/12.5GHz spacing";
             }
             enum "1552.60" {
               description "1552.60 nm/193.090625 THz 3.125GHz spacing";
             }
             enum "1552.57" {
               description "1552.57 nm/193.093750 THz 3.125/6.25GHz spacing";
             }
             enum "1552.55" {
               description "1552.55 nm/193.096875 THz 3.125GHz spacing";
             }
             enum "1552.52" {
               description "1552.52 nm/193.100000 THz 3.125/6.25/12.5/100GHz spacing";
             }
             enum "1552.50" {
               description "1552.50 nm/193.103125 THz 3.125GHz spacing";
             }
             enum "1552.47" {
               description "1552.47 nm/193.106250 THz 3.125/6.25GHz spacing";
             }
             enum "1552.45" {
               description "1552.45 nm/193.109375 THz 3.125GHz spacing";
             }
             enum "1552.42" {
               description "1552.42 nm/193.112500 THz 3.125/6.25/12.5GHz spacing";
             }
             enum "1552.40" {
               description "1552.40 nm/193.115625 THz 3.125GHz spacing";
             }
             enum "1552.37" {
               description "1552.37 nm/193.118750 THz 3.125/6.25GHz spacing";
             }
             enum "1552.35" {
               description "1552.35 nm/193.121875 THz 3.125GHz spacing";
             }
             enum "1552.32" {
               description "1552.32 nm/193.125000 THz 3.125/6.25/12.5/75GHz spacing";
             }
             enum "1552.30" {
               description "1552.30 nm/193.128125 THz 3.125GHz spacing";
             }
             enum "1552.27" {
               description "1552.27 nm/193.131250 THz 3.125/6.25GHz spacing";
             }
             enum "1552.25" {
               description "1552.25 nm/193.134375 THz 3.125GHz spacing";
             }
             enum "1552.22" {
               description "1552.22 nm/193.137500 THz 3.125/6.25/12.5GHz spacing";
             }
             enum "1552.20" {
               description "1552.20 nm/193.140625 THz 3.125GHz spacing";
             }
             enum "1552.17" {
               description "1552.17 nm/193.143750 THz 3.125/6.25GHz spacing";
             }
             enum "1552.15" {
               description "1552.15 nm/193.146875 THz 3.125GHz spacing";
             }
             enum "1552.12" {
               description "1552.12 nm/193.150000 THz 3.125/6.25/12.5/50GHz spacing";
             }
             enum "1552.10" {
               description "1552.10 nm/193.153125 THz 3.125GHz spacing";
             }
             enum "1552.07" {
               description "1552.07 nm/193.156250 THz 3.125/6.25GHz spacing";
             }
             enum "1552.05" {
               description "1552.05 nm/193.159375 THz 3.125GHz spacing";
             }
             enum "1552.02" {
               description "1552.02 nm/193.162500 THz 3.125/6.25/12.5GHz spacing";
             }
             enum "1552.00" {
               description "1552.00 nm/193.165625 THz 3.125GHz spacing";
             }
             enum "1551.97" {
               description "1551.97 nm/193.168750 THz 3.125/6.25GHz spacing";
             }
             enum "1551.95" {
               description "1551.95 nm/193.171875 THz 3.125GHz spacing";
             }
             enum "1551.92" {
               description "1551.92 nm/193.175000 THz 3.125/6.25/12.5GHz spacing";
             }
             enum "1551.90" {
               description "1551.90 nm/193.178125 THz 3.125GHz spacing";
             }
             enum "1551.87" {
               description "1551.87 nm/193.181250 THz 3.125/6.25GHz spacing";
             }
             enum "1551.85" {
               description "1551.85 nm/193.184375 THz 3.125GHz spacing";
             }
             enum "1551.82" {
               description "1551.82 nm/193.187500 THz 3.125/6.25/12.5GHz spacing";
             }
             enum "1551.80" {
               description "1551.80 nm/193.190625 THz 3.125GHz spacing";
             }
             enum "1551.77" {
               description "1551.77 nm/193.193750 THz 3.125/6.25GHz spacing";
             }
             enum "1551.75" {
               description "1551.75 nm/193.196875 THz 3.125GHz spacing";
             }
             enum "1551.72" {
               description "1551.72 nm/193.200000 THz 3.125/6.25/12.5/50/75/100GHz spacing";
             }
             enum "1551.70" {
               description "1551.70 nm/193.203125 THz 3.125GHz spacing";
             }
             enum "1551.67" {
               description "1551.67 nm/193.206250 THz 3.125/6.25GHz spacing";
             }
             enum "1551.65" {
               description "1551.65 nm/193.209375 THz 3.125GHz spacing";
             }
             enum "1551.62" {
               description "1551.62 nm/193.212500 THz 3.125/6.25/12.5GHz spacing";
             }
             enum "1551.60" {
               description "1551.60 nm/193.215625 THz 3.125GHz spacing";
             }
             enum "1551.57" {
               description "1551.57 nm/193.218750 THz 3.125/6.25GHz spacing";
             }
             enum "1551.55" {
               description "1551.55 nm/193.221875 THz 3.125GHz spacing";
             }
             enum "1551.52" {
               description "1551.52 nm/193.225000 THz 3.125/6.25/12.5GHz spacing";
             }
             enum "1551.49" {
               description "1551.49 nm/193.228125 THz 3.125GHz spacing";
             }
             enum "1551.47" {
               description "1551.47 nm/193.231250 THz 3.125/6.25GHz spacing";
             }
             enum "1551.44" {
               description "1551.44 nm/193.234375 THz 3.125GHz spacing";
             }
             enum "1551.42" {
               description "1551.42 nm/193.237500 THz 3.125/6.25/12.5GHz spacing";
             }
             enum "1551.39" {
               description "1551.39 nm/193.240625 THz 3.125GHz spacing";
             }
             enum "1551.37" {
               description "1551.37 nm/193.243750 THz 3.125/6.25GHz spacing";
             }
             enum "1551.34" {
               description "1551.34 nm/193.246875 THz 3.125GHz spacing";
             }
             enum "1551.32" {
               description "1551.32 nm/193.250000 THz 3.125/6.25/12.5/50GHz spacing";
             }
             enum "1551.29" {
               description "1551.29 nm/193.253125 THz 3.125GHz spacing";
             }
             enum "1551.27" {
               description "1551.27 nm/193.256250 THz 3.125/6.25GHz spacing";
             }
             enum "1551.24" {
               description "1551.24 nm/193.259375 THz 3.125GHz spacing";
             }
             enum "1551.22" {
               description "1551.22 nm/193.262500 THz 3.125/6.25/12.5GHz spacing";
             }
             enum "1551.19" {
               description "1551.19 nm/193.265625 THz 3.125GHz spacing";
             }
             enum "1551.17" {
               description "1551.17 nm/193.268750 THz 3.125/6.25GHz spacing";
             }
             enum "1551.14" {
               description "1551.14 nm/193.271875 THz 3.125GHz spacing";
             }
             enum "1551.12" {
               description "1551.12 nm/193.275000 THz 3.125/6.25/12.5/75GHz spacing";
             }
             enum "1551.09" {
               description "1551.09 nm/193.278125 THz 3.125GHz spacing";
             }
             enum "1551.07" {
               description "1551.07 nm/193.281250 THz 3.125/6.25GHz spacing";
             }
             enum "1551.04" {
               description "1551.04 nm/193.284375 THz 3.125GHz spacing";
             }
             enum "1551.02" {
               description "1551.02 nm/193.287500 THz 3.125/6.25/12.5GHz spacing";
             }
             enum "1550.99" {
               description "1550.99 nm/193.290625 THz 3.125GHz spacing";
             }
             enum "1550.97" {
               description "1550.97 nm/193.293750 THz 3.125/6.25GHz spacing";
             }
             enum "1550.94" {
               description "1550.94 nm/193.296875 THz 3.125GHz spacing";
             }
             enum "1550.92" {
               description "1550.92 nm/193.300000 THz 3.125/6.25/12.5/100GHz spacing";
             }
             enum "1550.89" {
               description "1550.89 nm/193.303125 THz 3.125GHz spacing";
             }
             enum "1550.87" {
               description "1550.87 nm/193.306250 THz 3.125/6.25GHz spacing";
             }
             enum "1550.84" {
               description "1550.84 nm/193.309375 THz 3.125GHz spacing";
             }
             enum "1550.82" {
               description "1550.82 nm/193.312500 THz 3.125/6.25/12.5GHz spacing";
             }
             enum "1550.79" {
               description "1550.79 nm/193.315625 THz 3.125GHz spacing";
             }
             enum "1550.77" {
               description "1550.77 nm/193.318750 THz 3.125/6.25GHz spacing";
             }
             enum "1550.74" {
               description "1550.74 nm/193.321875 THz 3.125GHz spacing";
             }
             enum "1550.72" {
               description "1550.72 nm/193.325000 THz 3.125/6.25/12.5GHz spacing";
             }
             enum "1550.69" {
               description "1550.69 nm/193.328125 THz 3.125GHz spacing";
             }
             enum "1550.67" {
               description "1550.67 nm/193.331250 THz 3.125/6.25GHz spacing";
             }
             enum "1550.64" {
               description "1550.64 nm/193.334375 THz 3.125GHz spacing";
             }
             enum "1550.62" {
               description "1550.62 nm/193.337500 THz 3.125/6.25/12.5GHz spacing";
             }
             enum "1550.59" {
               description "1550.59 nm/193.340625 THz 3.125GHz spacing";
             }
             enum "1550.57" {
               description "1550.57 nm/193.343750 THz 3.125/6.25GHz spacing";
             }
             enum "1550.54" {
               description "1550.54 nm/193.346875 THz 3.125GHz spacing";
             }
             enum "1550.52" {
               description "1550.52 nm/193.350000 THz 3.125/6.25/12.5/50/75GHz spacing";
             }
             enum "1550.49" {
               description "1550.49 nm/193.353125 THz 3.125GHz spacing";
             }
             enum "1550.47" {
               description "1550.47 nm/193.356250 THz 3.125/6.25GHz spacing";
             }
             enum "1550.44" {
               description "1550.44 nm/193.359375 THz 3.125GHz spacing";
             }
             enum "1550.42" {
               description "1550.42 nm/193.362500 THz 3.125/6.25/12.5GHz spacing";
             }
             enum "1550.39" {
               description "1550.39 nm/193.365625 THz 3.125GHz spacing";
             }
             enum "1550.37" {
               description "1550.37 nm/193.368750 THz 3.125/6.25GHz spacing";
             }
             enum "1550.34" {
               description "1550.34 nm/193.371875 THz 3.125GHz spacing";
             }
             enum "1550.32" {
               description "1550.32 nm/193.375000 THz 3.125/6.25/12.5GHz spacing";
             }
             enum "1550.29" {
               description "1550.29 nm/193.378125 THz 3.125GHz spacing";
             }
             enum "1550.27" {
               description "1550.27 nm/193.381250 THz 3.125/6.25GHz spacing";
             }
             enum "1550.24" {
               description "1550.24 nm/193.384375 THz 3.125GHz spacing";
             }
             enum "1550.22" {
               description "1550.22 nm/193.387500 THz 3.125/6.25/12.5GHz spacing";
             }
             enum "1550.19" {
               description "1550.19 nm/193.390625 THz 3.125GHz spacing";
             }
             enum "1550.17" {
               description "1550.17 nm/193.393750 THz 3.125/6.25GHz spacing";
             }
             enum "1550.14" {
               description "1550.14 nm/193.396875 THz 3.125GHz spacing";
             }
             enum "1550.12" {
               description "1550.12 nm/193.400000 THz 3.125/6.25/12.5/100GHz spacing";
             }
             enum "1550.09" {
               description "1550.09 nm/193.403125 THz 3.125GHz spacing";
             }
             enum "1550.07" {
               description "1550.07 nm/193.406250 THz 3.125/6.25GHz spacing";
             }
             enum "1550.04" {
               description "1550.04 nm/193.409375 THz 3.125GHz spacing";
             }
             enum "1550.02" {
               description "1550.02 nm/193.412500 THz 3.125/6.25/12.5GHz spacing";
             }
             enum "1549.99" {
               description "1549.99 nm/193.415625 THz 3.125GHz spacing";
             }
             enum "1549.97" {
               description "1549.97 nm/193.418750 THz 3.125/6.25GHz spacing";
             }
             enum "1549.94" {
               description "1549.94 nm/193.421875 THz 3.125GHz spacing";
             }
             enum "1549.92" {
               description "1549.92 nm/193.425000 THz 3.125/6.25/12.5/75GHz spacing";
             }
             enum "1549.89" {
               description "1549.89 nm/193.428125 THz 3.125GHz spacing";
             }
             enum "1549.87" {
               description "1549.87 nm/193.431250 THz 3.125/6.25GHz spacing";
             }
             enum "1549.84" {
               description "1549.84 nm/193.434375 THz 3.125GHz spacing";
             }
             enum "1549.82" {
               description "1549.82 nm/193.437500 THz 3.125/6.25/12.5GHz spacing";
             }
             enum "1549.79" {
               description "1549.79 nm/193.440625 THz 3.125GHz spacing";
             }
             enum "1549.77" {
               description "1549.77 nm/193.443750 THz 3.125/6.25GHz spacing";
             }
             enum "1549.74" {
               description "1549.74 nm/193.446875 THz 3.125GHz spacing";
             }
             enum "1549.72" {
               description "1549.72 nm/193.450000 THz 3.125/6.25/12.5/50GHz spacing";
             }
             enum "1549.69" {
               description "1549.69 nm/193.453125 THz 3.125GHz spacing";
             }
             enum "1549.67" {
               description "1549.67 nm/193.456250 THz 3.125/6.25GHz spacing";
             }
             enum "1549.64" {
               description "1549.64 nm/193.459375 THz 3.125GHz spacing";
             }
             enum "1549.62" {
               description "1549.62 nm/193.462500 THz 3.125/6.25/12.5GHz spacing";
             }
             enum "1549.59" {
               description "1549.59 nm/193.465625 THz 3.125GHz spacing";
             }
             enum "1549.57" {
               description "1549.57 nm/193.468750 THz 3.125/6.25GHz spacing";
             }
             enum "1549.54" {
               description "1549.54 nm/193.471875 THz 3.125GHz spacing";
             }
             enum "1549.52" {
               description "1549.52 nm/193.475000 THz 3.125/6.25/12.5GHz spacing";
             }
             enum "1549.49" {
               description "1549.49 nm/193.478125 THz 3.125GHz spacing";
             }
             enum "1549.47" {
               description "1549.47 nm/193.481250 THz 3.125/6.25GHz spacing";
             }
             enum "1549.44" {
               description "1549.44 nm/193.484375 THz 3.125GHz spacing";
             }
             enum "1549.42" {
               description "1549.42 nm/193.487500 THz 3.125/6.25/12.5GHz spacing";
             }
             enum "1549.39" {
               description "1549.39 nm/193.490625 THz 3.125GHz spacing";
             }
             enum "1549.37" {
               description "1549.37 nm/193.493750 THz 3.125/6.25GHz spacing";
             }
             enum "1549.34" {
               description "1549.34 nm/193.496875 THz 3.125GHz spacing";
             }
             enum "1549.32" {
               description "1549.32 nm/193.500000 THz 3.125/6.25/12.5/50/75/100GHz spacing";
             }
             enum "1549.29" {
               description "1549.29 nm/193.503125 THz 3.125GHz spacing";
             }
             enum "1549.26" {
               description "1549.26 nm/193.506250 THz 3.125/6.25GHz spacing";
             }
             enum "1549.24" {
               description "1549.24 nm/193.509375 THz 3.125GHz spacing";
             }
             enum "1549.21" {
               description "1549.21 nm/193.512500 THz 3.125/6.25/12.5GHz spacing";
             }
             enum "1549.19" {
               description "1549.19 nm/193.515625 THz 3.125GHz spacing";
             }
             enum "1549.16" {
               description "1549.16 nm/193.518750 THz 3.125/6.25GHz spacing";
             }
             enum "1549.14" {
               description "1549.14 nm/193.521875 THz 3.125GHz spacing";
             }
             enum "1549.11" {
               description "1549.11 nm/193.525000 THz 3.125/6.25/12.5GHz spacing";
             }
             enum "1549.09" {
               description "1549.09 nm/193.528125 THz 3.125GHz spacing";
             }
             enum "1549.06" {
               description "1549.06 nm/193.531250 THz 3.125/6.25GHz spacing";
             }
             enum "1549.04" {
               description "1549.04 nm/193.534375 THz 3.125GHz spacing";
             }
             enum "1549.01" {
               description "1549.01 nm/193.537500 THz 3.125/6.25/12.5GHz spacing";
             }
             enum "1548.99" {
               description "1548.99 nm/193.540625 THz 3.125GHz spacing";
             }
             enum "1548.96" {
               description "1548.96 nm/193.543750 THz 3.125/6.25GHz spacing";
             }
             enum "1548.94" {
               description "1548.94 nm/193.546875 THz 3.125GHz spacing";
             }
             enum "1548.91" {
               description "1548.91 nm/193.550000 THz 3.125/6.25/12.5/50GHz spacing";
             }
             enum "1548.89" {
               description "1548.89 nm/193.553125 THz 3.125GHz spacing";
             }
             enum "1548.86" {
               description "1548.86 nm/193.556250 THz 3.125/6.25GHz spacing";
             }
             enum "1548.84" {
               description "1548.84 nm/193.559375 THz 3.125GHz spacing";
             }
             enum "1548.81" {
               description "1548.81 nm/193.562500 THz 3.125/6.25/12.5GHz spacing";
             }
             enum "1548.79" {
               description "1548.79 nm/193.565625 THz 3.125GHz spacing";
             }
             enum "1548.76" {
               description "1548.76 nm/193.568750 THz 3.125/6.25GHz spacing";
             }
             enum "1548.74" {
               description "1548.74 nm/193.571875 THz 3.125GHz spacing";
             }
             enum "1548.71" {
               description "1548.71 nm/193.575000 THz 3.125/6.25/12.5/75GHz spacing";
             }
             enum "1548.69" {
               description "1548.69 nm/193.578125 THz 3.125GHz spacing";
             }
             enum "1548.66" {
               description "1548.66 nm/193.581250 THz 3.125/6.25GHz spacing";
             }
             enum "1548.64" {
               description "1548.64 nm/193.584375 THz 3.125GHz spacing";
             }
             enum "1548.61" {
               description "1548.61 nm/193.587500 THz 3.125/6.25/12.5GHz spacing";
             }
             enum "1548.59" {
               description "1548.59 nm/193.590625 THz 3.125GHz spacing";
             }
             enum "1548.56" {
               description "1548.56 nm/193.593750 THz 3.125/6.25GHz spacing";
             }
             enum "1548.54" {
               description "1548.54 nm/193.596875 THz 3.125GHz spacing";
             }
             enum "1548.51" {
               description "1548.51 nm/193.600000 THz 3.125/6.25/12.5/100GHz spacing";
             }
             enum "1548.49" {
               description "1548.49 nm/193.603125 THz 3.125GHz spacing";
             }
             enum "1548.46" {
               description "1548.46 nm/193.606250 THz 3.125/6.25GHz spacing";
             }
             enum "1548.44" {
               description "1548.44 nm/193.609375 THz 3.125GHz spacing";
             }
             enum "1548.41" {
               description "1548.41 nm/193.612500 THz 3.125/6.25/12.5GHz spacing";
             }
             enum "1548.39" {
               description "1548.39 nm/193.615625 THz 3.125GHz spacing";
             }
             enum "1548.36" {
               description "1548.36 nm/193.618750 THz 3.125/6.25GHz spacing";
             }
             enum "1548.34" {
               description "1548.34 nm/193.621875 THz 3.125GHz spacing";
             }
             enum "1548.31" {
               description "1548.31 nm/193.625000 THz 3.125/6.25/12.5GHz spacing";
             }
             enum "1548.29" {
               description "1548.29 nm/193.628125 THz 3.125GHz spacing";
             }
             enum "1548.26" {
               description "1548.26 nm/193.631250 THz 3.125/6.25GHz spacing";
             }
             enum "1548.24" {
               description "1548.24 nm/193.634375 THz 3.125GHz spacing";
             }
             enum "1548.21" {
               description "1548.21 nm/193.637500 THz 3.125/6.25/12.5GHz spacing";
             }
             enum "1548.19" {
               description "1548.19 nm/193.640625 THz 3.125GHz spacing";
             }
             enum "1548.16" {
               description "1548.16 nm/193.643750 THz 3.125/6.25GHz spacing";
             }
             enum "1548.14" {
               description "1548.14 nm/193.646875 THz 3.125GHz spacing";
             }
             enum "1548.11" {
               description "1548.11 nm/193.650000 THz 3.125/6.25/12.5/50/75GHz spacing";
             }
             enum "1548.09" {
               description "1548.09 nm/193.653125 THz 3.125GHz spacing";
             }
             enum "1548.06" {
               description "1548.06 nm/193.656250 THz 3.125/6.25GHz spacing";
             }
             enum "1548.04" {
               description "1548.04 nm/193.659375 THz 3.125GHz spacing";
             }
             enum "1548.02" {
               description "1548.02 nm/193.662500 THz 3.125/6.25/12.5GHz spacing";
             }
             enum "1547.99" {
               description "1547.99 nm/193.665625 THz 3.125GHz spacing";
             }
             enum "1547.97" {
               description "1547.97 nm/193.668750 THz 3.125/6.25GHz spacing";
             }
             enum "1547.94" {
               description "1547.94 nm/193.671875 THz 3.125GHz spacing";
             }
             enum "1547.92" {
               description "1547.92 nm/193.675000 THz 3.125/6.25/12.5GHz spacing";
             }
             enum "1547.89" {
               description "1547.89 nm/193.678125 THz 3.125GHz spacing";
             }
             enum "1547.87" {
               description "1547.87 nm/193.681250 THz 3.125/6.25GHz spacing";
             }
             enum "1547.84" {
               description "1547.84 nm/193.684375 THz 3.125GHz spacing";
             }
             enum "1547.82" {
               description "1547.82 nm/193.687500 THz 3.125/6.25/12.5GHz spacing";
             }
             enum "1547.79" {
               description "1547.79 nm/193.690625 THz 3.125GHz spacing";
             }
             enum "1547.77" {
               description "1547.77 nm/193.693750 THz 3.125/6.25GHz spacing";
             }
             enum "1547.74" {
               description "1547.74 nm/193.696875 THz 3.125GHz spacing";
             }
             enum "1547.72" {
               description "1547.72 nm/193.700000 THz 3.125/6.25/12.5/100GHz spacing";
             }
             enum "1547.69" {
               description "1547.69 nm/193.703125 THz 3.125GHz spacing";
             }
             enum "1547.67" {
               description "1547.67 nm/193.706250 THz 3.125/6.25GHz spacing";
             }
             enum "1547.64" {
               description "1547.64 nm/193.709375 THz 3.125GHz spacing";
             }
             enum "1547.62" {
               description "1547.62 nm/193.712500 THz 3.125/6.25/12.5GHz spacing";
             }
             enum "1547.59" {
               description "1547.59 nm/193.715625 THz 3.125GHz spacing";
             }
             enum "1547.57" {
               description "1547.57 nm/193.718750 THz 3.125/6.25GHz spacing";
             }
             enum "1547.54" {
               description "1547.54 nm/193.721875 THz 3.125GHz spacing";
             }
             enum "1547.52" {
               description "1547.52 nm/193.725000 THz 3.125/6.25/12.5/75GHz spacing";
             }
             enum "1547.49" {
               description "1547.49 nm/193.728125 THz 3.125GHz spacing";
             }
             enum "1547.47" {
               description "1547.47 nm/193.731250 THz 3.125/6.25GHz spacing";
             }
             enum "1547.44" {
               description "1547.44 nm/193.734375 THz 3.125GHz spacing";
             }
             enum "1547.42" {
               description "1547.42 nm/193.737500 THz 3.125/6.25/12.5GHz spacing";
             }
             enum "1547.39" {
               description "1547.39 nm/193.740625 THz 3.125GHz spacing";
             }
             enum "1547.37" {
               description "1547.37 nm/193.743750 THz 3.125/6.25GHz spacing";
             }
             enum "1547.34" {
               description "1547.34 nm/193.746875 THz 3.125GHz spacing";
             }
             enum "1547.32" {
               description "1547.32 nm/193.750000 THz 3.125/6.25/12.5/50GHz spacing";
             }
             enum "1547.29" {
               description "1547.29 nm/193.753125 THz 3.125GHz spacing";
             }
             enum "1547.27" {
               description "1547.27 nm/193.756250 THz 3.125/6.25GHz spacing";
             }
             enum "1547.24" {
               description "1547.24 nm/193.759375 THz 3.125GHz spacing";
             }
             enum "1547.22" {
               description "1547.22 nm/193.762500 THz 3.125/6.25/12.5GHz spacing";
             }
             enum "1547.19" {
               description "1547.19 nm/193.765625 THz 3.125GHz spacing";
             }
             enum "1547.17" {
               description "1547.17 nm/193.768750 THz 3.125/6.25GHz spacing";
             }
             enum "1547.14" {
               description "1547.14 nm/193.771875 THz 3.125GHz spacing";
             }
             enum "1547.12" {
               description "1547.12 nm/193.775000 THz 3.125/6.25/12.5GHz spacing";
             }
             enum "1547.09" {
               description "1547.09 nm/193.778125 THz 3.125GHz spacing";
             }
             enum "1547.07" {
               description "1547.07 nm/193.781250 THz 3.125/6.25GHz spacing";
             }
             enum "1547.04" {
               description "1547.04 nm/193.784375 THz 3.125GHz spacing";
             }
             enum "1547.02" {
               description "1547.02 nm/193.787500 THz 3.125/6.25/12.5GHz spacing";
             }
             enum "1546.99" {
               description "1546.99 nm/193.790625 THz 3.125GHz spacing";
             }
             enum "1546.97" {
               description "1546.97 nm/193.793750 THz 3.125/6.25GHz spacing";
             }
             enum "1546.94" {
               description "1546.94 nm/193.796875 THz 3.125GHz spacing";
             }
             enum "1546.92" {
               description "1546.92 nm/193.800000 THz 3.125/6.25/12.5/50/75/100GHz spacing";
             }
             enum "1546.89" {
               description "1546.89 nm/193.803125 THz 3.125GHz spacing";
             }
             enum "1546.87" {
               description "1546.87 nm/193.806250 THz 3.125/6.25GHz spacing";
             }
             enum "1546.84" {
               description "1546.84 nm/193.809375 THz 3.125GHz spacing";
             }
             enum "1546.82" {
               description "1546.82 nm/193.812500 THz 3.125/6.25/12.5GHz spacing";
             }
             enum "1546.79" {
               description "1546.79 nm/193.815625 THz 3.125GHz spacing";
             }
             enum "1546.77" {
               description "1546.77 nm/193.818750 THz 3.125/6.25GHz spacing";
             }
             enum "1546.74" {
               description "1546.74 nm/193.821875 THz 3.125GHz spacing";
             }
             enum "1546.72" {
               description "1546.72 nm/193.825000 THz 3.125/6.25/12.5GHz spacing";
             }
             enum "1546.69" {
               description "1546.69 nm/193.828125 THz 3.125GHz spacing";
             }
             enum "1546.67" {
               description "1546.67 nm/193.831250 THz 3.125/6.25GHz spacing";
             }
             enum "1546.64" {
               description "1546.64 nm/193.834375 THz 3.125GHz spacing";
             }
             enum "1546.62" {
               description "1546.62 nm/193.837500 THz 3.125/6.25/12.5GHz spacing";
             }
             enum "1546.59" {
               description "1546.59 nm/193.840625 THz 3.125GHz spacing";
             }
             enum "1546.57" {
               description "1546.57 nm/193.843750 THz 3.125/6.25GHz spacing";
             }
             enum "1546.54" {
               description "1546.54 nm/193.846875 THz 3.125GHz spacing";
             }
             enum "1546.52" {
               description "1546.52 nm/193.850000 THz 3.125/6.25/12.5/50GHz spacing";
             }
             enum "1546.49" {
               description "1546.49 nm/193.853125 THz 3.125GHz spacing";
             }
             enum "1546.47" {
               description "1546.47 nm/193.856250 THz 3.125/6.25GHz spacing";
             }
             enum "1546.44" {
               description "1546.44 nm/193.859375 THz 3.125GHz spacing";
             }
             enum "1546.42" {
               description "1546.42 nm/193.862500 THz 3.125/6.25/12.5GHz spacing";
             }
             enum "1546.39" {
               description "1546.39 nm/193.865625 THz 3.125GHz spacing";
             }
             enum "1546.37" {
               description "1546.37 nm/193.868750 THz 3.125/6.25GHz spacing";
             }
             enum "1546.34" {
               description "1546.34 nm/193.871875 THz 3.125GHz spacing";
             }
             enum "1546.32" {
               description "1546.32 nm/193.875000 THz 3.125/6.25/12.5/75GHz spacing";
             }
             enum "1546.29" {
               description "1546.29 nm/193.878125 THz 3.125GHz spacing";
             }
             enum "1546.27" {
               description "1546.27 nm/193.881250 THz 3.125/6.25GHz spacing";
             }
             enum "1546.24" {
               description "1546.24 nm/193.884375 THz 3.125GHz spacing";
             }
             enum "1546.22" {
               description "1546.22 nm/193.887500 THz 3.125/6.25/12.5GHz spacing";
             }
             enum "1546.19" {
               description "1546.19 nm/193.890625 THz 3.125GHz spacing";
             }
             enum "1546.17" {
               description "1546.17 nm/193.893750 THz 3.125/6.25GHz spacing";
             }
             enum "1546.14" {
               description "1546.14 nm/193.896875 THz 3.125GHz spacing";
             }
             enum "1546.12" {
               description "1546.12 nm/193.900000 THz 3.125/6.25/12.5/100GHz spacing";
             }
             enum "1546.09" {
               description "1546.09 nm/193.903125 THz 3.125GHz spacing";
             }
             enum "1546.07" {
               description "1546.07 nm/193.906250 THz 3.125/6.25GHz spacing";
             }
             enum "1546.04" {
               description "1546.04 nm/193.909375 THz 3.125GHz spacing";
             }
             enum "1546.02" {
               description "1546.02 nm/193.912500 THz 3.125/6.25/12.5GHz spacing";
             }
             enum "1545.99" {
               description "1545.99 nm/193.915625 THz 3.125GHz spacing";
             }
             enum "1545.97" {
               description "1545.97 nm/193.918750 THz 3.125/6.25GHz spacing";
             }
             enum "1545.94" {
               description "1545.94 nm/193.921875 THz 3.125GHz spacing";
             }
             enum "1545.92" {
               description "1545.92 nm/193.925000 THz 3.125/6.25/12.5GHz spacing";
             }
             enum "1545.89" {
               description "1545.89 nm/193.928125 THz 3.125GHz spacing";
             }
             enum "1545.87" {
               description "1545.87 nm/193.931250 THz 3.125/6.25GHz spacing";
             }
             enum "1545.84" {
               description "1545.84 nm/193.934375 THz 3.125GHz spacing";
             }
             enum "1545.82" {
               description "1545.82 nm/193.937500 THz 3.125/6.25/12.5GHz spacing";
             }
             enum "1545.80" {
               description "1545.80 nm/193.940625 THz 3.125GHz spacing";
             }
             enum "1545.77" {
               description "1545.77 nm/193.943750 THz 3.125/6.25GHz spacing";
             }
             enum "1545.75" {
               description "1545.75 nm/193.946875 THz 3.125GHz spacing";
             }
             enum "1545.72" {
               description "1545.72 nm/193.950000 THz 3.125/6.25/12.5/50/75GHz spacing";
             }
             enum "1545.70" {
               description "1545.70 nm/193.953125 THz 3.125GHz spacing";
             }
             enum "1545.67" {
               description "1545.67 nm/193.956250 THz 3.125/6.25GHz spacing";
             }
             enum "1545.65" {
               description "1545.65 nm/193.959375 THz 3.125GHz spacing";
             }
             enum "1545.62" {
               description "1545.62 nm/193.962500 THz 3.125/6.25/12.5GHz spacing";
             }
             enum "1545.60" {
               description "1545.60 nm/193.965625 THz 3.125GHz spacing";
             }
             enum "1545.57" {
               description "1545.57 nm/193.968750 THz 3.125/6.25GHz spacing";
             }
             enum "1545.55" {
               description "1545.55 nm/193.971875 THz 3.125GHz spacing";
             }
             enum "1545.52" {
               description "1545.52 nm/193.975000 THz 3.125/6.25/12.5GHz spacing";
             }
             enum "1545.50" {
               description "1545.50 nm/193.978125 THz 3.125GHz spacing";
             }
             enum "1545.47" {
               description "1545.47 nm/193.981250 THz 3.125/6.25GHz spacing";
             }
             enum "1545.45" {
               description "1545.45 nm/193.984375 THz 3.125GHz spacing";
             }
             enum "1545.42" {
               description "1545.42 nm/193.987500 THz 3.125/6.25/12.5GHz spacing";
             }
             enum "1545.40" {
               description "1545.40 nm/193.990625 THz 3.125GHz spacing";
             }
             enum "1545.37" {
               description "1545.37 nm/193.993750 THz 3.125/6.25GHz spacing";
             }
             enum "1545.35" {
               description "1545.35 nm/193.996875 THz 3.125GHz spacing";
             }
             enum "1545.32" {
               description "1545.32 nm/194.000000 THz 3.125/6.25/12.5/100GHz spacing";
             }
             enum "1545.30" {
               description "1545.30 nm/194.003125 THz 3.125GHz spacing";
             }
             enum "1545.27" {
               description "1545.27 nm/194.006250 THz 3.125/6.25GHz spacing";
             }
             enum "1545.25" {
               description "1545.25 nm/194.009375 THz 3.125GHz spacing";
             }
             enum "1545.22" {
               description "1545.22 nm/194.012500 THz 3.125/6.25/12.5GHz spacing";
             }
             enum "1545.20" {
               description "1545.20 nm/194.015625 THz 3.125GHz spacing";
             }
             enum "1545.17" {
               description "1545.17 nm/194.018750 THz 3.125/6.25GHz spacing";
             }
             enum "1545.15" {
               description "1545.15 nm/194.021875 THz 3.125GHz spacing";
             }
             enum "1545.12" {
               description "1545.12 nm/194.025000 THz 3.125/6.25/12.5/75GHz spacing";
             }
             enum "1545.10" {
               description "1545.10 nm/194.028125 THz 3.125GHz spacing";
             }
             enum "1545.07" {
               description "1545.07 nm/194.031250 THz 3.125/6.25GHz spacing";
             }
             enum "1545.05" {
               description "1545.05 nm/194.034375 THz 3.125GHz spacing";
             }
             enum "1545.02" {
               description "1545.02 nm/194.037500 THz 3.125/6.25/12.5GHz spacing";
             }
             enum "1545.00" {
               description "1545.00 nm/194.040625 THz 3.125GHz spacing";
             }
             enum "1544.97" {
               description "1544.97 nm/194.043750 THz 3.125/6.25GHz spacing";
             }
             enum "1544.95" {
               description "1544.95 nm/194.046875 THz 3.125GHz spacing";
             }
             enum "1544.92" {
               description "1544.92 nm/194.050000 THz 3.125/6.25/12.5/50GHz spacing";
             }
             enum "1544.90" {
               description "1544.90 nm/194.053125 THz 3.125GHz spacing";
             }
             enum "1544.87" {
               description "1544.87 nm/194.056250 THz 3.125/6.25GHz spacing";
             }
             enum "1544.85" {
               description "1544.85 nm/194.059375 THz 3.125GHz spacing";
             }
             enum "1544.82" {
               description "1544.82 nm/194.062500 THz 3.125/6.25/12.5GHz spacing";
             }
             enum "1544.80" {
               description "1544.80 nm/194.065625 THz 3.125GHz spacing";
             }
             enum "1544.77" {
               description "1544.77 nm/194.068750 THz 3.125/6.25GHz spacing";
             }
             enum "1544.75" {
               description "1544.75 nm/194.071875 THz 3.125GHz spacing";
             }
             enum "1544.72" {
               description "1544.72 nm/194.075000 THz 3.125/6.25/12.5GHz spacing";
             }
             enum "1544.70" {
               description "1544.70 nm/194.078125 THz 3.125GHz spacing";
             }
             enum "1544.68" {
               description "1544.68 nm/194.081250 THz 3.125/6.25GHz spacing";
             }
             enum "1544.65" {
               description "1544.65 nm/194.084375 THz 3.125GHz spacing";
             }
             enum "1544.63" {
               description "1544.63 nm/194.087500 THz 3.125/6.25/12.5GHz spacing";
             }
             enum "1544.60" {
               description "1544.60 nm/194.090625 THz 3.125GHz spacing";
             }
             enum "1544.58" {
               description "1544.58 nm/194.093750 THz 3.125/6.25GHz spacing";
             }
             enum "1544.55" {
               description "1544.55 nm/194.096875 THz 3.125GHz spacing";
             }
             enum "1544.53" {
               description "1544.53 nm/194.100000 THz 3.125/6.25/12.5/50/75/100GHz spacing";
             }
             enum "1544.50" {
               description "1544.50 nm/194.103125 THz 3.125GHz spacing";
             }
             enum "1544.48" {
               description "1544.48 nm/194.106250 THz 3.125/6.25GHz spacing";
             }
             enum "1544.45" {
               description "1544.45 nm/194.109375 THz 3.125GHz spacing";
             }
             enum "1544.43" {
               description "1544.43 nm/194.112500 THz 3.125/6.25/12.5GHz spacing";
             }
             enum "1544.40" {
               description "1544.40 nm/194.115625 THz 3.125GHz spacing";
             }
             enum "1544.38" {
               description "1544.38 nm/194.118750 THz 3.125/6.25GHz spacing";
             }
             enum "1544.35" {
               description "1544.35 nm/194.121875 THz 3.125GHz spacing";
             }
             enum "1544.33" {
               description "1544.33 nm/194.125000 THz 3.125/6.25/12.5GHz spacing";
             }
             enum "1544.30" {
               description "1544.30 nm/194.128125 THz 3.125GHz spacing";
             }
             enum "1544.28" {
               description "1544.28 nm/194.131250 THz 3.125/6.25GHz spacing";
             }
             enum "1544.25" {
               description "1544.25 nm/194.134375 THz 3.125GHz spacing";
             }
             enum "1544.23" {
               description "1544.23 nm/194.137500 THz 3.125/6.25/12.5GHz spacing";
             }
             enum "1544.20" {
               description "1544.20 nm/194.140625 THz 3.125GHz spacing";
             }
             enum "1544.18" {
               description "1544.18 nm/194.143750 THz 3.125/6.25GHz spacing";
             }
             enum "1544.15" {
               description "1544.15 nm/194.146875 THz 3.125GHz spacing";
             }
             enum "1544.13" {
               description "1544.13 nm/194.150000 THz 3.125/6.25/12.5/50GHz spacing";
             }
             enum "1544.10" {
               description "1544.10 nm/194.153125 THz 3.125GHz spacing";
             }
             enum "1544.08" {
               description "1544.08 nm/194.156250 THz 3.125/6.25GHz spacing";
             }
             enum "1544.05" {
               description "1544.05 nm/194.159375 THz 3.125GHz spacing";
             }
             enum "1544.03" {
               description "1544.03 nm/194.162500 THz 3.125/6.25/12.5GHz spacing";
             }
             enum "1544.00" {
               description "1544.00 nm/194.165625 THz 3.125GHz spacing";
             }
             enum "1543.98" {
               description "1543.98 nm/194.168750 THz 3.125/6.25GHz spacing";
             }
             enum "1543.95" {
               description "1543.95 nm/194.171875 THz 3.125GHz spacing";
             }
             enum "1543.93" {
               description "1543.93 nm/194.175000 THz 3.125/6.25/12.5/75GHz spacing";
             }
             enum "1543.90" {
               description "1543.90 nm/194.178125 THz 3.125GHz spacing";
             }
             enum "1543.88" {
               description "1543.88 nm/194.181250 THz 3.125/6.25GHz spacing";
             }
             enum "1543.85" {
               description "1543.85 nm/194.184375 THz 3.125GHz spacing";
             }
             enum "1543.83" {
               description "1543.83 nm/194.187500 THz 3.125/6.25/12.5GHz spacing";
             }
             enum "1543.81" {
               description "1543.81 nm/194.190625 THz 3.125GHz spacing";
             }
             enum "1543.78" {
               description "1543.78 nm/194.193750 THz 3.125/6.25GHz spacing";
             }
             enum "1543.76" {
               description "1543.76 nm/194.196875 THz 3.125GHz spacing";
             }
             enum "1543.73" {
               description "1543.73 nm/194.200000 THz 3.125/6.25/12.5/100GHz spacing";
             }
             enum "1543.71" {
               description "1543.71 nm/194.203125 THz 3.125GHz spacing";
             }
             enum "1543.68" {
               description "1543.68 nm/194.206250 THz 3.125/6.25GHz spacing";
             }
             enum "1543.66" {
               description "1543.66 nm/194.209375 THz 3.125GHz spacing";
             }
             enum "1543.63" {
               description "1543.63 nm/194.212500 THz 3.125/6.25/12.5GHz spacing";
             }
             enum "1543.61" {
               description "1543.61 nm/194.215625 THz 3.125GHz spacing";
             }
             enum "1543.58" {
               description "1543.58 nm/194.218750 THz 3.125/6.25GHz spacing";
             }
             enum "1543.56" {
               description "1543.56 nm/194.221875 THz 3.125GHz spacing";
             }
             enum "1543.53" {
               description "1543.53 nm/194.225000 THz 3.125/6.25/12.5GHz spacing";
             }
             enum "1543.51" {
               description "1543.51 nm/194.228125 THz 3.125GHz spacing";
             }
             enum "1543.48" {
               description "1543.48 nm/194.231250 THz 3.125/6.25GHz spacing";
             }
             enum "1543.46" {
               description "1543.46 nm/194.234375 THz 3.125GHz spacing";
             }
             enum "1543.43" {
               description "1543.43 nm/194.237500 THz 3.125/6.25/12.5GHz spacing";
             }
             enum "1543.41" {
               description "1543.41 nm/194.240625 THz 3.125GHz spacing";
             }
             enum "1543.38" {
               description "1543.38 nm/194.243750 THz 3.125/6.25GHz spacing";
             }
             enum "1543.36" {
               description "1543.36 nm/194.246875 THz 3.125GHz spacing";
             }
             enum "1543.33" {
               description "1543.33 nm/194.250000 THz 3.125/6.25/12.5/50/75GHz spacing";
             }
             enum "1543.31" {
               description "1543.31 nm/194.253125 THz 3.125GHz spacing";
             }
             enum "1543.28" {
               description "1543.28 nm/194.256250 THz 3.125/6.25GHz spacing";
             }
             enum "1543.26" {
               description "1543.26 nm/194.259375 THz 3.125GHz spacing";
             }
             enum "1543.23" {
               description "1543.23 nm/194.262500 THz 3.125/6.25/12.5GHz spacing";
             }
             enum "1543.21" {
               description "1543.21 nm/194.265625 THz 3.125GHz spacing";
             }
             enum "1543.18" {
               description "1543.18 nm/194.268750 THz 3.125/6.25GHz spacing";
             }
             enum "1543.16" {
               description "1543.16 nm/194.271875 THz 3.125GHz spacing";
             }
             enum "1543.13" {
               description "1543.13 nm/194.275000 THz 3.125/6.25/12.5GHz spacing";
             }
             enum "1543.11" {
               description "1543.11 nm/194.278125 THz 3.125GHz spacing";
             }
             enum "1543.08" {
               description "1543.08 nm/194.281250 THz 3.125/6.25GHz spacing";
             }
             enum "1543.06" {
               description "1543.06 nm/194.284375 THz 3.125GHz spacing";
             }
             enum "1543.04" {
               description "1543.04 nm/194.287500 THz 3.125/6.25/12.5GHz spacing";
             }
             enum "1543.01" {
               description "1543.01 nm/194.290625 THz 3.125GHz spacing";
             }
             enum "1542.99" {
               description "1542.99 nm/194.293750 THz 3.125/6.25GHz spacing";
             }
             enum "1542.96" {
               description "1542.96 nm/194.296875 THz 3.125GHz spacing";
             }
             enum "1542.94" {
               description "1542.94 nm/194.300000 THz 3.125/6.25/12.5/100GHz spacing";
             }
             enum "1542.91" {
               description "1542.91 nm/194.303125 THz 3.125GHz spacing";
             }
             enum "1542.89" {
               description "1542.89 nm/194.306250 THz 3.125/6.25GHz spacing";
             }
             enum "1542.86" {
               description "1542.86 nm/194.309375 THz 3.125GHz spacing";
             }
             enum "1542.84" {
               description "1542.84 nm/194.312500 THz 3.125/6.25/12.5GHz spacing";
             }
             enum "1542.81" {
               description "1542.81 nm/194.315625 THz 3.125GHz spacing";
             }
             enum "1542.79" {
               description "1542.79 nm/194.318750 THz 3.125/6.25GHz spacing";
             }
             enum "1542.76" {
               description "1542.76 nm/194.321875 THz 3.125GHz spacing";
             }
             enum "1542.74" {
               description "1542.74 nm/194.325000 THz 3.125/6.25/12.5/75GHz spacing";
             }
             enum "1542.71" {
               description "1542.71 nm/194.328125 THz 3.125GHz spacing";
             }
             enum "1542.69" {
               description "1542.69 nm/194.331250 THz 3.125/6.25GHz spacing";
             }
             enum "1542.66" {
               description "1542.66 nm/194.334375 THz 3.125GHz spacing";
             }
             enum "1542.64" {
               description "1542.64 nm/194.337500 THz 3.125/6.25/12.5GHz spacing";
             }
             enum "1542.61" {
               description "1542.61 nm/194.340625 THz 3.125GHz spacing";
             }
             enum "1542.59" {
               description "1542.59 nm/194.343750 THz 3.125/6.25GHz spacing";
             }
             enum "1542.56" {
               description "1542.56 nm/194.346875 THz 3.125GHz spacing";
             }
             enum "1542.54" {
               description "1542.54 nm/194.350000 THz 3.125/6.25/12.5/50GHz spacing";
             }
             enum "1542.51" {
               description "1542.51 nm/194.353125 THz 3.125GHz spacing";
             }
             enum "1542.49" {
               description "1542.49 nm/194.356250 THz 3.125/6.25GHz spacing";
             }
             enum "1542.46" {
               description "1542.46 nm/194.359375 THz 3.125GHz spacing";
             }
             enum "1542.44" {
               description "1542.44 nm/194.362500 THz 3.125/6.25/12.5GHz spacing";
             }
             enum "1542.42" {
               description "1542.42 nm/194.365625 THz 3.125GHz spacing";
             }
             enum "1542.39" {
               description "1542.39 nm/194.368750 THz 3.125/6.25GHz spacing";
             }
             enum "1542.37" {
               description "1542.37 nm/194.371875 THz 3.125GHz spacing";
             }
             enum "1542.34" {
               description "1542.34 nm/194.375000 THz 3.125/6.25/12.5GHz spacing";
             }
             enum "1542.32" {
               description "1542.32 nm/194.378125 THz 3.125GHz spacing";
             }
             enum "1542.29" {
               description "1542.29 nm/194.381250 THz 3.125/6.25GHz spacing";
             }
             enum "1542.27" {
               description "1542.27 nm/194.384375 THz 3.125GHz spacing";
             }
             enum "1542.24" {
               description "1542.24 nm/194.387500 THz 3.125/6.25/12.5GHz spacing";
             }
             enum "1542.22" {
               description "1542.22 nm/194.390625 THz 3.125GHz spacing";
             }
             enum "1542.19" {
               description "1542.19 nm/194.393750 THz 3.125/6.25GHz spacing";
             }
             enum "1542.17" {
               description "1542.17 nm/194.396875 THz 3.125GHz spacing";
             }
             enum "1542.14" {
               description "1542.14 nm/194.400000 THz 3.125/6.25/12.5/50/75/100GHz spacing";
             }
             enum "1542.12" {
               description "1542.12 nm/194.403125 THz 3.125GHz spacing";
             }
             enum "1542.09" {
               description "1542.09 nm/194.406250 THz 3.125/6.25GHz spacing";
             }
             enum "1542.07" {
               description "1542.07 nm/194.409375 THz 3.125GHz spacing";
             }
             enum "1542.04" {
               description "1542.04 nm/194.412500 THz 3.125/6.25/12.5GHz spacing";
             }
             enum "1542.02" {
               description "1542.02 nm/194.415625 THz 3.125GHz spacing";
             }
             enum "1541.99" {
               description "1541.99 nm/194.418750 THz 3.125/6.25GHz spacing";
             }
             enum "1541.97" {
               description "1541.97 nm/194.421875 THz 3.125GHz spacing";
             }
             enum "1541.94" {
               description "1541.94 nm/194.425000 THz 3.125/6.25/12.5GHz spacing";
             }
             enum "1541.92" {
               description "1541.92 nm/194.428125 THz 3.125GHz spacing";
             }
             enum "1541.89" {
               description "1541.89 nm/194.431250 THz 3.125/6.25GHz spacing";
             }
             enum "1541.87" {
               description "1541.87 nm/194.434375 THz 3.125GHz spacing";
             }
             enum "1541.84" {
               description "1541.84 nm/194.437500 THz 3.125/6.25/12.5GHz spacing";
             }
             enum "1541.82" {
               description "1541.82 nm/194.440625 THz 3.125GHz spacing";
             }
             enum "1541.80" {
               description "1541.80 nm/194.443750 THz 3.125/6.25GHz spacing";
             }
             enum "1541.77" {
               description "1541.77 nm/194.446875 THz 3.125GHz spacing";
             }
             enum "1541.75" {
               description "1541.75 nm/194.450000 THz 3.125/6.25/12.5/50GHz spacing";
             }
             enum "1541.72" {
               description "1541.72 nm/194.453125 THz 3.125GHz spacing";
             }
             enum "1541.70" {
               description "1541.70 nm/194.456250 THz 3.125/6.25GHz spacing";
             }
             enum "1541.67" {
               description "1541.67 nm/194.459375 THz 3.125GHz spacing";
             }
             enum "1541.65" {
               description "1541.65 nm/194.462500 THz 3.125/6.25/12.5GHz spacing";
             }
             enum "1541.62" {
               description "1541.62 nm/194.465625 THz 3.125GHz spacing";
             }
             enum "1541.60" {
               description "1541.60 nm/194.468750 THz 3.125/6.25GHz spacing";
             }
             enum "1541.57" {
               description "1541.57 nm/194.471875 THz 3.125GHz spacing";
             }
             enum "1541.55" {
               description "1541.55 nm/194.475000 THz 3.125/6.25/12.5/75GHz spacing";
             }
             enum "1541.52" {
               description "1541.52 nm/194.478125 THz 3.125GHz spacing";
             }
             enum "1541.50" {
               description "1541.50 nm/194.481250 THz 3.125/6.25GHz spacing";
             }
             enum "1541.47" {
               description "1541.47 nm/194.484375 THz 3.125GHz spacing";
             }
             enum "1541.45" {
               description "1541.45 nm/194.487500 THz 3.125/6.25/12.5GHz spacing";
             }
             enum "1541.42" {
               description "1541.42 nm/194.490625 THz 3.125GHz spacing";
             }
             enum "1541.40" {
               description "1541.40 nm/194.493750 THz 3.125/6.25GHz spacing";
             }
             enum "1541.37" {
               description "1541.37 nm/194.496875 THz 3.125GHz spacing";
             }
             enum "1541.35" {
               description "1541.35 nm/194.500000 THz 3.125/6.25/12.5/100GHz spacing";
             }
             enum "1541.32" {
               description "1541.32 nm/194.503125 THz 3.125GHz spacing";
             }
             enum "1541.30" {
               description "1541.30 nm/194.506250 THz 3.125/6.25GHz spacing";
             }
             enum "1541.28" {
               description "1541.28 nm/194.509375 THz 3.125GHz spacing";
             }
             enum "1541.25" {
               description "1541.25 nm/194.512500 THz 3.125/6.25/12.5GHz spacing";
             }
             enum "1541.23" {
               description "1541.23 nm/194.515625 THz 3.125GHz spacing";
             }
             enum "1541.20" {
               description "1541.20 nm/194.518750 THz 3.125/6.25GHz spacing";
             }
             enum "1541.18" {
               description "1541.18 nm/194.521875 THz 3.125GHz spacing";
             }
             enum "1541.15" {
               description "1541.15 nm/194.525000 THz 3.125/6.25/12.5GHz spacing";
             }
             enum "1541.13" {
               description "1541.13 nm/194.528125 THz 3.125GHz spacing";
             }
             enum "1541.10" {
               description "1541.10 nm/194.531250 THz 3.125/6.25GHz spacing";
             }
             enum "1541.08" {
               description "1541.08 nm/194.534375 THz 3.125GHz spacing";
             }
             enum "1541.05" {
               description "1541.05 nm/194.537500 THz 3.125/6.25/12.5GHz spacing";
             }
             enum "1541.03" {
               description "1541.03 nm/194.540625 THz 3.125GHz spacing";
             }
             enum "1541.00" {
               description "1541.00 nm/194.543750 THz 3.125/6.25GHz spacing";
             }
             enum "1540.98" {
               description "1540.98 nm/194.546875 THz 3.125GHz spacing";
             }
             enum "1540.95" {
               description "1540.95 nm/194.550000 THz 3.125/6.25/12.5/50/75GHz spacing";
             }
             enum "1540.93" {
               description "1540.93 nm/194.553125 THz 3.125GHz spacing";
             }
             enum "1540.90" {
               description "1540.90 nm/194.556250 THz 3.125/6.25GHz spacing";
             }
             enum "1540.88" {
               description "1540.88 nm/194.559375 THz 3.125GHz spacing";
             }
             enum "1540.85" {
               description "1540.85 nm/194.562500 THz 3.125/6.25/12.5GHz spacing";
             }
             enum "1540.83" {
               description "1540.83 nm/194.565625 THz 3.125GHz spacing";
             }
             enum "1540.80" {
               description "1540.80 nm/194.568750 THz 3.125/6.25GHz spacing";
             }
             enum "1540.78" {
               description "1540.78 nm/194.571875 THz 3.125GHz spacing";
             }
             enum "1540.76" {
               description "1540.76 nm/194.575000 THz 3.125/6.25/12.5GHz spacing";
             }
             enum "1540.73" {
               description "1540.73 nm/194.578125 THz 3.125GHz spacing";
             }
             enum "1540.71" {
               description "1540.71 nm/194.581250 THz 3.125/6.25GHz spacing";
             }
             enum "1540.68" {
               description "1540.68 nm/194.584375 THz 3.125GHz spacing";
             }
             enum "1540.66" {
               description "1540.66 nm/194.587500 THz 3.125/6.25/12.5GHz spacing";
             }
             enum "1540.63" {
               description "1540.63 nm/194.590625 THz 3.125GHz spacing";
             }
             enum "1540.61" {
               description "1540.61 nm/194.593750 THz 3.125/6.25GHz spacing";
             }
             enum "1540.58" {
               description "1540.58 nm/194.596875 THz 3.125GHz spacing";
             }
             enum "1540.56" {
               description "1540.56 nm/194.600000 THz 3.125/6.25/12.5/100GHz spacing";
             }
             enum "1540.53" {
               description "1540.53 nm/194.603125 THz 3.125GHz spacing";
             }
             enum "1540.51" {
               description "1540.51 nm/194.606250 THz 3.125/6.25GHz spacing";
             }
             enum "1540.48" {
               description "1540.48 nm/194.609375 THz 3.125GHz spacing";
             }
             enum "1540.46" {
               description "1540.46 nm/194.612500 THz 3.125/6.25/12.5GHz spacing";
             }
             enum "1540.43" {
               description "1540.43 nm/194.615625 THz 3.125GHz spacing";
             }
             enum "1540.41" {
               description "1540.41 nm/194.618750 THz 3.125/6.25GHz spacing";
             }
             enum "1540.38" {
               description "1540.38 nm/194.621875 THz 3.125GHz spacing";
             }
             enum "1540.36" {
               description "1540.36 nm/194.625000 THz 3.125/6.25/12.5/75GHz spacing";
             }
             enum "1540.33" {
               description "1540.33 nm/194.628125 THz 3.125GHz spacing";
             }
             enum "1540.31" {
               description "1540.31 nm/194.631250 THz 3.125/6.25GHz spacing";
             }
             enum "1540.29" {
               description "1540.29 nm/194.634375 THz 3.125GHz spacing";
             }
             enum "1540.26" {
               description "1540.26 nm/194.637500 THz 3.125/6.25/12.5GHz spacing";
             }
             enum "1540.24" {
               description "1540.24 nm/194.640625 THz 3.125GHz spacing";
             }
             enum "1540.21" {
               description "1540.21 nm/194.643750 THz 3.125/6.25GHz spacing";
             }
             enum "1540.19" {
               description "1540.19 nm/194.646875 THz 3.125GHz spacing";
             }
             enum "1540.16" {
               description "1540.16 nm/194.650000 THz 3.125/6.25/12.5/50GHz spacing";
             }
             enum "1540.14" {
               description "1540.14 nm/194.653125 THz 3.125GHz spacing";
             }
             enum "1540.11" {
               description "1540.11 nm/194.656250 THz 3.125/6.25GHz spacing";
             }
             enum "1540.09" {
               description "1540.09 nm/194.659375 THz 3.125GHz spacing";
             }
             enum "1540.06" {
               description "1540.06 nm/194.662500 THz 3.125/6.25/12.5GHz spacing";
             }
             enum "1540.04" {
               description "1540.04 nm/194.665625 THz 3.125GHz spacing";
             }
             enum "1540.01" {
               description "1540.01 nm/194.668750 THz 3.125/6.25GHz spacing";
             }
             enum "1539.99" {
               description "1539.99 nm/194.671875 THz 3.125GHz spacing";
             }
             enum "1539.96" {
               description "1539.96 nm/194.675000 THz 3.125/6.25/12.5/75GHz spacing";
             }
             enum "1539.94" {
               description "1539.94 nm/194.678125 THz 3.125GHz spacing";
             }
             enum "1539.91" {
               description "1539.91 nm/194.681250 THz 3.125/6.25GHz spacing";
             }
             enum "1539.89" {
               description "1539.89 nm/194.684375 THz 3.125GHz spacing";
             }
             enum "1539.86" {
               description "1539.86 nm/194.687500 THz 3.125/6.25/12.5GHz spacing";
             }
             enum "1539.84" {
               description "1539.84 nm/194.690625 THz 3.125GHz spacing";
             }
             enum "1539.82" {
               description "1539.82 nm/194.693750 THz 3.125/6.25GHz spacing";
             }
             enum "1539.79" {
               description "1539.79 nm/194.696875 THz 3.125GHz spacing";
             }
             enum "1539.77" {
               description "1539.77 nm/194.700000 THz 3.125/6.25/12.5/50/75/100GHz spacing";
             }
             enum "1539.74" {
               description "1539.74 nm/194.703125 THz 3.125GHz spacing";
             }
             enum "1539.72" {
               description "1539.72 nm/194.706250 THz 3.125/6.25GHz spacing";
             }
             enum "1539.69" {
               description "1539.69 nm/194.709375 THz 3.125GHz spacing";
             }
             enum "1539.67" {
               description "1539.67 nm/194.712500 THz 3.125/6.25/12.5GHz spacing";
             }
             enum "1539.64" {
               description "1539.64 nm/194.715625 THz 3.125GHz spacing";
             }
             enum "1539.62" {
               description "1539.62 nm/194.718750 THz 3.125/6.25GHz spacing";
             }
             enum "1539.59" {
               description "1539.59 nm/194.721875 THz 3.125GHz spacing";
             }
             enum "1539.57" {
               description "1539.57 nm/194.725000 THz 3.125/6.25/12.5GHz spacing";
             }
             enum "1539.54" {
               description "1539.54 nm/194.728125 THz 3.125GHz spacing";
             }
             enum "1539.52" {
               description "1539.52 nm/194.731250 THz 3.125/6.25GHz spacing";
             }
             enum "1539.49" {
               description "1539.49 nm/194.734375 THz 3.125GHz spacing";
             }
             enum "1539.47" {
               description "1539.47 nm/194.737500 THz 3.125/6.25/12.5GHz spacing";
             }
             enum "1539.44" {
               description "1539.44 nm/194.740625 THz 3.125GHz spacing";
             }
             enum "1539.42" {
               description "1539.42 nm/194.743750 THz 3.125/6.25GHz spacing";
             }
             enum "1539.40" {
               description "1539.40 nm/194.746875 THz 3.125GHz spacing";
             }
             enum "1539.37" {
               description "1539.37 nm/194.750000 THz 3.125/6.25/12.5/50GHz spacing";
             }
             enum "1539.35" {
               description "1539.35 nm/194.753125 THz 3.125GHz spacing";
             }
             enum "1539.32" {
               description "1539.32 nm/194.756250 THz 3.125/6.25GHz spacing";
             }
             enum "1539.30" {
               description "1539.30 nm/194.759375 THz 3.125GHz spacing";
             }
             enum "1539.27" {
               description "1539.27 nm/194.762500 THz 3.125/6.25/12.5GHz spacing";
             }
             enum "1539.25" {
               description "1539.25 nm/194.765625 THz 3.125GHz spacing";
             }
             enum "1539.22" {
               description "1539.22 nm/194.768750 THz 3.125/6.25GHz spacing";
             }
             enum "1539.20" {
               description "1539.20 nm/194.771875 THz 3.125GHz spacing";
             }
             enum "1539.17" {
               description "1539.17 nm/194.775000 THz 3.125/6.25/12.5/75GHz spacing";
             }
             enum "1539.15" {
               description "1539.15 nm/194.778125 THz 3.125GHz spacing";
             }
             enum "1539.12" {
               description "1539.12 nm/194.781250 THz 3.125/6.25GHz spacing";
             }
             enum "1539.10" {
               description "1539.10 nm/194.784375 THz 3.125GHz spacing";
             }
             enum "1539.07" {
               description "1539.07 nm/194.787500 THz 3.125/6.25/12.5GHz spacing";
             }
             enum "1539.05" {
               description "1539.05 nm/194.790625 THz 3.125GHz spacing";
             }
             enum "1539.03" {
               description "1539.03 nm/194.793750 THz 3.125/6.25GHz spacing";
             }
             enum "1539.00" {
               description "1539.00 nm/194.796875 THz 3.125GHz spacing";
             }
             enum "1538.98" {
               description "1538.98 nm/194.800000 THz 3.125/6.25/12.5/100GHz spacing";
             }
             enum "1538.95" {
               description "1538.95 nm/194.803125 THz 3.125GHz spacing";
             }
             enum "1538.93" {
               description "1538.93 nm/194.806250 THz 3.125/6.25GHz spacing";
             }
             enum "1538.90" {
               description "1538.90 nm/194.809375 THz 3.125GHz spacing";
             }
             enum "1538.88" {
               description "1538.88 nm/194.812500 THz 3.125/6.25/12.5GHz spacing";
             }
             enum "1538.85" {
               description "1538.85 nm/194.815625 THz 3.125GHz spacing";
             }
             enum "1538.83" {
               description "1538.83 nm/194.818750 THz 3.125/6.25GHz spacing";
             }
             enum "1538.80" {
               description "1538.80 nm/194.821875 THz 3.125GHz spacing";
             }
             enum "1538.78" {
               description "1538.78 nm/194.825000 THz 3.125/6.25/12.5GHz spacing";
             }
             enum "1538.75" {
               description "1538.75 nm/194.828125 THz 3.125GHz spacing";
             }
             enum "1538.73" {
               description "1538.73 nm/194.831250 THz 3.125/6.25GHz spacing";
             }
             enum "1538.70" {
               description "1538.70 nm/194.834375 THz 3.125GHz spacing";
             }
             enum "1538.68" {
               description "1538.68 nm/194.837500 THz 3.125/6.25/12.5GHz spacing";
             }
             enum "1538.65" {
               description "1538.65 nm/194.840625 THz 3.125GHz spacing";
             }
             enum "1538.63" {
               description "1538.63 nm/194.843750 THz 3.125/6.25GHz spacing";
             }
             enum "1538.61" {
               description "1538.61 nm/194.846875 THz 3.125GHz spacing";
             }
             enum "1538.58" {
               description "1538.58 nm/194.850000 THz 3.125/6.25/12.5/50/75GHz spacing";
             }
             enum "1538.56" {
               description "1538.56 nm/194.853125 THz 3.125GHz spacing";
             }
             enum "1538.53" {
               description "1538.53 nm/194.856250 THz 3.125/6.25GHz spacing";
             }
             enum "1538.51" {
               description "1538.51 nm/194.859375 THz 3.125GHz spacing";
             }
             enum "1538.48" {
               description "1538.48 nm/194.862500 THz 3.125/6.25/12.5GHz spacing";
             }
             enum "1538.46" {
               description "1538.46 nm/194.865625 THz 3.125GHz spacing";
             }
             enum "1538.43" {
               description "1538.43 nm/194.868750 THz 3.125/6.25GHz spacing";
             }
             enum "1538.41" {
               description "1538.41 nm/194.871875 THz 3.125GHz spacing";
             }
             enum "1538.38" {
               description "1538.38 nm/194.875000 THz 3.125/6.25/12.5GHz spacing";
             }
             enum "1538.36" {
               description "1538.36 nm/194.878125 THz 3.125GHz spacing";
             }
             enum "1538.33" {
               description "1538.33 nm/194.881250 THz 3.125/6.25GHz spacing";
             }
             enum "1538.31" {
               description "1538.31 nm/194.884375 THz 3.125GHz spacing";
             }
             enum "1538.28" {
               description "1538.28 nm/194.887500 THz 3.125/6.25/12.5GHz spacing";
             }
             enum "1538.26" {
               description "1538.26 nm/194.890625 THz 3.125GHz spacing";
             }
             enum "1538.24" {
               description "1538.24 nm/194.893750 THz 3.125/6.25GHz spacing";
             }
             enum "1538.21" {
               description "1538.21 nm/194.896875 THz 3.125GHz spacing";
             }
             enum "1538.19" {
               description "1538.19 nm/194.900000 THz 3.125/6.25/12.5/100GHz spacing";
             }
             enum "1538.16" {
               description "1538.16 nm/194.903125 THz 3.125GHz spacing";
             }
             enum "1538.14" {
               description "1538.14 nm/194.906250 THz 3.125/6.25GHz spacing";
             }
             enum "1538.11" {
               description "1538.11 nm/194.909375 THz 3.125GHz spacing";
             }
             enum "1538.09" {
               description "1538.09 nm/194.912500 THz 3.125/6.25/12.5GHz spacing";
             }
             enum "1538.06" {
               description "1538.06 nm/194.915625 THz 3.125GHz spacing";
             }
             enum "1538.04" {
               description "1538.04 nm/194.918750 THz 3.125/6.25GHz spacing";
             }
             enum "1538.01" {
               description "1538.01 nm/194.921875 THz 3.125GHz spacing";
             }
             enum "1537.99" {
               description "1537.99 nm/194.925000 THz 3.125/6.25/12.5/75GHz spacing";
             }
             enum "1537.96" {
               description "1537.96 nm/194.928125 THz 3.125GHz spacing";
             }
             enum "1537.94" {
               description "1537.94 nm/194.931250 THz 3.125/6.25GHz spacing";
             }
             enum "1537.91" {
               description "1537.91 nm/194.934375 THz 3.125GHz spacing";
             }
             enum "1537.89" {
               description "1537.89 nm/194.937500 THz 3.125/6.25/12.5GHz spacing";
             }
             enum "1537.87" {
               description "1537.87 nm/194.940625 THz 3.125GHz spacing";
             }
             enum "1537.84" {
               description "1537.84 nm/194.943750 THz 3.125/6.25GHz spacing";
             }
             enum "1537.82" {
               description "1537.82 nm/194.946875 THz 3.125GHz spacing";
             }
             enum "1537.79" {
               description "1537.79 nm/194.950000 THz 3.125/6.25/12.5/50GHz spacing";
             }
             enum "1537.77" {
               description "1537.77 nm/194.953125 THz 3.125GHz spacing";
             }
             enum "1537.74" {
               description "1537.74 nm/194.956250 THz 3.125/6.25GHz spacing";
             }
             enum "1537.72" {
               description "1537.72 nm/194.959375 THz 3.125GHz spacing";
             }
             enum "1537.69" {
               description "1537.69 nm/194.962500 THz 3.125/6.25/12.5GHz spacing";
             }
             enum "1537.67" {
               description "1537.67 nm/194.965625 THz 3.125GHz spacing";
             }
             enum "1537.64" {
               description "1537.64 nm/194.968750 THz 3.125/6.25GHz spacing";
             }
             enum "1537.62" {
               description "1537.62 nm/194.971875 THz 3.125GHz spacing";
             }
             enum "1537.59" {
               description "1537.59 nm/194.975000 THz 3.125/6.25/12.5GHz spacing";
             }
             enum "1537.57" {
               description "1537.57 nm/194.978125 THz 3.125GHz spacing";
             }
             enum "1537.55" {
               description "1537.55 nm/194.981250 THz 3.125/6.25GHz spacing";
             }
             enum "1537.52" {
               description "1537.52 nm/194.984375 THz 3.125GHz spacing";
             }
             enum "1537.50" {
               description "1537.50 nm/194.987500 THz 3.125/6.25/12.5GHz spacing";
             }
             enum "1537.47" {
               description "1537.47 nm/194.990625 THz 3.125GHz spacing";
             }
             enum "1537.45" {
               description "1537.45 nm/194.993750 THz 3.125/6.25GHz spacing";
             }
             enum "1537.42" {
               description "1537.42 nm/194.996875 THz 3.125GHz spacing";
             }
             enum "1537.40" {
               description "1537.40 nm/195.000000 THz 3.125/6.25/12.5/50/75/100GHz spacing";
             }
             enum "1537.37" {
               description "1537.37 nm/195.003125 THz 3.125GHz spacing";
             }
             enum "1537.35" {
               description "1537.35 nm/195.006250 THz 3.125/6.25GHz spacing";
             }
             enum "1537.32" {
               description "1537.32 nm/195.009375 THz 3.125GHz spacing";
             }
             enum "1537.30" {
               description "1537.30 nm/195.012500 THz 3.125/6.25/12.5GHz spacing";
             }
             enum "1537.27" {
               description "1537.27 nm/195.015625 THz 3.125GHz spacing";
             }
             enum "1537.25" {
               description "1537.25 nm/195.018750 THz 3.125/6.25GHz spacing";
             }
             enum "1537.22" {
               description "1537.22 nm/195.021875 THz 3.125GHz spacing";
             }
             enum "1537.20" {
               description "1537.20 nm/195.025000 THz 3.125/6.25/12.5GHz spacing";
             }
             enum "1537.18" {
               description "1537.18 nm/195.028125 THz 3.125GHz spacing";
             }
             enum "1537.15" {
               description "1537.15 nm/195.031250 THz 3.125/6.25GHz spacing";
             }
             enum "1537.13" {
               description "1537.13 nm/195.034375 THz 3.125GHz spacing";
             }
             enum "1537.10" {
               description "1537.10 nm/195.037500 THz 3.125/6.25/12.5GHz spacing";
             }
             enum "1537.08" {
               description "1537.08 nm/195.040625 THz 3.125GHz spacing";
             }
             enum "1537.05" {
               description "1537.05 nm/195.043750 THz 3.125/6.25GHz spacing";
             }
             enum "1537.03" {
               description "1537.03 nm/195.046875 THz 3.125GHz spacing";
             }
             enum "1537.00" {
               description "1537.00 nm/195.050000 THz 3.125/6.25/12.5/50GHz spacing";
             }
             enum "1536.98" {
               description "1536.98 nm/195.053125 THz 3.125GHz spacing";
             }
             enum "1536.95" {
               description "1536.95 nm/195.056250 THz 3.125/6.25GHz spacing";
             }
             enum "1536.93" {
               description "1536.93 nm/195.059375 THz 3.125GHz spacing";
             }
             enum "1536.90" {
               description "1536.90 nm/195.062500 THz 3.125/6.25/12.5GHz spacing";
             }
             enum "1536.88" {
               description "1536.88 nm/195.065625 THz 3.125GHz spacing";
             }
             enum "1536.86" {
               description "1536.86 nm/195.068750 THz 3.125/6.25GHz spacing";
             }
             enum "1536.83" {
               description "1536.83 nm/195.071875 THz 3.125GHz spacing";
             }
             enum "1536.81" {
               description "1536.81 nm/195.075000 THz 3.125/6.25/12.5/75GHz spacing";
             }
             enum "1536.78" {
               description "1536.78 nm/195.078125 THz 3.125GHz spacing";
             }
             enum "1536.76" {
               description "1536.76 nm/195.081250 THz 3.125/6.25GHz spacing";
             }
             enum "1536.73" {
               description "1536.73 nm/195.084375 THz 3.125GHz spacing";
             }
             enum "1536.71" {
               description "1536.71 nm/195.087500 THz 3.125/6.25/12.5GHz spacing";
             }
             enum "1536.68" {
               description "1536.68 nm/195.090625 THz 3.125GHz spacing";
             }
             enum "1536.66" {
               description "1536.66 nm/195.093750 THz 3.125/6.25GHz spacing";
             }
             enum "1536.63" {
               description "1536.63 nm/195.096875 THz 3.125GHz spacing";
             }
             enum "1536.61" {
               description "1536.61 nm/195.100000 THz 3.125/6.25/12.5/100GHz spacing";
             }
             enum "1536.58" {
               description "1536.58 nm/195.103125 THz 3.125GHz spacing";
             }
             enum "1536.56" {
               description "1536.56 nm/195.106250 THz 3.125/6.25GHz spacing";
             }
             enum "1536.54" {
               description "1536.54 nm/195.109375 THz 3.125GHz spacing";
             }
             enum "1536.51" {
               description "1536.51 nm/195.112500 THz 3.125/6.25/12.5GHz spacing";
             }
             enum "1536.49" {
               description "1536.49 nm/195.115625 THz 3.125GHz spacing";
             }
             enum "1536.46" {
               description "1536.46 nm/195.118750 THz 3.125/6.25GHz spacing";
             }
             enum "1536.44" {
               description "1536.44 nm/195.121875 THz 3.125GHz spacing";
             }
             enum "1536.41" {
               description "1536.41 nm/195.125000 THz 3.125/6.25/12.5GHz spacing";
             }
             enum "1536.39" {
               description "1536.39 nm/195.128125 THz 3.125GHz spacing";
             }
             enum "1536.36" {
               description "1536.36 nm/195.131250 THz 3.125/6.25GHz spacing";
             }
             enum "1536.34" {
               description "1536.34 nm/195.134375 THz 3.125GHz spacing";
             }
             enum "1536.31" {
               description "1536.31 nm/195.137500 THz 3.125/6.25/12.5GHz spacing";
             }
             enum "1536.29" {
               description "1536.29 nm/195.140625 THz 3.125GHz spacing";
             }
             enum "1536.26" {
               description "1536.26 nm/195.143750 THz 3.125/6.25GHz spacing";
             }
             enum "1536.24" {
               description "1536.24 nm/195.146875 THz 3.125GHz spacing";
             }
             enum "1536.22" {
               description "1536.22 nm/195.150000 THz 3.125/6.25/12.5/50/75GHz spacing";
             }
             enum "1536.19" {
               description "1536.19 nm/195.153125 THz 3.125GHz spacing";
             }
             enum "1536.17" {
               description "1536.17 nm/195.156250 THz 3.125/6.25GHz spacing";
             }
             enum "1536.14" {
               description "1536.14 nm/195.159375 THz 3.125GHz spacing";
             }
             enum "1536.12" {
               description "1536.12 nm/195.162500 THz 3.125/6.25/12.5GHz spacing";
             }
             enum "1536.09" {
               description "1536.09 nm/195.165625 THz 3.125GHz spacing";
             }
             enum "1536.07" {
               description "1536.07 nm/195.168750 THz 3.125/6.25GHz spacing";
             }
             enum "1536.04" {
               description "1536.04 nm/195.171875 THz 3.125GHz spacing";
             }
             enum "1536.02" {
               description "1536.02 nm/195.175000 THz 3.125/6.25/12.5GHz spacing";
             }
             enum "1535.99" {
               description "1535.99 nm/195.178125 THz 3.125GHz spacing";
             }
             enum "1535.97" {
               description "1535.97 nm/195.181250 THz 3.125/6.25GHz spacing";
             }
             enum "1535.94" {
               description "1535.94 nm/195.184375 THz 3.125GHz spacing";
             }
             enum "1535.92" {
               description "1535.92 nm/195.187500 THz 3.125/6.25/12.5GHz spacing";
             }
             enum "1535.90" {
               description "1535.90 nm/195.190625 THz 3.125GHz spacing";
             }
             enum "1535.87" {
               description "1535.87 nm/195.193750 THz 3.125/6.25GHz spacing";
             }
             enum "1535.85" {
               description "1535.85 nm/195.196875 THz 3.125GHz spacing";
             }
             enum "1535.82" {
               description "1535.82 nm/195.200000 THz 3.125/6.25/12.5/100GHz spacing";
             }
             enum "1535.80" {
               description "1535.80 nm/195.203125 THz 3.125GHz spacing";
             }
             enum "1535.77" {
               description "1535.77 nm/195.206250 THz 3.125/6.25GHz spacing";
             }
             enum "1535.75" {
               description "1535.75 nm/195.209375 THz 3.125GHz spacing";
             }
             enum "1535.72" {
               description "1535.72 nm/195.212500 THz 3.125/6.25/12.5GHz spacing";
             }
             enum "1535.70" {
               description "1535.70 nm/195.215625 THz 3.125GHz spacing";
             }
             enum "1535.67" {
               description "1535.67 nm/195.218750 THz 3.125/6.25GHz spacing";
             }
             enum "1535.65" {
               description "1535.65 nm/195.221875 THz 3.125GHz spacing";
             }
             enum "1535.63" {
               description "1535.63 nm/195.225000 THz 3.125/6.25/12.5/75GHz spacing";
             }
             enum "1535.60" {
               description "1535.60 nm/195.228125 THz 3.125GHz spacing";
             }
             enum "1535.58" {
               description "1535.58 nm/195.231250 THz 3.125/6.25GHz spacing";
             }
             enum "1535.55" {
               description "1535.55 nm/195.234375 THz 3.125GHz spacing";
             }
             enum "1535.53" {
               description "1535.53 nm/195.237500 THz 3.125/6.25/12.5GHz spacing";
             }
             enum "1535.50" {
               description "1535.50 nm/195.240625 THz 3.125GHz spacing";
             }
             enum "1535.48" {
               description "1535.48 nm/195.243750 THz 3.125/6.25GHz spacing";
             }
             enum "1535.45" {
               description "1535.45 nm/195.246875 THz 3.125GHz spacing";
             }
             enum "1535.43" {
               description "1535.43 nm/195.250000 THz 3.125/6.25/12.5/50GHz spacing";
             }
             enum "1535.40" {
               description "1535.40 nm/195.253125 THz 3.125GHz spacing";
             }
             enum "1535.38" {
               description "1535.38 nm/195.256250 THz 3.125/6.25GHz spacing";
             }
             enum "1535.36" {
               description "1535.36 nm/195.259375 THz 3.125GHz spacing";
             }
             enum "1535.33" {
               description "1535.33 nm/195.262500 THz 3.125/6.25/12.5GHz spacing";
             }
             enum "1535.31" {
               description "1535.31 nm/195.265625 THz 3.125GHz spacing";
             }
             enum "1535.28" {
               description "1535.28 nm/195.268750 THz 3.125/6.25GHz spacing";
             }
             enum "1535.26" {
               description "1535.26 nm/195.271875 THz 3.125GHz spacing";
             }
             enum "1535.23" {
               description "1535.23 nm/195.275000 THz 3.125/6.25/12.5GHz spacing";
             }
             enum "1535.21" {
               description "1535.21 nm/195.278125 THz 3.125GHz spacing";
             }
             enum "1535.18" {
               description "1535.18 nm/195.281250 THz 3.125/6.25GHz spacing";
             }
             enum "1535.16" {
               description "1535.16 nm/195.284375 THz 3.125GHz spacing";
             }
             enum "1535.13" {
               description "1535.13 nm/195.287500 THz 3.125/6.25/12.5GHz spacing";
             }
             enum "1535.11" {
               description "1535.11 nm/195.290625 THz 3.125GHz spacing";
             }
             enum "1535.08" {
               description "1535.08 nm/195.293750 THz 3.125/6.25GHz spacing";
             }
             enum "1535.06" {
               description "1535.06 nm/195.296875 THz 3.125GHz spacing";
             }
             enum "1535.04" {
               description "1535.04 nm/195.300000 THz 3.125/6.25/12.5/50/75/100GHz spacing";
             }
             enum "1535.01" {
               description "1535.01 nm/195.303125 THz 3.125GHz spacing";
             }
             enum "1534.99" {
               description "1534.99 nm/195.306250 THz 3.125/6.25GHz spacing";
             }
             enum "1534.96" {
               description "1534.96 nm/195.309375 THz 3.125GHz spacing";
             }
             enum "1534.94" {
               description "1534.94 nm/195.312500 THz 3.125/6.25/12.5GHz spacing";
             }
             enum "1534.91" {
               description "1534.91 nm/195.315625 THz 3.125GHz spacing";
             }
             enum "1534.89" {
               description "1534.89 nm/195.318750 THz 3.125/6.25GHz spacing";
             }
             enum "1534.86" {
               description "1534.86 nm/195.321875 THz 3.125GHz spacing";
             }
             enum "1534.84" {
               description "1534.84 nm/195.325000 THz 3.125/6.25/12.5GHz spacing";
             }
             enum "1534.81" {
               description "1534.81 nm/195.328125 THz 3.125GHz spacing";
             }
             enum "1534.79" {
               description "1534.79 nm/195.331250 THz 3.125/6.25GHz spacing";
             }
             enum "1534.77" {
               description "1534.77 nm/195.334375 THz 3.125GHz spacing";
             }
             enum "1534.74" {
               description "1534.74 nm/195.337500 THz 3.125/6.25/12.5GHz spacing";
             }
             enum "1534.72" {
               description "1534.72 nm/195.340625 THz 3.125GHz spacing";
             }
             enum "1534.69" {
               description "1534.69 nm/195.343750 THz 3.125/6.25GHz spacing";
             }
             enum "1534.67" {
               description "1534.67 nm/195.346875 THz 3.125GHz spacing";
             }
             enum "1534.64" {
               description "1534.64 nm/195.350000 THz 3.125/6.25/12.5/50GHz spacing";
             }
             enum "1534.62" {
               description "1534.62 nm/195.353125 THz 3.125GHz spacing";
             }
             enum "1534.59" {
               description "1534.59 nm/195.356250 THz 3.125/6.25GHz spacing";
             }
             enum "1534.57" {
               description "1534.57 nm/195.359375 THz 3.125GHz spacing";
             }
             enum "1534.54" {
               description "1534.54 nm/195.362500 THz 3.125/6.25/12.5GHz spacing";
             }
             enum "1534.52" {
               description "1534.52 nm/195.365625 THz 3.125GHz spacing";
             }
             enum "1534.50" {
               description "1534.50 nm/195.368750 THz 3.125/6.25GHz spacing";
             }
             enum "1534.47" {
               description "1534.47 nm/195.371875 THz 3.125GHz spacing";
             }
             enum "1534.45" {
               description "1534.45 nm/195.375000 THz 3.125/6.25/12.5/75GHz spacing";
             }
             enum "1534.42" {
               description "1534.42 nm/195.378125 THz 3.125GHz spacing";
             }
             enum "1534.40" {
               description "1534.40 nm/195.381250 THz 3.125/6.25GHz spacing";
             }
             enum "1534.37" {
               description "1534.37 nm/195.384375 THz 3.125GHz spacing";
             }
             enum "1534.35" {
               description "1534.35 nm/195.387500 THz 3.125/6.25/12.5GHz spacing";
             }
             enum "1534.32" {
               description "1534.32 nm/195.390625 THz 3.125GHz spacing";
             }
             enum "1534.30" {
               description "1534.30 nm/195.393750 THz 3.125/6.25GHz spacing";
             }
             enum "1534.27" {
               description "1534.27 nm/195.396875 THz 3.125GHz spacing";
             }
             enum "1534.25" {
               description "1534.25 nm/195.400000 THz 3.125/6.25/12.5/100GHz spacing";
             }
             enum "1534.23" {
               description "1534.23 nm/195.403125 THz 3.125GHz spacing";
             }
             enum "1534.20" {
               description "1534.20 nm/195.406250 THz 3.125/6.25GHz spacing";
             }
             enum "1534.18" {
               description "1534.18 nm/195.409375 THz 3.125GHz spacing";
             }
             enum "1534.15" {
               description "1534.15 nm/195.412500 THz 3.125/6.25/12.5GHz spacing";
             }
             enum "1534.13" {
               description "1534.13 nm/195.415625 THz 3.125GHz spacing";
             }
             enum "1534.10" {
               description "1534.10 nm/195.418750 THz 3.125/6.25GHz spacing";
             }
             enum "1534.08" {
               description "1534.08 nm/195.421875 THz 3.125GHz spacing";
             }
             enum "1534.05" {
               description "1534.05 nm/195.425000 THz 3.125/6.25/12.5GHz spacing";
             }
             enum "1534.03" {
               description "1534.03 nm/195.428125 THz 3.125GHz spacing";
             }
             enum "1534.00" {
               description "1534.00 nm/195.431250 THz 3.125/6.25GHz spacing";
             }
             enum "1533.98" {
               description "1533.98 nm/195.434375 THz 3.125GHz spacing";
             }
             enum "1533.96" {
               description "1533.96 nm/195.437500 THz 3.125/6.25/12.5GHz spacing";
             }
             enum "1533.93" {
               description "1533.93 nm/195.440625 THz 3.125GHz spacing";
             }
             enum "1533.91" {
               description "1533.91 nm/195.443750 THz 3.125/6.25GHz spacing";
             }
             enum "1533.88" {
               description "1533.88 nm/195.446875 THz 3.125GHz spacing";
             }
             enum "1533.86" {
               description "1533.86 nm/195.450000 THz 3.125/6.25/12.5/50/75GHz spacing";
             }
             enum "1533.83" {
               description "1533.83 nm/195.453125 THz 3.125GHz spacing";
             }
             enum "1533.81" {
               description "1533.81 nm/195.456250 THz 3.125/6.25GHz spacing";
             }
             enum "1533.78" {
               description "1533.78 nm/195.459375 THz 3.125GHz spacing";
             }
             enum "1533.76" {
               description "1533.76 nm/195.462500 THz 3.125/6.25/12.5GHz spacing";
             }
             enum "1533.73" {
               description "1533.73 nm/195.465625 THz 3.125GHz spacing";
             }
             enum "1533.71" {
               description "1533.71 nm/195.468750 THz 3.125/6.25GHz spacing";
             }
             enum "1533.69" {
               description "1533.69 nm/195.471875 THz 3.125GHz spacing";
             }
             enum "1533.66" {
               description "1533.66 nm/195.475000 THz 3.125/6.25/12.5GHz spacing";
             }
             enum "1533.64" {
               description "1533.64 nm/195.478125 THz 3.125GHz spacing";
             }
             enum "1533.61" {
               description "1533.61 nm/195.481250 THz 3.125/6.25GHz spacing";
             }
             enum "1533.59" {
               description "1533.59 nm/195.484375 THz 3.125GHz spacing";
             }
             enum "1533.56" {
               description "1533.56 nm/195.487500 THz 3.125/6.25/12.5GHz spacing";
             }
             enum "1533.54" {
               description "1533.54 nm/195.490625 THz 3.125GHz spacing";
             }
             enum "1533.51" {
               description "1533.51 nm/195.493750 THz 3.125/6.25GHz spacing";
             }
             enum "1533.49" {
               description "1533.49 nm/195.496875 THz 3.125GHz spacing";
             }
             enum "1533.47" {
               description "1533.47 nm/195.500000 THz 3.125/6.25/12.5/100GHz spacing";
             }
             enum "1533.44" {
               description "1533.44 nm/195.503125 THz 3.125GHz spacing";
             }
             enum "1533.42" {
               description "1533.42 nm/195.506250 THz 3.125/6.25GHz spacing";
             }
             enum "1533.39" {
               description "1533.39 nm/195.509375 THz 3.125GHz spacing";
             }
             enum "1533.37" {
               description "1533.37 nm/195.512500 THz 3.125/6.25/12.5GHz spacing";
             }
             enum "1533.34" {
               description "1533.34 nm/195.515625 THz 3.125GHz spacing";
             }
             enum "1533.32" {
               description "1533.32 nm/195.518750 THz 3.125/6.25GHz spacing";
             }
             enum "1533.29" {
               description "1533.29 nm/195.521875 THz 3.125GHz spacing";
             }
             enum "1533.27" {
               description "1533.27 nm/195.525000 THz 3.125/6.25/12.5/75GHz spacing";
             }
             enum "1533.24" {
               description "1533.24 nm/195.528125 THz 3.125GHz spacing";
             }
             enum "1533.22" {
               description "1533.22 nm/195.531250 THz 3.125/6.25GHz spacing";
             }
             enum "1533.20" {
               description "1533.20 nm/195.534375 THz 3.125GHz spacing";
             }
             enum "1533.17" {
               description "1533.17 nm/195.537500 THz 3.125/6.25/12.5GHz spacing";
             }
             enum "1533.15" {
               description "1533.15 nm/195.540625 THz 3.125GHz spacing";
             }
             enum "1533.12" {
               description "1533.12 nm/195.543750 THz 3.125/6.25GHz spacing";
             }
             enum "1533.10" {
               description "1533.10 nm/195.546875 THz 3.125GHz spacing";
             }
             enum "1533.07" {
               description "1533.07 nm/195.550000 THz 3.125/6.25/12.5/50GHz spacing";
             }
             enum "1533.05" {
               description "1533.05 nm/195.553125 THz 3.125GHz spacing";
             }
             enum "1533.02" {
               description "1533.02 nm/195.556250 THz 3.125/6.25GHz spacing";
             }
             enum "1533.00" {
               description "1533.00 nm/195.559375 THz 3.125GHz spacing";
             }
             enum "1532.98" {
               description "1532.98 nm/195.562500 THz 3.125/6.25/12.5GHz spacing";
             }
             enum "1532.95" {
               description "1532.95 nm/195.565625 THz 3.125GHz spacing";
             }
             enum "1532.93" {
               description "1532.93 nm/195.568750 THz 3.125/6.25GHz spacing";
             }
             enum "1532.90" {
               description "1532.90 nm/195.571875 THz 3.125GHz spacing";
             }
             enum "1532.88" {
               description "1532.88 nm/195.575000 THz 3.125/6.25/12.5GHz spacing";
             }
             enum "1532.85" {
               description "1532.85 nm/195.578125 THz 3.125GHz spacing";
             }
             enum "1532.83" {
               description "1532.83 nm/195.581250 THz 3.125/6.25GHz spacing";
             }
             enum "1532.80" {
               description "1532.80 nm/195.584375 THz 3.125GHz spacing";
             }
             enum "1532.78" {
               description "1532.78 nm/195.587500 THz 3.125/6.25/12.5GHz spacing";
             }
             enum "1532.75" {
               description "1532.75 nm/195.590625 THz 3.125GHz spacing";
             }
             enum "1532.73" {
               description "1532.73 nm/195.593750 THz 3.125/6.25GHz spacing";
             }
             enum "1532.71" {
               description "1532.71 nm/195.596875 THz 3.125GHz spacing";
             }
             enum "1532.68" {
               description "1532.68 nm/195.600000 THz 3.125/6.25/12.5/50/75/100GHz spacing";
             }
             enum "1532.66" {
               description "1532.66 nm/195.603125 THz 3.125GHz spacing";
             }
             enum "1532.63" {
               description "1532.63 nm/195.606250 THz 3.125/6.25GHz spacing";
             }
             enum "1532.61" {
               description "1532.61 nm/195.609375 THz 3.125GHz spacing";
             }
             enum "1532.58" {
               description "1532.58 nm/195.612500 THz 3.125/6.25/12.5GHz spacing";
             }
             enum "1532.56" {
               description "1532.56 nm/195.615625 THz 3.125GHz spacing";
             }
             enum "1532.53" {
               description "1532.53 nm/195.618750 THz 3.125/6.25GHz spacing";
             }
             enum "1532.51" {
               description "1532.51 nm/195.621875 THz 3.125GHz spacing";
             }
             enum "1532.49" {
               description "1532.49 nm/195.625000 THz 3.125/6.25/12.5GHz spacing";
             }
             enum "1532.46" {
               description "1532.46 nm/195.628125 THz 3.125GHz spacing";
             }
             enum "1532.44" {
               description "1532.44 nm/195.631250 THz 3.125/6.25GHz spacing";
             }
             enum "1532.41" {
               description "1532.41 nm/195.634375 THz 3.125GHz spacing";
             }
             enum "1532.39" {
               description "1532.39 nm/195.637500 THz 3.125/6.25/12.5GHz spacing";
             }
             enum "1532.36" {
               description "1532.36 nm/195.640625 THz 3.125GHz spacing";
             }
             enum "1532.34" {
               description "1532.34 nm/195.643750 THz 3.125/6.25GHz spacing";
             }
             enum "1532.31" {
               description "1532.31 nm/195.646875 THz 3.125GHz spacing";
             }
             enum "1532.29" {
               description "1532.29 nm/195.650000 THz 3.125/6.25/12.5/50GHz spacing";
             }
             enum "1532.27" {
               description "1532.27 nm/195.653125 THz 3.125GHz spacing";
             }
             enum "1532.24" {
               description "1532.24 nm/195.656250 THz 3.125/6.25GHz spacing";
             }
             enum "1532.22" {
               description "1532.22 nm/195.659375 THz 3.125GHz spacing";
             }
             enum "1532.19" {
               description "1532.19 nm/195.662500 THz 3.125/6.25/12.5GHz spacing";
             }
             enum "1532.17" {
               description "1532.17 nm/195.665625 THz 3.125GHz spacing";
             }
             enum "1532.14" {
               description "1532.14 nm/195.668750 THz 3.125/6.25GHz spacing";
             }
             enum "1532.12" {
               description "1532.12 nm/195.671875 THz 3.125GHz spacing";
             }
             enum "1532.09" {
               description "1532.09 nm/195.675000 THz 3.125/6.25/12.5/75GHz spacing";
             }
             enum "1532.07" {
               description "1532.07 nm/195.678125 THz 3.125GHz spacing";
             }
             enum "1532.04" {
               description "1532.04 nm/195.681250 THz 3.125/6.25GHz spacing";
             }
             enum "1532.02" {
               description "1532.02 nm/195.684375 THz 3.125GHz spacing";
             }
             enum "1532.00" {
               description "1532.00 nm/195.687500 THz 3.125/6.25/12.5GHz spacing";
             }
             enum "1531.97" {
               description "1531.97 nm/195.690625 THz 3.125GHz spacing";
             }
             enum "1531.95" {
               description "1531.95 nm/195.693750 THz 3.125/6.25GHz spacing";
             }
             enum "1531.92" {
               description "1531.92 nm/195.696875 THz 3.125GHz spacing";
             }
             enum "1531.90" {
               description "1531.90 nm/195.700000 THz 3.125/6.25/12.5/100GHz spacing";
             }
             enum "1531.87" {
               description "1531.87 nm/195.703125 THz 3.125GHz spacing";
             }
             enum "1531.85" {
               description "1531.85 nm/195.706250 THz 3.125/6.25GHz spacing";
             }
             enum "1531.82" {
               description "1531.82 nm/195.709375 THz 3.125GHz spacing";
             }
             enum "1531.80" {
               description "1531.80 nm/195.712500 THz 3.125/6.25/12.5GHz spacing";
             }
             enum "1531.78" {
               description "1531.78 nm/195.715625 THz 3.125GHz spacing";
             }
             enum "1531.75" {
               description "1531.75 nm/195.718750 THz 3.125/6.25GHz spacing";
             }
             enum "1531.73" {
               description "1531.73 nm/195.721875 THz 3.125GHz spacing";
             }
             enum "1531.70" {
               description "1531.70 nm/195.725000 THz 3.125/6.25/12.5GHz spacing";
             }
             enum "1531.68" {
               description "1531.68 nm/195.728125 THz 3.125GHz spacing";
             }
             enum "1531.65" {
               description "1531.65 nm/195.731250 THz 3.125/6.25GHz spacing";
             }
             enum "1531.63" {
               description "1531.63 nm/195.734375 THz 3.125GHz spacing";
             }
             enum "1531.60" {
               description "1531.60 nm/195.737500 THz 3.125/6.25/12.5GHz spacing";
             }
             enum "1531.58" {
               description "1531.58 nm/195.740625 THz 3.125GHz spacing";
             }
             enum "1531.56" {
               description "1531.56 nm/195.743750 THz 3.125/6.25GHz spacing";
             }
             enum "1531.53" {
               description "1531.53 nm/195.746875 THz 3.125GHz spacing";
             }
             enum "1531.51" {
               description "1531.51 nm/195.750000 THz 3.125/6.25/12.5/50/75GHz spacing";
             }
             enum "1531.48" {
               description "1531.48 nm/195.753125 THz 3.125GHz spacing";
             }
             enum "1531.46" {
               description "1531.46 nm/195.756250 THz 3.125/6.25GHz spacing";
             }
             enum "1531.43" {
               description "1531.43 nm/195.759375 THz 3.125GHz spacing";
             }
             enum "1531.41" {
               description "1531.41 nm/195.762500 THz 3.125/6.25/12.5GHz spacing";
             }
             enum "1531.38" {
               description "1531.38 nm/195.765625 THz 3.125GHz spacing";
             }
             enum "1531.36" {
               description "1531.36 nm/195.768750 THz 3.125/6.25GHz spacing";
             }
             enum "1531.34" {
               description "1531.34 nm/195.771875 THz 3.125GHz spacing";
             }
             enum "1531.31" {
               description "1531.31 nm/195.775000 THz 3.125/6.25/12.5GHz spacing";
             }
             enum "1531.29" {
               description "1531.29 nm/195.778125 THz 3.125GHz spacing";
             }
             enum "1531.26" {
               description "1531.26 nm/195.781250 THz 3.125/6.25GHz spacing";
             }
             enum "1531.24" {
               description "1531.24 nm/195.784375 THz 3.125GHz spacing";
             }
             enum "1531.21" {
               description "1531.21 nm/195.787500 THz 3.125/6.25/12.5GHz spacing";
             }
             enum "1531.19" {
               description "1531.19 nm/195.790625 THz 3.125GHz spacing";
             }
             enum "1531.16" {
               description "1531.16 nm/195.793750 THz 3.125/6.25GHz spacing";
             }
             enum "1531.14" {
               description "1531.14 nm/195.796875 THz 3.125GHz spacing";
             }
             enum "1531.12" {
               description "1531.12 nm/195.800000 THz 3.125/6.25/12.5/100GHz spacing";
             }
             enum "1531.09" {
               description "1531.09 nm/195.803125 THz 3.125GHz spacing";
             }
             enum "1531.07" {
               description "1531.07 nm/195.806250 THz 3.125/6.25GHz spacing";
             }
             enum "1531.04" {
               description "1531.04 nm/195.809375 THz 3.125GHz spacing";
             }
             enum "1531.02" {
               description "1531.02 nm/195.812500 THz 3.125/6.25/12.5GHz spacing";
             }
             enum "1530.99" {
               description "1530.99 nm/195.815625 THz 3.125GHz spacing";
             }
             enum "1530.97" {
               description "1530.97 nm/195.818750 THz 3.125/6.25GHz spacing";
             }
             enum "1530.94" {
               description "1530.94 nm/195.821875 THz 3.125GHz spacing";
             }
             enum "1530.92" {
               description "1530.92 nm/195.825000 THz 3.125/6.25/12.5/75GHz spacing";
             }
             enum "1530.90" {
               description "1530.90 nm/195.828125 THz 3.125GHz spacing";
             }
             enum "1530.87" {
               description "1530.87 nm/195.831250 THz 3.125/6.25GHz spacing";
             }
             enum "1530.85" {
               description "1530.85 nm/195.834375 THz 3.125GHz spacing";
             }
             enum "1530.82" {
               description "1530.82 nm/195.837500 THz 3.125/6.25/12.5GHz spacing";
             }
             enum "1530.80" {
               description "1530.80 nm/195.840625 THz 3.125GHz spacing";
             }
             enum "1530.77" {
               description "1530.77 nm/195.843750 THz 3.125/6.25GHz spacing";
             }
             enum "1530.75" {
               description "1530.75 nm/195.846875 THz 3.125GHz spacing";
             }
             enum "1530.72" {
               description "1530.72 nm/195.850000 THz 3.125/6.25/12.5/50GHz spacing";
             }
             enum "1530.70" {
               description "1530.70 nm/195.853125 THz 3.125GHz spacing";
             }
             enum "1530.68" {
               description "1530.68 nm/195.856250 THz 3.125/6.25GHz spacing";
             }
             enum "1530.65" {
               description "1530.65 nm/195.859375 THz 3.125GHz spacing";
             }
             enum "1530.63" {
               description "1530.63 nm/195.862500 THz 3.125/6.25/12.5GHz spacing";
             }
             enum "1530.60" {
               description "1530.60 nm/195.865625 THz 3.125GHz spacing";
             }
             enum "1530.58" {
               description "1530.58 nm/195.868750 THz 3.125/6.25GHz spacing";
             }
             enum "1530.55" {
               description "1530.55 nm/195.871875 THz 3.125GHz spacing";
             }
             enum "1530.53" {
               description "1530.53 nm/195.875000 THz 3.125/6.25/12.5GHz spacing";
             }
             enum "1530.51" {
               description "1530.51 nm/195.878125 THz 3.125GHz spacing";
             }
             enum "1530.48" {
               description "1530.48 nm/195.881250 THz 3.125/6.25GHz spacing";
             }
             enum "1530.46" {
               description "1530.46 nm/195.884375 THz 3.125GHz spacing";
             }
             enum "1530.43" {
               description "1530.43 nm/195.887500 THz 3.125/6.25/12.5GHz spacing";
             }
             enum "1530.41" {
               description "1530.41 nm/195.890625 THz 3.125GHz spacing";
             }
             enum "1530.38" {
               description "1530.38 nm/195.893750 THz 3.125/6.25GHz spacing";
             }
             enum "1530.36" {
               description "1530.36 nm/195.896875 THz 3.125GHz spacing";
             }
             enum "1530.33" {
               description "1530.33 nm/195.900000 THz 3.125/6.25/12.5/50/75/100GHz spacing";
             }
             enum "1530.31" {
               description "1530.31 nm/195.903125 THz 3.125GHz spacing";
             }
             enum "1530.29" {
               description "1530.29 nm/195.906250 THz 3.125/6.25GHz spacing";
             }
             enum "1530.26" {
               description "1530.26 nm/195.909375 THz 3.125GHz spacing";
             }
             enum "1530.24" {
               description "1530.24 nm/195.912500 THz 3.125/6.25/12.5GHz spacing";
             }
             enum "1530.21" {
               description "1530.21 nm/195.915625 THz 3.125GHz spacing";
             }
             enum "1530.19" {
               description "1530.19 nm/195.918750 THz 3.125/6.25GHz spacing";
             }
             enum "1530.16" {
               description "1530.16 nm/195.921875 THz 3.125GHz spacing";
             }
             enum "1530.14" {
               description "1530.14 nm/195.925000 THz 3.125/6.25/12.5GHz spacing";
             }
             enum "1530.11" {
               description "1530.11 nm/195.928125 THz 3.125GHz spacing";
             }
             enum "1530.09" {
               description "1530.09 nm/195.931250 THz 3.125/6.25GHz spacing";
             }
             enum "1530.07" {
               description "1530.07 nm/195.934375 THz 3.125GHz spacing";
             }
             enum "1530.04" {
               description "1530.04 nm/195.937500 THz 3.125/6.25/12.5GHz spacing";
             }
             enum "1530.02" {
               description "1530.02 nm/195.940625 THz 3.125GHz spacing";
             }
             enum "1529.99" {
               description "1529.99 nm/195.943750 THz 3.125/6.25GHz spacing";
             }
             enum "1529.97" {
               description "1529.97 nm/195.946875 THz 3.125GHz spacing";
             }
             enum "1529.94" {
               description "1529.94 nm/195.950000 THz 3.125/6.25/12.5/50GHz spacing";
             }
             enum "1529.92" {
               description "1529.92 nm/195.953125 THz 3.125GHz spacing";
             }
             enum "1529.89" {
               description "1529.89 nm/195.956250 THz 3.125/6.25GHz spacing";
             }
             enum "1529.87" {
               description "1529.87 nm/195.959375 THz 3.125GHz spacing";
             }
             enum "1529.85" {
               description "1529.85 nm/195.962500 THz 3.125/6.25/12.5GHz spacing";
             }
             enum "1529.82" {
               description "1529.82 nm/195.965625 THz 3.125GHz spacing";
             }
             enum "1529.80" {
               description "1529.80 nm/195.968750 THz 3.125/6.25GHz spacing";
             }
             enum "1529.77" {
               description "1529.77 nm/195.971875 THz 3.125GHz spacing";
             }
             enum "1529.75" {
               description "1529.75 nm/195.975000 THz 3.125/6.25/12.5/75GHz spacing";
             }
             enum "1529.72" {
               description "1529.72 nm/195.978125 THz 3.125GHz spacing";
             }
             enum "1529.70" {
               description "1529.70 nm/195.981250 THz 3.125/6.25GHz spacing";
             }
             enum "1529.68" {
               description "1529.68 nm/195.984375 THz 3.125GHz spacing";
             }
             enum "1529.65" {
               description "1529.65 nm/195.987500 THz 3.125/6.25/12.5GHz spacing";
             }
             enum "1529.63" {
               description "1529.63 nm/195.990625 THz 3.125GHz spacing";
             }
             enum "1529.60" {
               description "1529.60 nm/195.993750 THz 3.125/6.25GHz spacing";
             }
             enum "1529.58" {
               description "1529.58 nm/195.996875 THz 3.125GHz spacing";
             }
             enum "1529.55" {
               description "1529.55 nm/196.000000 THz 3.125/6.25/12.5/100GHz spacing";
             }
             enum "1529.53" {
               description "1529.53 nm/196.003125 THz 3.125GHz spacing";
             }
             enum "1529.50" {
               description "1529.50 nm/196.006250 THz 3.125/6.25GHz spacing";
             }
             enum "1529.48" {
               description "1529.48 nm/196.009375 THz 3.125GHz spacing";
             }
             enum "1529.46" {
               description "1529.46 nm/196.012500 THz 3.125/6.25/12.5GHz spacing";
             }
             enum "1529.43" {
               description "1529.43 nm/196.015625 THz 3.125GHz spacing";
             }
             enum "1529.41" {
               description "1529.41 nm/196.018750 THz 3.125/6.25GHz spacing";
             }
             enum "1529.38" {
               description "1529.38 nm/196.021875 THz 3.125GHz spacing";
             }
             enum "1529.36" {
               description "1529.36 nm/196.025000 THz 3.125/6.25/12.5GHz spacing";
             }
             enum "1529.33" {
               description "1529.33 nm/196.028125 THz 3.125GHz spacing";
             }
             enum "1529.31" {
               description "1529.31 nm/196.031250 THz 3.125/6.25GHz spacing";
             }
             enum "1529.29" {
               description "1529.29 nm/196.034375 THz 3.125GHz spacing";
             }
             enum "1529.26" {
               description "1529.26 nm/196.037500 THz 3.125/6.25/12.5GHz spacing";
             }
             enum "1529.24" {
               description "1529.24 nm/196.040625 THz 3.125GHz spacing";
             }
             enum "1529.21" {
               description "1529.21 nm/196.043750 THz 3.125/6.25GHz spacing";
             }
             enum "1529.19" {
               description "1529.19 nm/196.046875 THz 3.125GHz spacing";
             }
             enum "1529.16" {
               description "1529.16 nm/196.050000 THz 3.125/6.25/12.5/50/75GHz spacing";
             }
             enum "1529.14" {
               description "1529.14 nm/196.053125 THz 3.125GHz spacing";
             }
             enum "1529.11" {
               description "1529.11 nm/196.056250 THz 3.125/6.25GHz spacing";
             }
             enum "1529.09" {
               description "1529.09 nm/196.059375 THz 3.125GHz spacing";
             }
             enum "1529.07" {
               description "1529.07 nm/196.062500 THz 3.125/6.25/12.5GHz spacing";
             }
             enum "1529.04" {
               description "1529.04 nm/196.065625 THz 3.125GHz spacing";
             }
             enum "1529.02" {
               description "1529.02 nm/196.068750 THz 3.125/6.25GHz spacing";
             }
             enum "1528.99" {
               description "1528.99 nm/196.071875 THz 3.125GHz spacing";
             }
             enum "1528.97" {
               description "1528.97 nm/196.075000 THz 3.125/6.25/12.5GHz spacing";
             }
             enum "1528.94" {
               description "1528.94 nm/196.078125 THz 3.125GHz spacing";
             }
             enum "1528.92" {
               description "1528.92 nm/196.081250 THz 3.125/6.25GHz spacing";
             }
             enum "1528.90" {
               description "1528.90 nm/196.084375 THz 3.125GHz spacing";
             }
             enum "1528.87" {
               description "1528.87 nm/196.087500 THz 3.125/6.25/12.5GHz spacing";
             }
             enum "1528.85" {
               description "1528.85 nm/196.090625 THz 3.125GHz spacing";
             }
             enum "1528.82" {
               description "1528.82 nm/196.093750 THz 3.125/6.25GHz spacing";
             }
             enum "1528.80" {
               description "1528.80 nm/196.096875 THz 3.125GHz spacing";
             }
             enum "1528.77" {
               description "1528.77 nm/196.100000 THz 3.125/6.25/12.5/50/75/100GHz spacing";
             }
             enum "1528.75" {
               description "1528.75 nm/196.103125 THz 3.125GHz spacing";
             }
             enum "1528.72" {
               description "1528.72 nm/196.106250 THz 3.125/6.25GHz spacing";
             }
             enum "1528.70" {
               description "1528.70 nm/196.109375 THz 3.125GHz spacing";
             }
             enum "1528.68" {
               description "1528.68 nm/196.112500 THz 3.125/6.25/12.5GHz spacing";
             }
             enum "1528.65" {
               description "1528.65 nm/196.115625 THz 3.125GHz spacing";
             }
             enum "1528.63" {
               description "1528.63 nm/196.118750 THz 3.125/6.25GHz spacing";
             }
             enum "1528.60" {
               description "1528.60 nm/196.121875 THz 3.125GHz spacing";
             }
             enum "1528.58" {
               description "1528.58 nm/196.125000 THz 3.125/6.25/12.5/75GHz spacing";
             }
             enum "1528.55" {
               description "1528.55 nm/196.128125 THz 3.125GHz spacing";
             }
             enum "1528.53" {
               description "1528.53 nm/196.131250 THz 3.125/6.25GHz spacing";
             }
             enum "1528.51" {
               description "1528.51 nm/196.134375 THz 3.125GHz spacing";
             }
             enum "1528.48" {
               description "1528.48 nm/196.137500 THz 3.125/6.25/12.5GHz spacing";
             }
             enum "1528.46" {
               description "1528.46 nm/196.140625 THz 3.125GHz spacing";
             }
             enum "1528.43" {
               description "1528.43 nm/196.143750 THz 3.125/6.25GHz spacing";
             }
             enum "1528.41" {
               description "1528.41 nm/196.146875 THz 3.125GHz spacing";
             }
             enum "1528.38" {
               description "1528.38 nm/196.15040 THz 50Ghz spacing";
             }
           }
         }
       }
       case case_2 {
         leaf frequency {
           description "Optical channel frequency in terahertz";
           type enumeration {
             enum "191.1003" {
               description "191.1003 THz/1568.77 nm 50/100Ghz spacing";
             }
             enum "191.15000" {
               description "191.15000 THz/1568.36 nm 6.25/12.5/50GHz spacing";
             }
             enum "191.15625" {
               description "191.15625 THz/1568.31 nm 6.25GHz spacing";
             }
             enum "191.16250" {
               description "191.16250 THz/1568.26 nm 6.25/12.5GHz spacing";
             }
             enum "191.16875" {
               description "191.16875 THz/1568.21 nm 6.25GHz spacing";
             }
             enum "191.17500" {
               description "191.17500 THz/1568.16 nm 6.25/12.5GHz spacing";
             }
             enum "191.18125" {
               description "191.18125 THz/1568.11 nm 6.25GHz spacing";
             }
             enum "191.18750" {
               description "191.18750 THz/1568.05 nm 6.25/12.5GHz spacing";
             }
             enum "191.19375" {
               description "191.19375 THz/1568.00 nm 6.25GHz spacing";
             }
             enum "191.20000" {
               description "191.20000 THz/1567.95 nm 6.25/12.5/50/100GHz spacing";
             }
             enum "191.20625" {
               description "191.20625 THz/1567.90 nm 6.25GHz spacing";
             }
             enum "191.21250" {
               description "191.21250 THz/1567.85 nm 6.25/12.5GHz spacing";
             }
             enum "191.21875" {
               description "191.21875 THz/1567.80 nm 6.25GHz spacing";
             }
             enum "191.22500" {
               description "191.22500 THz/1567.75 nm 6.25/12.5GHz spacing";
             }
             enum "191.23125" {
               description "191.23125 THz/1567.70 nm 6.25GHz spacing";
             }
             enum "191.23750" {
               description "191.23750 THz/1567.64 nm 6.25/12.5GHz spacing";
             }
             enum "191.24375" {
               description "191.24375 THz/1567.59 nm 6.25GHz spacing";
             }
             enum "191.25000" {
               description "191.25000 THz/1567.54 nm 6.25/12.5/50GHz spacing";
             }
             enum "191.25625" {
               description "191.25625 THz/1567.49 nm 6.25GHz spacing";
             }
             enum "191.26250" {
               description "191.26250 THz/1567.44 nm 6.25/12.5GHz spacing";
             }
             enum "191.26875" {
               description "191.26875 THz/1567.39 nm 6.25GHz spacing";
             }
             enum "191.27500" {
               description "191.27500 THz/1567.34 nm 6.25/12.5GHz spacing";
             }
             enum "191.28125" {
               description "191.28125 THz/1567.29 nm 6.25GHz spacing";
             }
             enum "191.28750" {
               description "191.28750 THz/1567.23 nm 6.25/12.5GHz spacing";
             }
             enum "191.29375" {
               description "191.29375 THz/1567.18 nm 6.25GHz spacing";
             }
             enum "191.30000" {
               description "191.30000 THz/1567.13 nm 6.25/12.5/50/100GHz spacing";
             }
             enum "191.30625" {
               description "191.30625 THz/1567.08 nm 6.25GHz spacing";
             }
             enum "191.31250" {
               description "191.31250 THz/1567.03 nm 6.25/12.5GHz spacing";
             }
             enum "191.31875" {
               description "191.31875 THz/1566.98 nm 6.25GHz spacing";
             }
             enum "191.32500" {
               description "191.32500 THz/1566.93 nm 6.25/12.5GHz spacing";
             }
             enum "191.33125" {
               description "191.33125 THz/1566.88 nm 6.25GHz spacing";
             }
             enum "191.33750" {
               description "191.33750 THz/1566.83 nm 6.25/12.5GHz spacing";
             }
             enum "191.34375" {
               description "191.34375 THz/1566.77 nm 6.25GHz spacing";
             }
             enum "191.35000" {
               description "191.35000 THz/1566.72 nm 6.25/12.5/50GHz spacing";
             }
             enum "191.35625" {
               description "191.35625 THz/1566.67 nm 6.25GHz spacing";
             }
             enum "191.36250" {
               description "191.36250 THz/1566.62 nm 6.25/12.5GHz spacing";
             }
             enum "191.36875" {
               description "191.36875 THz/1566.57 nm 6.25GHz spacing";
             }
             enum "191.37500" {
               description "191.37500 THz/1566.52 nm 6.25/12.5/75GHz spacing";
             }
             enum "191.38125" {
               description "191.38125 THz/1566.47 nm 6.25GHz spacing";
             }
             enum "191.38750" {
               description "191.38750 THz/1566.42 nm 6.25/12.5GHz spacing";
             }
             enum "191.39375" {
               description "191.39375 THz/1566.36 nm 6.25GHz spacing";
             }
             enum "191.40000" {
               description "191.40000 THz/1566.31 nm 6.25/12.5/50/100GHz spacing";
             }
             enum "191.40625" {
               description "191.40625 THz/1566.26 nm 6.25GHz spacing";
             }
             enum "191.41250" {
               description "191.41250 THz/1566.21 nm 6.25/12.5GHz spacing";
             }
             enum "191.41875" {
               description "191.41875 THz/1566.16 nm 6.25GHz spacing";
             }
             enum "191.42500" {
               description "191.42500 THz/1566.11 nm 6.25/12.5GHz spacing";
             }
             enum "191.43125" {
               description "191.43125 THz/1566.06 nm 6.25GHz spacing";
             }
             enum "191.43750" {
               description "191.43750 THz/1566.01 nm 6.25/12.5GHz spacing";
             }
             enum "191.44375" {
               description "191.44375 THz/1565.96 nm 6.25GHz spacing";
             }
             enum "191.45000" {
               description "191.45000 THz/1565.90 nm 6.25/12.5/50/75GHz spacing";
             }
             enum "191.45625" {
               description "191.45625 THz/1565.85 nm 6.25GHz spacing";
             }
             enum "191.46250" {
               description "191.46250 THz/1565.80 nm 6.25/12.5GHz spacing";
             }
             enum "191.46875" {
               description "191.46875 THz/1565.75 nm 6.25GHz spacing";
             }
             enum "191.47500" {
               description "191.47500 THz/1565.70 nm 6.25/12.5GHz spacing";
             }
             enum "191.48125" {
               description "191.48125 THz/1565.65 nm 6.25GHz spacing";
             }
             enum "191.48750" {
               description "191.48750 THz/1565.60 nm 6.25/12.5GHz spacing";
             }
             enum "191.49375" {
               description "191.49375 THz/1565.55 nm 6.25GHz spacing";
             }
             enum "191.50000" {
               description "191.50000 THz/1565.50 nm 6.25/12.5/50/100GHz spacing";
             }
             enum "191.50625" {
               description "191.50625 THz/1565.44 nm 6.25GHz spacing";
             }
             enum "191.51250" {
               description "191.51250 THz/1565.39 nm 6.25/12.5GHz spacing";
             }
             enum "191.51875" {
               description "191.51875 THz/1565.34 nm 6.25GHz spacing";
             }
             enum "191.52500" {
               description "191.52500 THz/1565.29 nm 6.25/12.5/75GHz spacing";
             }
             enum "191.53125" {
               description "191.53125 THz/1565.24 nm 6.25GHz spacing";
             }
             enum "191.53750" {
               description "191.53750 THz/1565.19 nm 6.25/12.5GHz spacing";
             }
             enum "191.54375" {
               description "191.54375 THz/1565.14 nm 6.25GHz spacing";
             }
             enum "191.55000" {
               description "191.55000 THz/1565.09 nm 6.25/12.5/50GHz spacing";
             }
             enum "191.55625" {
               description "191.55625 THz/1565.04 nm 6.25GHz spacing";
             }
             enum "191.56250" {
               description "191.56250 THz/1564.99 nm 6.25/12.5GHz spacing";
             }
             enum "191.56875" {
               description "191.56875 THz/1564.93 nm 6.25GHz spacing";
             }
             enum "191.57500" {
               description "191.57500 THz/1564.88 nm 6.25/12.5GHz spacing";
             }
             enum "191.58125" {
               description "191.58125 THz/1564.83 nm 6.25GHz spacing";
             }
             enum "191.58750" {
               description "191.58750 THz/1564.78 nm 6.25/12.5GHz spacing";
             }
             enum "191.59375" {
               description "191.59375 THz/1564.73 nm 6.25GHz spacing";
             }
             enum "191.60000" {
               description "191.60000 THz/1564.68 nm 6.25/12.5/50/75/100GHz spacing";
             }
             enum "191.60625" {
               description "191.60625 THz/1564.63 nm 6.25GHz spacing";
             }
             enum "191.61250" {
               description "191.61250 THz/1564.58 nm 6.25/12.5GHz spacing";
             }
             enum "191.61875" {
               description "191.61875 THz/1564.53 nm 6.25GHz spacing";
             }
             enum "191.62500" {
               description "191.62500 THz/1564.47 nm 6.25/12.5GHz spacing";
             }
             enum "191.63125" {
               description "191.63125 THz/1564.42 nm 6.25GHz spacing";
             }
             enum "191.63750" {
               description "191.63750 THz/1564.37 nm 6.25/12.5GHz spacing";
             }
             enum "191.64375" {
               description "191.64375 THz/1564.32 nm 6.25GHz spacing";
             }
             enum "191.65000" {
               description "191.65000 THz/1564.27 nm 6.25/12.5/50GHz spacing";
             }
             enum "191.65625" {
               description "191.65625 THz/1564.22 nm 6.25GHz spacing";
             }
             enum "191.66250" {
               description "191.66250 THz/1564.17 nm 6.25/12.5GHz spacing";
             }
             enum "191.66875" {
               description "191.66875 THz/1564.12 nm 6.25GHz spacing";
             }
             enum "191.67500" {
               description "191.67500 THz/1564.07 nm 6.25/12.5/75GHz spacing";
             }
             enum "191.68125" {
               description "191.68125 THz/1564.02 nm 6.25GHz spacing";
             }
             enum "191.68750" {
               description "191.68750 THz/1563.96 nm 6.25/12.5GHz spacing";
             }
             enum "191.69375" {
               description "191.69375 THz/1563.91 nm 6.25GHz spacing";
             }
             enum "191.70000" {
               description "191.70000 THz/1563.86 nm 6.25/12.5/50/100GHz spacing";
             }
             enum "191.70625" {
               description "191.70625 THz/1563.81 nm 6.25GHz spacing";
             }
             enum "191.71250" {
               description "191.71250 THz/1563.76 nm 6.25/12.5GHz spacing";
             }
             enum "191.71875" {
               description "191.71875 THz/1563.71 nm 6.25GHz spacing";
             }
             enum "191.72500" {
               description "191.72500 THz/1563.66 nm 6.25/12.5GHz spacing";
             }
             enum "191.73125" {
               description "191.73125 THz/1563.61 nm 6.25GHz spacing";
             }
             enum "191.73750" {
               description "191.73750 THz/1563.56 nm 6.25/12.5GHz spacing";
             }
             enum "191.74375" {
               description "191.74375 THz/1563.51 nm 6.25GHz spacing";
             }
             enum "191.75000" {
               description "191.75000 THz/1563.45 nm 6.25/12.5/50/75GHz spacing";
             }
             enum "191.75625" {
               description "191.75625 THz/1563.40 nm 6.25GHz spacing";
             }
             enum "191.76250" {
               description "191.76250 THz/1563.35 nm 6.25/12.5GHz spacing";
             }
             enum "191.76875" {
               description "191.76875 THz/1563.30 nm 6.25GHz spacing";
             }
             enum "191.77500" {
               description "191.77500 THz/1563.25 nm 6.25/12.5GHz spacing";
             }
             enum "191.78125" {
               description "191.78125 THz/1563.20 nm 6.25GHz spacing";
             }
             enum "191.78750" {
               description "191.78750 THz/1563.15 nm 6.25/12.5GHz spacing";
             }
             enum "191.79375" {
               description "191.79375 THz/1563.10 nm 6.25GHz spacing";
             }
             enum "191.80000" {
               description "191.80000 THz/1563.05 nm 6.25/12.5/50/100GHz spacing";
             }
             enum "191.80625" {
               description "191.80625 THz/1563.00 nm 6.25GHz spacing";
             }
             enum "191.81250" {
               description "191.81250 THz/1562.95 nm 6.25/12.5GHz spacing";
             }
             enum "191.81875" {
               description "191.81875 THz/1562.89 nm 6.25GHz spacing";
             }
             enum "191.82500" {
               description "191.82500 THz/1562.84 nm 6.25/12.5/75GHz spacing";
             }
             enum "191.83125" {
               description "191.83125 THz/1562.79 nm 6.25GHz spacing";
             }
             enum "191.83750" {
               description "191.83750 THz/1562.74 nm 6.25/12.5GHz spacing";
             }
             enum "191.84375" {
               description "191.84375 THz/1562.69 nm 6.25GHz spacing";
             }
             enum "191.85000" {
               description "191.85000 THz/1562.64 nm 6.25/12.5/50GHz spacing";
             }
             enum "191.85625" {
               description "191.85625 THz/1562.59 nm 6.25GHz spacing";
             }
             enum "191.86250" {
               description "191.86250 THz/1562.54 nm 6.25/12.5GHz spacing";
             }
             enum "191.86875" {
               description "191.86875 THz/1562.49 nm 6.25GHz spacing";
             }
             enum "191.87500" {
               description "191.87500 THz/1562.44 nm 6.25/12.5GHz spacing";
             }
             enum "191.88125" {
               description "191.88125 THz/1562.39 nm 6.25GHz spacing";
             }
             enum "191.88750" {
               description "191.88750 THz/1562.33 nm 6.25/12.5GHz spacing";
             }
             enum "191.89375" {
               description "191.89375 THz/1562.28 nm 6.25GHz spacing";
             }
             enum "191.90000" {
               description "191.90000 THz/1562.23 nm 6.25/12.5/50/75/100GHz spacing";
             }
             enum "191.90625" {
               description "191.90625 THz/1562.18 nm 6.25GHz spacing";
             }
             enum "191.91250" {
               description "191.91250 THz/1562.13 nm 6.25/12.5GHz spacing";
             }
             enum "191.91875" {
               description "191.91875 THz/1562.08 nm 6.25GHz spacing";
             }
             enum "191.92500" {
               description "191.92500 THz/1562.03 nm 6.25/12.5GHz spacing";
             }
             enum "191.93125" {
               description "191.93125 THz/1561.98 nm 6.25GHz spacing";
             }
             enum "191.93750" {
               description "191.93750 THz/1561.93 nm 6.25/12.5GHz spacing";
             }
             enum "191.94375" {
               description "191.94375 THz/1561.88 nm 6.25GHz spacing";
             }
             enum "191.95000" {
               description "191.95000 THz/1561.83 nm 6.25/12.5/50GHz spacing";
             }
             enum "191.95625" {
               description "191.95625 THz/1561.77 nm 6.25GHz spacing";
             }
             enum "191.96250" {
               description "191.96250 THz/1561.72 nm 6.25/12.5GHz spacing";
             }
             enum "191.96875" {
               description "191.96875 THz/1561.67 nm 6.25GHz spacing";
             }
             enum "191.97500" {
               description "191.97500 THz/1561.62 nm 6.25/12.5/75GHz spacing";
             }
             enum "191.98125" {
               description "191.98125 THz/1561.57 nm 6.25GHz spacing";
             }
             enum "191.98750" {
               description "191.98750 THz/1561.52 nm 6.25/12.5GHz spacing";
             }
             enum "191.99375" {
               description "191.99375 THz/1561.47 nm 6.25GHz spacing";
             }
             enum "192.00000" {
               description "192.00000 THz/1561.42 nm 6.25/12.5/50/100GHz spacing";
             }
             enum "192.00625" {
               description "192.00625 THz/1561.37 nm 6.25GHz spacing";
             }
             enum "192.01250" {
               description "192.01250 THz/1561.32 nm 6.25/12.5GHz spacing";
             }
             enum "192.01875" {
               description "192.01875 THz/1561.27 nm 6.25GHz spacing";
             }
             enum "192.02500" {
               description "192.02500 THz/1561.22 nm 6.25/12.5GHz spacing";
             }
             enum "192.03125" {
               description "192.03125 THz/1561.16 nm 6.25GHz spacing";
             }
             enum "192.03750" {
               description "192.03750 THz/1561.11 nm 6.25/12.5GHz spacing";
             }
             enum "192.04375" {
               description "192.04375 THz/1561.06 nm 6.25GHz spacing";
             }
             enum "192.05000" {
               description "192.05000 THz/1561.01 nm 6.25/12.5/50/75GHz spacing";
             }
             enum "192.05625" {
               description "192.05625 THz/1560.96 nm 6.25GHz spacing";
             }
             enum "192.06250" {
               description "192.06250 THz/1560.91 nm 6.25/12.5GHz spacing";
             }
             enum "192.06875" {
               description "192.06875 THz/1560.86 nm 6.25GHz spacing";
             }
             enum "192.07500" {
               description "192.07500 THz/1560.81 nm 6.25/12.5GHz spacing";
             }
             enum "192.08125" {
               description "192.08125 THz/1560.76 nm 6.25GHz spacing";
             }
             enum "192.08750" {
               description "192.08750 THz/1560.71 nm 6.25/12.5GHz spacing";
             }
             enum "192.09375" {
               description "192.09375 THz/1560.66 nm 6.25GHz spacing";
             }
             enum "192.10000" {
               description "192.10000 THz/1560.61 nm 6.25/12.5/50/100GHz spacing";
             }
             enum "192.10625" {
               description "192.10625 THz/1560.56 nm 6.25GHz spacing";
             }
             enum "192.11250" {
               description "192.11250 THz/1560.50 nm 6.25/12.5GHz spacing";
             }
             enum "192.11875" {
               description "192.11875 THz/1560.45 nm 6.25GHz spacing";
             }
             enum "192.12500" {
               description "192.12500 THz/1560.40 nm 6.25/12.5/75GHz spacing";
             }
             enum "192.13125" {
               description "192.13125 THz/1560.35 nm 6.25GHz spacing";
             }
             enum "192.13750" {
               description "192.13750 THz/1560.30 nm 6.25/12.5GHz spacing";
             }
             enum "192.14375" {
               description "192.14375 THz/1560.25 nm 6.25GHz spacing";
             }
             enum "192.15000" {
               description "192.15000 THz/1560.20 nm 6.25/12.5/50GHz spacing";
             }
             enum "192.15625" {
               description "192.15625 THz/1560.15 nm 6.25GHz spacing";
             }
             enum "192.16250" {
               description "192.16250 THz/1560.10 nm 6.25/12.5GHz spacing";
             }
             enum "192.16875" {
               description "192.16875 THz/1560.05 nm 6.25GHz spacing";
             }
             enum "192.17500" {
               description "192.17500 THz/1560.00 nm 6.25/12.5GHz spacing";
             }
             enum "192.18125" {
               description "192.18125 THz/1559.95 nm 6.25GHz spacing";
             }
             enum "192.18750" {
               description "192.18750 THz/1559.90 nm 6.25/12.5GHz spacing";
             }
             enum "192.19375" {
               description "192.19375 THz/1559.84 nm 6.25GHz spacing";
             }
             enum "192.20000" {
               description "192.20000 THz/1559.79 nm 6.25/12.5/50/75/100GHz spacing";
             }
             enum "192.20625" {
               description "192.20625 THz/1559.74 nm 6.25GHz spacing";
             }
             enum "192.21250" {
               description "192.21250 THz/1559.69 nm 6.25/12.5GHz spacing";
             }
             enum "192.21875" {
               description "192.21875 THz/1559.64 nm 6.25GHz spacing";
             }
             enum "192.22500" {
               description "192.22500 THz/1559.59 nm 6.25/12.5GHz spacing";
             }
             enum "192.23125" {
               description "192.23125 THz/1559.54 nm 6.25GHz spacing";
             }
             enum "192.23750" {
               description "192.23750 THz/1559.49 nm 6.25/12.5GHz spacing";
             }
             enum "192.24375" {
               description "192.24375 THz/1559.44 nm 6.25GHz spacing";
             }
             enum "192.25000" {
               description "192.25000 THz/1559.39 nm 6.25/12.5/50GHz spacing";
             }
             enum "192.25625" {
               description "192.25625 THz/1559.34 nm 6.25GHz spacing";
             }
             enum "192.26250" {
               description "192.26250 THz/1559.29 nm 6.25/12.5GHz spacing";
             }
             enum "192.26875" {
               description "192.26875 THz/1559.24 nm 6.25GHz spacing";
             }
             enum "192.27500" {
               description "192.27500 THz/1559.19 nm 6.25/12.5GHz spacing";
             }
             enum "192.28125" {
               description "192.28125 THz/1559.14 nm 6.25GHz spacing";
             }
             enum "192.28750" {
               description "192.28750 THz/1559.08 nm 6.25/12.5GHz spacing";
             }
             enum "192.29375" {
               description "192.29375 THz/1559.03 nm 6.25GHz spacing";
             }
             enum "192.30000" {
               description "192.30000 THz/1558.98 nm 6.25/12.5/50/100GHz spacing";
             }
             enum "192.30625" {
               description "192.30625 THz/1558.93 nm 6.25GHz spacing";
             }
             enum "192.31250" {
               description "192.31250 THz/1558.88 nm 6.25/12.5GHz spacing";
             }
             enum "192.31875" {
               description "192.31875 THz/1558.83 nm 6.25GHz spacing";
             }
             enum "192.32500" {
               description "192.32500 THz/1558.78 nm 6.25/12.5GHz spacing";
             }
             enum "192.33125" {
               description "192.33125 THz/1558.73 nm 6.25GHz spacing";
             }
             enum "192.33750" {
               description "192.33750 THz/1558.68 nm 6.25/12.5GHz spacing";
             }
             enum "192.34375" {
               description "192.34375 THz/1558.63 nm 6.25GHz spacing";
             }
             enum "192.35000" {
               description "192.35000 THz/1558.58 nm 6.25/12.5/50/75GHz spacing";
             }
             enum "192.35625" {
               description "192.35625 THz/1558.53 nm 6.25GHz spacing";
             }
             enum "192.36250" {
               description "192.36250 THz/1558.48 nm 6.25/12.5GHz spacing";
             }
             enum "192.36875" {
               description "192.36875 THz/1558.43 nm 6.25GHz spacing";
             }
             enum "192.37500" {
               description "192.37500 THz/1558.38 nm 6.25/12.5GHz spacing";
             }
             enum "192.38125" {
               description "192.38125 THz/1558.32 nm 6.25GHz spacing";
             }
             enum "192.38750" {
               description "192.38750 THz/1558.27 nm 6.25/12.5GHz spacing";
             }
             enum "192.39375" {
               description "192.39375 THz/1558.22 nm 6.25GHz spacing";
             }
             enum "192.40000" {
               description "192.40000 THz/1558.17 nm 6.25/12.5/50/100GHz spacing";
             }
             enum "192.40625" {
               description "192.40625 THz/1558.12 nm 6.25GHz spacing";
             }
             enum "192.41250" {
               description "192.41250 THz/1558.07 nm 6.25/12.5GHz spacing";
             }
             enum "192.41875" {
               description "192.41875 THz/1558.02 nm 6.25GHz spacing";
             }
             enum "192.42500" {
               description "192.42500 THz/1557.97 nm 6.25/12.5/75GHz spacing";
             }
             enum "192.43125" {
               description "192.43125 THz/1557.92 nm 6.25GHz spacing";
             }
             enum "192.43750" {
               description "192.43750 THz/1557.87 nm 6.25/12.5GHz spacing";
             }
             enum "192.44375" {
               description "192.44375 THz/1557.82 nm 6.25GHz spacing";
             }
             enum "192.45000" {
               description "192.45000 THz/1557.77 nm 6.25/12.5/50GHz spacing";
             }
             enum "192.45625" {
               description "192.45625 THz/1557.72 nm 6.25GHz spacing";
             }
             enum "192.46250" {
               description "192.46250 THz/1557.67 nm 6.25/12.5GHz spacing";
             }
             enum "192.46875" {
               description "192.46875 THz/1557.62 nm 6.25GHz spacing";
             }
             enum "192.47500" {
               description "192.47500 THz/1557.57 nm 6.25/12.5GHz spacing";
             }
             enum "192.48125" {
               description "192.48125 THz/1557.52 nm 6.25GHz spacing";
             }
             enum "192.48750" {
               description "192.48750 THz/1557.46 nm 6.25/12.5GHz spacing";
             }
             enum "192.49375" {
               description "192.49375 THz/1557.41 nm 6.25GHz spacing";
             }
             enum "192.50000" {
               description "192.50000 THz/1557.36 nm 6.25/12.5/50/75/100GHz spacing";
             }
             enum "192.50625" {
               description "192.50625 THz/1557.31 nm 6.25GHz spacing";
             }
             enum "192.51250" {
               description "192.51250 THz/1557.26 nm 6.25/12.5GHz spacing";
             }
             enum "192.51875" {
               description "192.51875 THz/1557.21 nm 6.25GHz spacing";
             }
             enum "192.52500" {
               description "192.52500 THz/1557.16 nm 6.25/12.5GHz spacing";
             }
             enum "192.53125" {
               description "192.53125 THz/1557.11 nm 6.25GHz spacing";
             }
             enum "192.53750" {
               description "192.53750 THz/1557.06 nm 6.25/12.5GHz spacing";
             }
             enum "192.54375" {
               description "192.54375 THz/1557.01 nm 6.25GHz spacing";
             }
             enum "192.55000" {
               description "192.55000 THz/1556.96 nm 6.25/12.5/50GHz spacing";
             }
             enum "192.55625" {
               description "192.55625 THz/1556.91 nm 6.25GHz spacing";
             }
             enum "192.56250" {
               description "192.56250 THz/1556.86 nm 6.25/12.5GHz spacing";
             }
             enum "192.56875" {
               description "192.56875 THz/1556.81 nm 6.25GHz spacing";
             }
             enum "192.57500" {
               description "192.57500 THz/1556.76 nm 6.25/12.5/75GHz spacing";
             }
             enum "192.58125" {
               description "192.58125 THz/1556.71 nm 6.25GHz spacing";
             }
             enum "192.58750" {
               description "192.58750 THz/1556.66 nm 6.25/12.5GHz spacing";
             }
             enum "192.59375" {
               description "192.59375 THz/1556.61 nm 6.25GHz spacing";
             }
             enum "192.60000" {
               description "192.60000 THz/1556.55 nm 6.25/12.5/50/100GHz spacing";
             }
             enum "192.60625" {
               description "192.60625 THz/1556.50 nm 6.25GHz spacing";
             }
             enum "192.61250" {
               description "192.61250 THz/1556.45 nm 6.25/12.5GHz spacing";
             }
             enum "192.61875" {
               description "192.61875 THz/1556.40 nm 6.25GHz spacing";
             }
             enum "192.62500" {
               description "192.62500 THz/1556.35 nm 6.25/12.5GHz spacing";
             }
             enum "192.63125" {
               description "192.63125 THz/1556.30 nm 6.25GHz spacing";
             }
             enum "192.63750" {
               description "192.63750 THz/1556.25 nm 6.25/12.5GHz spacing";
             }
             enum "192.64375" {
               description "192.64375 THz/1556.20 nm 6.25GHz spacing";
             }
             enum "192.65000" {
               description "192.65000 THz/1556.15 nm 6.25/12.5/50/75GHz spacing";
             }
             enum "192.65625" {
               description "192.65625 THz/1556.10 nm 6.25GHz spacing";
             }
             enum "192.66250" {
               description "192.66250 THz/1556.05 nm 6.25/12.5GHz spacing";
             }
             enum "192.66875" {
               description "192.66875 THz/1556.00 nm 6.25GHz spacing";
             }
             enum "192.67500" {
               description "192.67500 THz/1555.95 nm 6.25/12.5GHz spacing";
             }
             enum "192.68125" {
               description "192.68125 THz/1555.90 nm 6.25GHz spacing";
             }
             enum "192.68750" {
               description "192.68750 THz/1555.85 nm 6.25/12.5GHz spacing";
             }
             enum "192.69375" {
               description "192.69375 THz/1555.80 nm 6.25GHz spacing";
             }
             enum "192.70000" {
               description "192.70000 THz/1555.75 nm 6.25/12.5/50/100GHz spacing";
             }
             enum "192.70625" {
               description "192.70625 THz/1555.70 nm 6.25GHz spacing";
             }
             enum "192.71250" {
               description "192.71250 THz/1555.65 nm 6.25/12.5GHz spacing";
             }
             enum "192.71875" {
               description "192.71875 THz/1555.60 nm 6.25GHz spacing";
             }
             enum "192.72500" {
               description "192.72500 THz/1555.55 nm 6.25/12.5/75GHz spacing";
             }
             enum "192.73125" {
               description "192.73125 THz/1555.49 nm 6.25GHz spacing";
             }
             enum "192.73750" {
               description "192.73750 THz/1555.44 nm 6.25/12.5GHz spacing";
             }
             enum "192.74375" {
               description "192.74375 THz/1555.39 nm 6.25GHz spacing";
             }
             enum "192.75000" {
               description "192.75000 THz/1555.34 nm 6.25/12.5/50GHz spacing";
             }
             enum "192.75625" {
               description "192.75625 THz/1555.29 nm 6.25GHz spacing";
             }
             enum "192.76250" {
               description "192.76250 THz/1555.24 nm 6.25/12.5GHz spacing";
             }
             enum "192.76875" {
               description "192.76875 THz/1555.19 nm 6.25GHz spacing";
             }
             enum "192.77500" {
               description "192.77500 THz/1555.14 nm 6.25/12.5GHz spacing";
             }
             enum "192.78125" {
               description "192.78125 THz/1555.09 nm 6.25GHz spacing";
             }
             enum "192.78750" {
               description "192.78750 THz/1555.04 nm 6.25/12.5GHz spacing";
             }
             enum "192.79375" {
               description "192.79375 THz/1554.99 nm 6.25GHz spacing";
             }
             enum "192.80000" {
               description "192.80000 THz/1554.94 nm 6.25/12.5/50/75/100GHz spacing";
             }
             enum "192.80625" {
               description "192.80625 THz/1554.89 nm 6.25GHz spacing";
             }
             enum "192.81250" {
               description "192.81250 THz/1554.84 nm 6.25/12.5GHz spacing";
             }
             enum "192.81875" {
               description "192.81875 THz/1554.79 nm 6.25GHz spacing";
             }
             enum "192.82500" {
               description "192.82500 THz/1554.74 nm 6.25/12.5GHz spacing";
             }
             enum "192.83125" {
               description "192.83125 THz/1554.69 nm 6.25GHz spacing";
             }
             enum "192.83750" {
               description "192.83750 THz/1554.64 nm 6.25/12.5GHz spacing";
             }
             enum "192.84375" {
               description "192.84375 THz/1554.59 nm 6.25GHz spacing";
             }
             enum "192.85000" {
               description "192.85000 THz/1554.54 nm 6.25/12.5/50GHz spacing";
             }
             enum "192.85625" {
               description "192.85625 THz/1554.49 nm 6.25GHz spacing";
             }
             enum "192.86250" {
               description "192.86250 THz/1554.44 nm 6.25/12.5GHz spacing";
             }
             enum "192.86875" {
               description "192.86875 THz/1554.39 nm 6.25GHz spacing";
             }
             enum "192.87500" {
               description "192.87500 THz/1554.34 nm 6.25/12.5/75GHz spacing";
             }
             enum "192.88125" {
               description "192.88125 THz/1554.29 nm 6.25GHz spacing";
             }
             enum "192.88750" {
               description "192.88750 THz/1554.23 nm 6.25/12.5GHz spacing";
             }
             enum "192.89375" {
               description "192.89375 THz/1554.18 nm 6.25GHz spacing";
             }
             enum "192.90000" {
               description "192.90000 THz/1554.13 nm 6.25/12.5/50/100GHz spacing";
             }
             enum "192.90625" {
               description "192.90625 THz/1554.08 nm 6.25GHz spacing";
             }
             enum "192.91250" {
               description "192.91250 THz/1554.03 nm 6.25/12.5GHz spacing";
             }
             enum "192.91875" {
               description "192.91875 THz/1553.98 nm 6.25GHz spacing";
             }
             enum "192.92500" {
               description "192.92500 THz/1553.93 nm 6.25/12.5GHz spacing";
             }
             enum "192.93125" {
               description "192.93125 THz/1553.88 nm 6.25GHz spacing";
             }
             enum "192.93750" {
               description "192.93750 THz/1553.83 nm 6.25/12.5GHz spacing";
             }
             enum "192.94375" {
               description "192.94375 THz/1553.78 nm 6.25GHz spacing";
             }
             enum "192.95000" {
               description "192.95000 THz/1553.73 nm 6.25/12.5/50/75GHz spacing";
             }
             enum "192.95625" {
               description "192.95625 THz/1553.68 nm 6.25GHz spacing";
             }
             enum "192.96250" {
               description "192.96250 THz/1553.63 nm 6.25/12.5GHz spacing";
             }
             enum "192.96875" {
               description "192.96875 THz/1553.58 nm 6.25GHz spacing";
             }
             enum "192.97500" {
               description "192.97500 THz/1553.53 nm 6.25/12.5GHz spacing";
             }
             enum "192.98125" {
               description "192.98125 THz/1553.48 nm 6.25GHz spacing";
             }
             enum "192.98750" {
               description "192.98750 THz/1553.43 nm 6.25/12.5GHz spacing";
             }
             enum "192.99375" {
               description "192.99375 THz/1553.38 nm 6.25GHz spacing";
             }
             enum "193.00000" {
               description "193.00000 THz/1553.33 nm 6.25/12.5/50/100GHz spacing";
             }
             enum "193.00625" {
               description "193.00625 THz/1553.28 nm 6.25GHz spacing";
             }
             enum "193.01250" {
               description "193.01250 THz/1553.23 nm 6.25/12.5GHz spacing";
             }
             enum "193.01875" {
               description "193.01875 THz/1553.18 nm 6.25GHz spacing";
             }
             enum "193.02500" {
               description "193.02500 THz/1553.13 nm 6.25/12.5/75GHz spacing";
             }
             enum "193.03125" {
               description "193.03125 THz/1553.08 nm 6.25GHz spacing";
             }
             enum "193.03750" {
               description "193.03750 THz/1553.03 nm 6.25/12.5GHz spacing";
             }
             enum "193.04375" {
               description "193.04375 THz/1552.98 nm 6.25GHz spacing";
             }
             enum "193.05000" {
               description "193.05000 THz/1552.93 nm 6.25/12.5/50GHz spacing";
             }
             enum "193.05625" {
               description "193.05625 THz/1552.88 nm 6.25GHz spacing";
             }
             enum "193.06250" {
               description "193.06250 THz/1552.83 nm 6.25/12.5GHz spacing";
             }
             enum "193.06875" {
               description "193.06875 THz/1552.78 nm 6.25GHz spacing";
             }
             enum "193.07500" {
               description "193.07500 THz/1552.73 nm 6.25/12.5GHz spacing";
             }
             enum "193.08125" {
               description "193.08125 THz/1552.68 nm 6.25GHz spacing";
             }
             enum "193.08750" {
               description "193.08750 THz/1552.62 nm 6.25/12.5GHz spacing";
             }
             enum "193.09375" {
               description "193.09375 THz/1552.57 nm 6.25GHz spacing";
             }
             enum "193.10000" {
               description "193.10000 THz/1552.52 nm 6.25/12.5/50/75/100GHz spacing";
             }
             enum "193.10625" {
               description "193.10625 THz/1552.47 nm 6.25GHz spacing";
             }
             enum "193.11250" {
               description "193.11250 THz/1552.42 nm 6.25/12.5GHz spacing";
             }
             enum "193.11875" {
               description "193.11875 THz/1552.37 nm 6.25GHz spacing";
             }
             enum "193.12500" {
               description "193.12500 THz/1552.32 nm 6.25/12.5GHz spacing";
             }
             enum "193.13125" {
               description "193.13125 THz/1552.27 nm 6.25GHz spacing";
             }
             enum "193.13750" {
               description "193.13750 THz/1552.22 nm 6.25/12.5GHz spacing";
             }
             enum "193.14375" {
               description "193.14375 THz/1552.17 nm 6.25GHz spacing";
             }
             enum "193.15000" {
               description "193.15000 THz/1552.12 nm 6.25/12.5/50GHz spacing";
             }
             enum "193.15625" {
               description "193.15625 THz/1552.07 nm 6.25GHz spacing";
             }
             enum "193.16250" {
               description "193.16250 THz/1552.02 nm 6.25/12.5GHz spacing";
             }
             enum "193.16875" {
               description "193.16875 THz/1551.97 nm 6.25GHz spacing";
             }
             enum "193.17500" {
               description "193.17500 THz/1551.92 nm 6.25/12.5/75GHz spacing";
             }
             enum "193.18125" {
               description "193.18125 THz/1551.87 nm 6.25GHz spacing";
             }
             enum "193.18750" {
               description "193.18750 THz/1551.82 nm 6.25/12.5GHz spacing";
             }
             enum "193.19375" {
               description "193.19375 THz/1551.77 nm 6.25GHz spacing";
             }
             enum "193.20000" {
               description "193.20000 THz/1551.72 nm 6.25/12.5/50/100GHz spacing";
             }
             enum "193.20625" {
               description "193.20625 THz/1551.67 nm 6.25GHz spacing";
             }
             enum "193.21250" {
               description "193.21250 THz/1551.62 nm 6.25/12.5GHz spacing";
             }
             enum "193.21875" {
               description "193.21875 THz/1551.57 nm 6.25GHz spacing";
             }
             enum "193.22500" {
               description "193.22500 THz/1551.52 nm 6.25/12.5GHz spacing";
             }
             enum "193.23125" {
               description "193.23125 THz/1551.47 nm 6.25GHz spacing";
             }
             enum "193.23750" {
               description "193.23750 THz/1551.42 nm 6.25/12.5GHz spacing";
             }
             enum "193.24375" {
               description "193.24375 THz/1551.37 nm 6.25GHz spacing";
             }
             enum "193.25000" {
               description "193.25000 THz/1551.32 nm 6.25/12.5/50/75GHz spacing";
             }
             enum "193.25625" {
               description "193.25625 THz/1551.27 nm 6.25GHz spacing";
             }
             enum "193.26250" {
               description "193.26250 THz/1551.22 nm 6.25/12.5GHz spacing";
             }
             enum "193.26875" {
               description "193.26875 THz/1551.17 nm 6.25GHz spacing";
             }
             enum "193.27500" {
               description "193.27500 THz/1551.12 nm 6.25/12.5GHz spacing";
             }
             enum "193.28125" {
               description "193.28125 THz/1551.07 nm 6.25GHz spacing";
             }
             enum "193.28750" {
               description "193.28750 THz/1551.02 nm 6.25/12.5GHz spacing";
             }
             enum "193.29375" {
               description "193.29375 THz/1550.97 nm 6.25GHz spacing";
             }
             enum "193.30000" {
               description "193.30000 THz/1550.92 nm 6.25/12.5/50/100GHz spacing";
             }
             enum "193.30625" {
               description "193.30625 THz/1550.87 nm 6.25GHz spacing";
             }
             enum "193.31250" {
               description "193.31250 THz/1550.82 nm 6.25/12.5GHz spacing";
             }
             enum "193.31875" {
               description "193.31875 THz/1550.77 nm 6.25GHz spacing";
             }
             enum "193.32500" {
               description "193.32500 THz/1550.72 nm 6.25/12.5/75GHz spacing";
             }
             enum "193.33125" {
               description "193.33125 THz/1550.67 nm 6.25GHz spacing";
             }
             enum "193.33750" {
               description "193.33750 THz/1550.62 nm 6.25/12.5GHz spacing";
             }
             enum "193.34375" {
               description "193.34375 THz/1550.57 nm 6.25GHz spacing";
             }
             enum "193.35000" {
               description "193.35000 THz/1550.52 nm 6.25/12.5/50GHz spacing";
             }
             enum "193.35625" {
               description "193.35625 THz/1550.47 nm 6.25GHz spacing";
             }
             enum "193.36250" {
               description "193.36250 THz/1550.42 nm 6.25/12.5GHz spacing";
             }
             enum "193.36875" {
               description "193.36875 THz/1550.37 nm 6.25GHz spacing";
             }
             enum "193.37500" {
               description "193.37500 THz/1550.32 nm 6.25/12.5GHz spacing";
             }
             enum "193.38125" {
               description "193.38125 THz/1550.27 nm 6.25GHz spacing";
             }
             enum "193.38750" {
               description "193.38750 THz/1550.22 nm 6.25/12.5GHz spacing";
             }
             enum "193.39375" {
               description "193.39375 THz/1550.17 nm 6.25GHz spacing";
             }
             enum "193.40000" {
               description "193.40000 THz/1550.12 nm 6.25/12.5/50/75/100GHz spacing";
             }
             enum "193.40625" {
               description "193.40625 THz/1550.07 nm 6.25GHz spacing";
             }
             enum "193.41250" {
               description "193.41250 THz/1550.02 nm 6.25/12.5GHz spacing";
             }
             enum "193.41875" {
               description "193.41875 THz/1549.97 nm 6.25GHz spacing";
             }
             enum "193.42500" {
               description "193.42500 THz/1549.92 nm 6.25/12.5GHz spacing";
             }
             enum "193.43125" {
               description "193.43125 THz/1549.87 nm 6.25GHz spacing";
             }
             enum "193.43750" {
               description "193.43750 THz/1549.82 nm 6.25/12.5GHz spacing";
             }
             enum "193.44375" {
               description "193.44375 THz/1549.77 nm 6.25GHz spacing";
             }
             enum "193.45000" {
               description "193.45000 THz/1549.72 nm 6.25/12.5/50GHz spacing";
             }
             enum "193.45625" {
               description "193.45625 THz/1549.67 nm 6.25GHz spacing";
             }
             enum "193.46250" {
               description "193.46250 THz/1549.62 nm 6.25/12.5GHz spacing";
             }
             enum "193.46875" {
               description "193.46875 THz/1549.57 nm 6.25GHz spacing";
             }
             enum "193.47500" {
               description "193.47500 THz/1549.52 nm 6.25/12.5/75GHz spacing";
             }
             enum "193.48125" {
               description "193.48125 THz/1549.47 nm 6.25GHz spacing";
             }
             enum "193.48750" {
               description "193.48750 THz/1549.42 nm 6.25/12.5GHz spacing";
             }
             enum "193.49375" {
               description "193.49375 THz/1549.37 nm 6.25GHz spacing";
             }
             enum "193.50000" {
               description "193.50000 THz/1549.32 nm 6.25/12.5/50/100GHz spacing";
             }
             enum "193.50625" {
               description "193.50625 THz/1549.26 nm 6.25GHz spacing";
             }
             enum "193.51250" {
               description "193.51250 THz/1549.21 nm 6.25/12.5GHz spacing";
             }
             enum "193.51875" {
               description "193.51875 THz/1549.16 nm 6.25GHz spacing";
             }
             enum "193.52500" {
               description "193.52500 THz/1549.11 nm 6.25/12.5GHz spacing";
             }
             enum "193.53125" {
               description "193.53125 THz/1549.06 nm 6.25GHz spacing";
             }
             enum "193.53750" {
               description "193.53750 THz/1549.01 nm 6.25/12.5GHz spacing";
             }
             enum "193.54375" {
               description "193.54375 THz/1548.96 nm 6.25GHz spacing";
             }
             enum "193.55000" {
               description "193.55000 THz/1548.91 nm 6.25/12.5/50/75GHz spacing";
             }
             enum "193.55625" {
               description "193.55625 THz/1548.86 nm 6.25GHz spacing";
             }
             enum "193.56250" {
               description "193.56250 THz/1548.81 nm 6.25/12.5GHz spacing";
             }
             enum "193.56875" {
               description "193.56875 THz/1548.76 nm 6.25GHz spacing";
             }
             enum "193.57500" {
               description "193.57500 THz/1548.71 nm 6.25/12.5GHz spacing";
             }
             enum "193.58125" {
               description "193.58125 THz/1548.66 nm 6.25GHz spacing";
             }
             enum "193.58750" {
               description "193.58750 THz/1548.61 nm 6.25/12.5GHz spacing";
             }
             enum "193.59375" {
               description "193.59375 THz/1548.56 nm 6.25GHz spacing";
             }
             enum "193.60000" {
               description "193.60000 THz/1548.51 nm 6.25/12.5/50/100GHz spacing";
             }
             enum "193.60625" {
               description "193.60625 THz/1548.46 nm 6.25GHz spacing";
             }
             enum "193.61250" {
               description "193.61250 THz/1548.41 nm 6.25/12.5GHz spacing";
             }
             enum "193.61875" {
               description "193.61875 THz/1548.36 nm 6.25GHz spacing";
             }
             enum "193.62500" {
               description "193.62500 THz/1548.31 nm 6.25/12.5/75GHz spacing";
             }
             enum "193.63125" {
               description "193.63125 THz/1548.26 nm 6.25GHz spacing";
             }
             enum "193.63750" {
               description "193.63750 THz/1548.21 nm 6.25/12.5GHz spacing";
             }
             enum "193.64375" {
               description "193.64375 THz/1548.16 nm 6.25GHz spacing";
             }
             enum "193.65000" {
               description "193.65000 THz/1548.11 nm 6.25/12.5/50GHz spacing";
             }
             enum "193.65625" {
               description "193.65625 THz/1548.06 nm 6.25GHz spacing";
             }
             enum "193.66250" {
               description "193.66250 THz/1548.02 nm 6.25/12.5GHz spacing";
             }
             enum "193.66875" {
               description "193.66875 THz/1547.97 nm 6.25GHz spacing";
             }
             enum "193.67500" {
               description "193.67500 THz/1547.92 nm 6.25/12.5GHz spacing";
             }
             enum "193.68125" {
               description "193.68125 THz/1547.87 nm 6.25GHz spacing";
             }
             enum "193.68750" {
               description "193.68750 THz/1547.82 nm 6.25/12.5GHz spacing";
             }
             enum "193.69375" {
               description "193.69375 THz/1547.77 nm 6.25GHz spacing";
             }
             enum "193.70000" {
               description "193.70000 THz/1547.72 nm 6.25/12.5/50/100/75GHz spacing";
             }
             enum "193.70625" {
               description "193.70625 THz/1547.67 nm 6.25GHz spacing";
             }
             enum "193.71250" {
               description "193.71250 THz/1547.62 nm 6.25/12.5GHz spacing";
             }
             enum "193.71875" {
               description "193.71875 THz/1547.57 nm 6.25GHz spacing";
             }
             enum "193.72500" {
               description "193.72500 THz/1547.52 nm 6.25/12.5GHz spacing";
             }
             enum "193.73125" {
               description "193.73125 THz/1547.47 nm 6.25GHz spacing";
             }
             enum "193.73750" {
               description "193.73750 THz/1547.42 nm 6.25/12.5GHz spacing";
             }
             enum "193.74375" {
               description "193.74375 THz/1547.37 nm 6.25GHz spacing";
             }
             enum "193.75000" {
               description "193.75000 THz/1547.32 nm 6.25/12.5/50GHz spacing";
             }
             enum "193.75625" {
               description "193.75625 THz/1547.27 nm 6.25GHz spacing";
             }
             enum "193.76250" {
               description "193.76250 THz/1547.22 nm 6.25/12.5GHz spacing";
             }
             enum "193.76875" {
               description "193.76875 THz/1547.17 nm 6.25GHz spacing";
             }
             enum "193.77500" {
               description "193.77500 THz/1547.12 nm 6.25/12.5/75GHz spacing";
             }
             enum "193.78125" {
               description "193.78125 THz/1547.07 nm 6.25GHz spacing";
             }
             enum "193.78750" {
               description "193.78750 THz/1547.02 nm 6.25/12.5GHz spacing";
             }
             enum "193.79375" {
               description "193.79375 THz/1546.97 nm 6.25GHz spacing";
             }
             enum "193.80000" {
               description "193.80000 THz/1546.92 nm 6.25/12.5/50/100GHz spacing";
             }
             enum "193.80625" {
               description "193.80625 THz/1546.87 nm 6.25GHz spacing";
             }
             enum "193.81250" {
               description "193.81250 THz/1546.82 nm 6.25/12.5GHz spacing";
             }
             enum "193.81875" {
               description "193.81875 THz/1546.77 nm 6.25GHz spacing";
             }
             enum "193.82500" {
               description "193.82500 THz/1546.72 nm 6.25/12.5GHz spacing";
             }
             enum "193.83125" {
               description "193.83125 THz/1546.67 nm 6.25GHz spacing";
             }
             enum "193.83750" {
               description "193.83750 THz/1546.62 nm 6.25/12.5GHz spacing";
             }
             enum "193.84375" {
               description "193.84375 THz/1546.57 nm 6.25GHz spacing";
             }
             enum "193.85000" {
               description "193.85000 THz/1546.52 nm 6.25/12.5/50/75GHz spacing";
             }
             enum "193.85625" {
               description "193.85625 THz/1546.47 nm 6.25GHz spacing";
             }
             enum "193.86250" {
               description "193.86250 THz/1546.42 nm 6.25/12.5GHz spacing";
             }
             enum "193.86875" {
               description "193.86875 THz/1546.37 nm 6.25GHz spacing";
             }
             enum "193.87500" {
               description "193.87500 THz/1546.32 nm 6.25/12.5GHz spacing";
             }
             enum "193.88125" {
               description "193.88125 THz/1546.27 nm 6.25GHz spacing";
             }
             enum "193.88750" {
               description "193.88750 THz/1546.22 nm 6.25/12.5GHz spacing";
             }
             enum "193.89375" {
               description "193.89375 THz/1546.17 nm 6.25GHz spacing";
             }
             enum "193.90000" {
               description "193.90000 THz/1546.12 nm 6.25/12.5/50/100GHz spacing";
             }
             enum "193.90625" {
               description "193.90625 THz/1546.07 nm 6.25GHz spacing";
             }
             enum "193.91250" {
               description "193.91250 THz/1546.02 nm 6.25/12.5GHz spacing";
             }
             enum "193.91875" {
               description "193.91875 THz/1545.97 nm 6.25GHz spacing";
             }
             enum "193.92500" {
               description "193.92500 THz/1545.92 nm 6.25/12.5/75GHz spacing";
             }
             enum "193.93125" {
               description "193.93125 THz/1545.87 nm 6.25GHz spacing";
             }
             enum "193.93750" {
               description "193.93750 THz/1545.82 nm 6.25/12.5GHz spacing";
             }
             enum "193.94375" {
               description "193.94375 THz/1545.77 nm 6.25GHz spacing";
             }
             enum "193.95000" {
               description "193.95000 THz/1545.72 nm 6.25/12.5/50GHz spacing";
             }
             enum "193.95625" {
               description "193.95625 THz/1545.67 nm 6.25GHz spacing";
             }
             enum "193.96250" {
               description "193.96250 THz/1545.62 nm 6.25/12.5GHz spacing";
             }
             enum "193.96875" {
               description "193.96875 THz/1545.57 nm 6.25GHz spacing";
             }
             enum "193.97500" {
               description "193.97500 THz/1545.52 nm 6.25/12.5GHz spacing";
             }
             enum "193.98125" {
               description "193.98125 THz/1545.47 nm 6.25GHz spacing";
             }
             enum "193.98750" {
               description "193.98750 THz/1545.42 nm 6.25/12.5GHz spacing";
             }
             enum "193.99375" {
               description "193.99375 THz/1545.37 nm 6.25GHz spacing";
             }
             enum "194.00000" {
               description "194.00000 THz/1545.32 nm 6.25/12.5/50/75/100GHz spacing";
             }
             enum "194.00625" {
               description "194.00625 THz/1545.27 nm 6.25GHz spacing";
             }
             enum "194.01250" {
               description "194.01250 THz/1545.22 nm 6.25/12.5GHz spacing";
             }
             enum "194.01875" {
               description "194.01875 THz/1545.17 nm 6.25GHz spacing";
             }
             enum "194.02500" {
               description "194.02500 THz/1545.12 nm 6.25/12.5GHz spacing";
             }
             enum "194.03125" {
               description "194.03125 THz/1545.07 nm 6.25GHz spacing";
             }
             enum "194.03750" {
               description "194.03750 THz/1545.02 nm 6.25/12.5GHz spacing";
             }
             enum "194.04375" {
               description "194.04375 THz/1544.97 nm 6.25GHz spacing";
             }
             enum "194.05000" {
               description "194.05000 THz/1544.92 nm 6.25/12.5/50GHz spacing";
             }
             enum "194.05625" {
               description "194.05625 THz/1544.87 nm 6.25GHz spacing";
             }
             enum "194.06250" {
               description "194.06250 THz/1544.82 nm 6.25/12.5GHz spacing";
             }
             enum "194.06875" {
               description "194.06875 THz/1544.77 nm 6.25GHz spacing";
             }
             enum "194.07500" {
               description "194.07500 THz/1544.72 nm 6.25/12.5/75GHz spacing";
             }
             enum "194.08125" {
               description "194.08125 THz/1544.68 nm 6.25GHz spacing";
             }
             enum "194.08750" {
               description "194.08750 THz/1544.63 nm 6.25/12.5GHz spacing";
             }
             enum "194.09375" {
               description "194.09375 THz/1544.58 nm 6.25GHz spacing";
             }
             enum "194.10000" {
               description "194.10000 THz/1544.53 nm 6.25/12.5/50/100GHz spacing";
             }
             enum "194.10625" {
               description "194.10625 THz/1544.48 nm 6.25GHz spacing";
             }
             enum "194.11250" {
               description "194.11250 THz/1544.43 nm 6.25/12.5GHz spacing";
             }
             enum "194.11875" {
               description "194.11875 THz/1544.38 nm 6.25GHz spacing";
             }
             enum "194.12500" {
               description "194.12500 THz/1544.33 nm 6.25/12.5GHz spacing";
             }
             enum "194.13125" {
               description "194.13125 THz/1544.28 nm 6.25GHz spacing";
             }
             enum "194.13750" {
               description "194.13750 THz/1544.23 nm 6.25/12.5GHz spacing";
             }
             enum "194.14375" {
               description "194.14375 THz/1544.18 nm 6.25GHz spacing";
             }
             enum "194.15000" {
               description "194.15000 THz/1544.13 nm 6.25/12.5/50/75GHz spacing";
             }
             enum "194.15625" {
               description "194.15625 THz/1544.08 nm 6.25GHz spacing";
             }
             enum "194.16250" {
               description "194.16250 THz/1544.03 nm 6.25/12.5GHz spacing";
             }
             enum "194.16875" {
               description "194.16875 THz/1543.98 nm 6.25GHz spacing";
             }
             enum "194.17500" {
               description "194.17500 THz/1543.93 nm 6.25/12.5GHz spacing";
             }
             enum "194.18125" {
               description "194.18125 THz/1543.88 nm 6.25GHz spacing";
             }
             enum "194.18750" {
               description "194.18750 THz/1543.83 nm 6.25/12.5GHz spacing";
             }
             enum "194.19375" {
               description "194.19375 THz/1543.78 nm 6.25GHz spacing";
             }
             enum "194.20000" {
               description "194.20000 THz/1543.73 nm 6.25/12.5/50/100GHz spacing";
             }
             enum "194.20625" {
               description "194.20625 THz/1543.68 nm 6.25GHz spacing";
             }
             enum "194.21250" {
               description "194.21250 THz/1543.63 nm 6.25/12.5GHz spacing";
             }
             enum "194.21875" {
               description "194.21875 THz/1543.58 nm 6.25GHz spacing";
             }
             enum "194.22500" {
               description "194.22500 THz/1543.53 nm 6.25/12.5/75GHz spacing";
             }
             enum "194.23125" {
               description "194.23125 THz/1543.48 nm 6.25GHz spacing";
             }
             enum "194.23750" {
               description "194.23750 THz/1543.43 nm 6.25/12.5GHz spacing";
             }
             enum "194.24375" {
               description "194.24375 THz/1543.38 nm 6.25GHz spacing";
             }
             enum "194.25000" {
               description "194.25000 THz/1543.33 nm 6.25/12.5/50/75GHz spacing";
             }
             enum "194.25625" {
               description "194.25625 THz/1543.28 nm 6.25GHz spacing";
             }
             enum "194.26250" {
               description "194.26250 THz/1543.23 nm 6.25/12.5GHz spacing";
             }
             enum "194.26875" {
               description "194.26875 THz/1543.18 nm 6.25GHz spacing";
             }
             enum "194.27500" {
               description "194.27500 THz/1543.13 nm 6.25/12.5GHz spacing";
             }
             enum "194.28125" {
               description "194.28125 THz/1543.08 nm 6.25GHz spacing";
             }
             enum "194.28750" {
               description "194.28750 THz/1543.04 nm 6.25/12.5GHz spacing";
             }
             enum "194.29375" {
               description "194.29375 THz/1542.99 nm 6.25GHz spacing";
             }
             enum "194.30000" {
               description "194.30000 THz/1542.94 nm 6.25/12.5/50/75/100GHz spacing";
             }
             enum "194.30625" {
               description "194.30625 THz/1542.89 nm 6.25GHz spacing";
             }
             enum "194.31250" {
               description "194.31250 THz/1542.84 nm 6.25/12.5GHz spacing";
             }
             enum "194.31875" {
               description "194.31875 THz/1542.79 nm 6.25GHz spacing";
             }
             enum "194.32500" {
               description "194.32500 THz/1542.74 nm 6.25/12.5GHz spacing";
             }
             enum "194.33125" {
               description "194.33125 THz/1542.69 nm 6.25GHz spacing";
             }
             enum "194.33750" {
               description "194.33750 THz/1542.64 nm 6.25/12.5GHz spacing";
             }
             enum "194.34375" {
               description "194.34375 THz/1542.59 nm 6.25GHz spacing";
             }
             enum "194.35000" {
               description "194.35000 THz/1542.54 nm 6.25/12.5/50GHz spacing";
             }
             enum "194.35625" {
               description "194.35625 THz/1542.49 nm 6.25GHz spacing";
             }
             enum "194.36250" {
               description "194.36250 THz/1542.44 nm 6.25/12.5GHz spacing";
             }
             enum "194.36875" {
               description "194.36875 THz/1542.39 nm 6.25GHz spacing";
             }
             enum "194.37500" {
               description "194.37500 THz/1542.34 nm 6.25/12.5/75GHz spacing";
             }
             enum "194.38125" {
               description "194.38125 THz/1542.29 nm 6.25GHz spacing";
             }
             enum "194.38750" {
               description "194.38750 THz/1542.24 nm 6.25/12.5GHz spacing";
             }
             enum "194.39375" {
               description "194.39375 THz/1542.19 nm 6.25GHz spacing";
             }
             enum "194.40000" {
               description "194.40000 THz/1542.14 nm 6.25/12.5/50/100GHz spacing";
             }
             enum "194.40625" {
               description "194.40625 THz/1542.09 nm 6.25GHz spacing";
             }
             enum "194.41250" {
               description "194.41250 THz/1542.04 nm 6.25/12.5GHz spacing";
             }
             enum "194.41875" {
               description "194.41875 THz/1541.99 nm 6.25GHz spacing";
             }
             enum "194.42500" {
               description "194.42500 THz/1541.94 nm 6.25/12.5GHz spacing";
             }
             enum "194.43125" {
               description "194.43125 THz/1541.89 nm 6.25GHz spacing";
             }
             enum "194.43750" {
               description "194.43750 THz/1541.84 nm 6.25/12.5GHz spacing";
             }
             enum "194.44375" {
               description "194.44375 THz/1541.80 nm 6.25GHz spacing";
             }
             enum "194.45000" {
               description "194.45000 THz/1541.75 nm 6.25/12.5/50/75GHz spacing";
             }
             enum "194.45625" {
               description "194.45625 THz/1541.70 nm 6.25GHz spacing";
             }
             enum "194.46250" {
               description "194.46250 THz/1541.65 nm 6.25/12.5GHz spacing";
             }
             enum "194.46875" {
               description "194.46875 THz/1541.60 nm 6.25GHz spacing";
             }
             enum "194.47500" {
               description "194.47500 THz/1541.55 nm 6.25/12.5GHz spacing";
             }
             enum "194.48125" {
               description "194.48125 THz/1541.50 nm 6.25GHz spacing";
             }
             enum "194.48750" {
               description "194.48750 THz/1541.45 nm 6.25/12.5GHz spacing";
             }
             enum "194.49375" {
               description "194.49375 THz/1541.40 nm 6.25GHz spacing";
             }
             enum "194.50000" {
               description "194.50000 THz/1541.35 nm 6.25/12.5/50/100GHz spacing";
             }
             enum "194.50625" {
               description "194.50625 THz/1541.30 nm 6.25GHz spacing";
             }
             enum "194.51250" {
               description "194.51250 THz/1541.25 nm 6.25/12.5GHz spacing";
             }
             enum "194.51875" {
               description "194.51875 THz/1541.20 nm 6.25GHz spacing";
             }
             enum "194.52500" {
               description "194.52500 THz/1541.15 nm 6.25/12.5/75GHz spacing";
             }
             enum "194.53125" {
               description "194.53125 THz/1541.10 nm 6.25GHz spacing";
             }
             enum "194.53750" {
               description "194.53750 THz/1541.05 nm 6.25/12.5GHz spacing";
             }
             enum "194.54375" {
               description "194.54375 THz/1541.00 nm 6.25GHz spacing";
             }
             enum "194.55000" {
               description "194.55000 THz/1540.95 nm 6.25/12.5/50GHz spacing";
             }
             enum "194.55625" {
               description "194.55625 THz/1540.90 nm 6.25GHz spacing";
             }
             enum "194.56250" {
               description "194.56250 THz/1540.85 nm 6.25/12.5GHz spacing";
             }
             enum "194.56875" {
               description "194.56875 THz/1540.80 nm 6.25GHz spacing";
             }
             enum "194.57500" {
               description "194.57500 THz/1540.76 nm 6.25/12.5GHz spacing";
             }
             enum "194.58125" {
               description "194.58125 THz/1540.71 nm 6.25GHz spacing";
             }
             enum "194.58750" {
               description "194.58750 THz/1540.66 nm 6.25/12.5GHz spacing";
             }
             enum "194.59375" {
               description "194.59375 THz/1540.61 nm 6.25GHz spacing";
             }
             enum "194.60000" {
               description "194.60000 THz/1540.56 nm 6.25/12.5/50/75/100GHz spacing";
             }
             enum "194.60625" {
               description "194.60625 THz/1540.51 nm 6.25GHz spacing";
             }
             enum "194.61250" {
               description "194.61250 THz/1540.46 nm 6.25/12.5GHz spacing";
             }
             enum "194.61875" {
               description "194.61875 THz/1540.41 nm 6.25GHz spacing";
             }
             enum "194.62500" {
               description "194.62500 THz/1540.36 nm 6.25/12.5GHz spacing";
             }
             enum "194.63125" {
               description "194.63125 THz/1540.31 nm 6.25GHz spacing";
             }
             enum "194.63750" {
               description "194.63750 THz/1540.26 nm 6.25/12.5GHz spacing";
             }
             enum "194.64375" {
               description "194.64375 THz/1540.21 nm 6.25GHz spacing";
             }
             enum "194.65000" {
               description "194.65000 THz/1540.16 nm 6.25/12.5/50GHz spacing";
             }
             enum "194.65625" {
               description "194.65625 THz/1540.11 nm 6.25GHz spacing";
             }
             enum "194.66250" {
               description "194.66250 THz/1540.06 nm 6.25/12.5GHz spacing";
             }
             enum "194.66875" {
               description "194.66875 THz/1540.01 nm 6.25GHz spacing";
             }
             enum "194.67500" {
               description "194.67500 THz/1539.96 nm 6.25/12.5/75GHz spacing";
             }
             enum "194.68125" {
               description "194.68125 THz/1539.91 nm 6.25GHz spacing";
             }
             enum "194.68750" {
               description "194.68750 THz/1539.86 nm 6.25/12.5GHz spacing";
             }
             enum "194.69375" {
               description "194.69375 THz/1539.82 nm 6.25GHz spacing";
             }
             enum "194.70000" {
               description "194.70000 THz/1539.77 nm 6.25/12.5/50/100GHz spacing";
             }
             enum "194.70625" {
               description "194.70625 THz/1539.72 nm 6.25GHz spacing";
             }
             enum "194.71250" {
               description "194.71250 THz/1539.67 nm 6.25/12.5GHz spacing";
             }
             enum "194.71875" {
               description "194.71875 THz/1539.62 nm 6.25GHz spacing";
             }
             enum "194.72500" {
               description "194.72500 THz/1539.57 nm 6.25/12.5GHz spacing";
             }
             enum "194.73125" {
               description "194.73125 THz/1539.52 nm 6.25GHz spacing";
             }
             enum "194.73750" {
               description "194.73750 THz/1539.47 nm 6.25/12.5GHz spacing";
             }
             enum "194.74375" {
               description "194.74375 THz/1539.42 nm 6.25GHz spacing";
             }
             enum "194.75000" {
               description "194.75000 THz/1539.37 nm 6.25/12.5/50/75GHz spacing";
             }
             enum "194.75625" {
               description "194.75625 THz/1539.32 nm 6.25GHz spacing";
             }
             enum "194.76250" {
               description "194.76250 THz/1539.27 nm 6.25/12.5GHz spacing";
             }
             enum "194.76875" {
               description "194.76875 THz/1539.22 nm 6.25GHz spacing";
             }
             enum "194.77500" {
               description "194.77500 THz/1539.17 nm 6.25/12.5GHz spacing";
             }
             enum "194.78125" {
               description "194.78125 THz/1539.12 nm 6.25GHz spacing";
             }
             enum "194.78750" {
               description "194.78750 THz/1539.07 nm 6.25/12.5GHz spacing";
             }
             enum "194.79375" {
               description "194.79375 THz/1539.03 nm 6.25GHz spacing";
             }
             enum "194.80000" {
               description "194.80000 THz/1538.98 nm 6.25/12.5/50/100GHz spacing";
             }
             enum "194.80625" {
               description "194.80625 THz/1538.93 nm 6.25GHz spacing";
             }
             enum "194.81250" {
               description "194.81250 THz/1538.88 nm 6.25/12.5GHz spacing";
             }
             enum "194.81875" {
               description "194.81875 THz/1538.83 nm 6.25GHz spacing";
             }
             enum "194.82500" {
               description "194.82500 THz/1538.78 nm 6.25/12.5/75GHz spacing";
             }
             enum "194.83125" {
               description "194.83125 THz/1538.73 nm 6.25GHz spacing";
             }
             enum "194.83750" {
               description "194.83750 THz/1538.68 nm 6.25/12.5GHz spacing";
             }
             enum "194.84375" {
               description "194.84375 THz/1538.63 nm 6.25GHz spacing";
             }
             enum "194.85000" {
               description "194.85000 THz/1538.58 nm 6.25/12.5/50GHz spacing";
             }
             enum "194.85625" {
               description "194.85625 THz/1538.53 nm 6.25GHz spacing";
             }
             enum "194.86250" {
               description "194.86250 THz/1538.48 nm 6.25/12.5GHz spacing";
             }
             enum "194.86875" {
               description "194.86875 THz/1538.43 nm 6.25GHz spacing";
             }
             enum "194.87500" {
               description "194.87500 THz/1538.38 nm 6.25/12.5GHz spacing";
             }
             enum "194.88125" {
               description "194.88125 THz/1538.33 nm 6.25GHz spacing";
             }
             enum "194.88750" {
               description "194.88750 THz/1538.28 nm 6.25/12.5GHz spacing";
             }
             enum "194.89375" {
               description "194.89375 THz/1538.24 nm 6.25GHz spacing";
             }
             enum "194.90000" {
               description "194.90000 THz/1538.19 nm 6.25/12.5/50/75/100GHz spacing";
             }
             enum "194.90625" {
               description "194.90625 THz/1538.14 nm 6.25GHz spacing";
             }
             enum "194.91250" {
               description "194.91250 THz/1538.09 nm 6.25/12.5GHz spacing";
             }
             enum "194.91875" {
               description "194.91875 THz/1538.04 nm 6.25GHz spacing";
             }
             enum "194.92500" {
               description "194.92500 THz/1537.99 nm 6.25/12.5GHz spacing";
             }
             enum "194.93125" {
               description "194.93125 THz/1537.94 nm 6.25GHz spacing";
             }
             enum "194.93750" {
               description "194.93750 THz/1537.89 nm 6.25/12.5GHz spacing";
             }
             enum "194.94375" {
               description "194.94375 THz/1537.84 nm 6.25GHz spacing";
             }
             enum "194.95000" {
               description "194.95000 THz/1537.79 nm 6.25/12.5/50GHz spacing";
             }
             enum "194.95625" {
               description "194.95625 THz/1537.74 nm 6.25GHz spacing";
             }
             enum "194.96250" {
               description "194.96250 THz/1537.69 nm 6.25/12.5GHz spacing";
             }
             enum "194.96875" {
               description "194.96875 THz/1537.64 nm 6.25GHz spacing";
             }
             enum "194.97500" {
               description "194.97500 THz/1537.59 nm 6.25/12.5/75GHz spacing";
             }
             enum "194.98125" {
               description "194.98125 THz/1537.55 nm 6.25GHz spacing";
             }
             enum "194.98750" {
               description "194.98750 THz/1537.50 nm 6.25/12.5GHz spacing";
             }
             enum "194.99375" {
               description "194.99375 THz/1537.45 nm 6.25GHz spacing";
             }
             enum "195.00000" {
               description "195.00000 THz/1537.40 nm 6.25/12.5/50/100GHz spacing";
             }
             enum "195.00625" {
               description "195.00625 THz/1537.35 nm 6.25GHz spacing";
             }
             enum "195.01250" {
               description "195.01250 THz/1537.30 nm 6.25/12.5GHz spacing";
             }
             enum "195.01875" {
               description "195.01875 THz/1537.25 nm 6.25GHz spacing";
             }
             enum "195.02500" {
               description "195.02500 THz/1537.20 nm 6.25/12.5GHz spacing";
             }
             enum "195.03125" {
               description "195.03125 THz/1537.15 nm 6.25GHz spacing";
             }
             enum "195.03750" {
               description "195.03750 THz/1537.10 nm 6.25/12.5GHz spacing";
             }
             enum "195.04375" {
               description "195.04375 THz/1537.05 nm 6.25GHz spacing";
             }
             enum "195.05000" {
               description "195.05000 THz/1537.00 nm 6.25/12.5/50/75GHz spacing";
             }
             enum "195.05625" {
               description "195.05625 THz/1536.95 nm 6.25GHz spacing";
             }
             enum "195.06250" {
               description "195.06250 THz/1536.90 nm 6.25/12.5GHz spacing";
             }
             enum "195.06875" {
               description "195.06875 THz/1536.86 nm 6.25GHz spacing";
             }
             enum "195.07500" {
               description "195.07500 THz/1536.81 nm 6.25/12.5GHz spacing";
             }
             enum "195.08125" {
               description "195.08125 THz/1536.76 nm 6.25GHz spacing";
             }
             enum "195.08750" {
               description "195.08750 THz/1536.71 nm 6.25/12.5GHz spacing";
             }
             enum "195.09375" {
               description "195.09375 THz/1536.66 nm 6.25GHz spacing";
             }
             enum "195.10000" {
               description "195.10000 THz/1536.61 nm 6.25/12.5/50/100GHz spacing";
             }
             enum "195.10625" {
               description "195.10625 THz/1536.56 nm 6.25GHz spacing";
             }
             enum "195.11250" {
               description "195.11250 THz/1536.51 nm 6.25/12.5GHz spacing";
             }
             enum "195.11875" {
               description "195.11875 THz/1536.46 nm 6.25GHz spacing";
             }
             enum "195.12500" {
               description "195.12500 THz/1536.41 nm 6.25/12.5/75GHz spacing";
             }
             enum "195.13125" {
               description "195.13125 THz/1536.36 nm 6.25GHz spacing";
             }
             enum "195.13750" {
               description "195.13750 THz/1536.31 nm 6.25/12.5GHz spacing";
             }
             enum "195.14375" {
               description "195.14375 THz/1536.26 nm 6.25GHz spacing";
             }
             enum "195.15000" {
               description "195.15000 THz/1536.22 nm 6.25/12.5/50GHz spacing";
             }
             enum "195.15625" {
               description "195.15625 THz/1536.17 nm 6.25GHz spacing";
             }
             enum "195.16250" {
               description "195.16250 THz/1536.12 nm 6.25/12.5GHz spacing";
             }
             enum "195.16875" {
               description "195.16875 THz/1536.07 nm 6.25GHz spacing";
             }
             enum "195.17500" {
               description "195.17500 THz/1536.02 nm 6.25/12.5GHz spacing";
             }
             enum "195.18125" {
               description "195.18125 THz/1535.97 nm 6.25GHz spacing";
             }
             enum "195.18750" {
               description "195.18750 THz/1535.92 nm 6.25/12.5GHz spacing";
             }
             enum "195.19375" {
               description "195.19375 THz/1535.87 nm 6.25GHz spacing";
             }
             enum "195.20000" {
               description "195.20000 THz/1535.82 nm 6.25/12.5/50/75/100GHz spacing";
             }
             enum "195.20625" {
               description "195.20625 THz/1535.77 nm 6.25GHz spacing";
             }
             enum "195.21250" {
               description "195.21250 THz/1535.72 nm 6.25/12.5GHz spacing";
             }
             enum "195.21875" {
               description "195.21875 THz/1535.67 nm 6.25GHz spacing";
             }
             enum "195.22500" {
               description "195.22500 THz/1535.63 nm 6.25/12.5GHz spacing";
             }
             enum "195.23125" {
               description "195.23125 THz/1535.58 nm 6.25GHz spacing";
             }
             enum "195.23750" {
               description "195.23750 THz/1535.53 nm 6.25/12.5GHz spacing";
             }
             enum "195.24375" {
               description "195.24375 THz/1535.48 nm 6.25GHz spacing";
             }
             enum "195.25000" {
               description "195.25000 THz/1535.43 nm 6.25/12.5/50GHz spacing";
             }
             enum "195.25625" {
               description "195.25625 THz/1535.38 nm 6.25GHz spacing";
             }
             enum "195.26250" {
               description "195.26250 THz/1535.33 nm 6.25/12.5GHz spacing";
             }
             enum "195.26875" {
               description "195.26875 THz/1535.28 nm 6.25GHz spacing";
             }
             enum "195.27500" {
               description "195.27500 THz/1535.23 nm 6.25/12.5/75GHz spacing";
             }
             enum "195.28125" {
               description "195.28125 THz/1535.18 nm 6.25GHz spacing";
             }
             enum "195.28750" {
               description "195.28750 THz/1535.13 nm 6.25/12.5GHz spacing";
             }
             enum "195.29375" {
               description "195.29375 THz/1535.08 nm 6.25GHz spacing";
             }
             enum "195.30000" {
               description "195.30000 THz/1535.04 nm 6.25/12.5/50/100GHz spacing";
             }
             enum "195.30625" {
               description "195.30625 THz/1534.99 nm 6.25GHz spacing";
             }
             enum "195.31250" {
               description "195.31250 THz/1534.94 nm 6.25/12.5GHz spacing";
             }
             enum "195.31875" {
               description "195.31875 THz/1534.89 nm 6.25GHz spacing";
             }
             enum "195.32500" {
               description "195.32500 THz/1534.84 nm 6.25/12.5GHz spacing";
             }
             enum "195.33125" {
               description "195.33125 THz/1534.79 nm 6.25GHz spacing";
             }
             enum "195.33750" {
               description "195.33750 THz/1534.74 nm 6.25/12.5GHz spacing";
             }
             enum "195.34375" {
               description "195.34375 THz/1534.69 nm 6.25GHz spacing";
             }
             enum "195.35000" {
               description "195.35000 THz/1534.64 nm 6.25/12.5/50/75GHz spacing";
             }
             enum "195.35625" {
               description "195.35625 THz/1534.59 nm 6.25GHz spacing";
             }
             enum "195.36250" {
               description "195.36250 THz/1534.54 nm 6.25/12.5GHz spacing";
             }
             enum "195.36875" {
               description "195.36875 THz/1534.50 nm 6.25GHz spacing";
             }
             enum "195.37500" {
               description "195.37500 THz/1534.45 nm 6.25/12.5GHz spacing";
             }
             enum "195.38125" {
               description "195.38125 THz/1534.40 nm 6.25GHz spacing";
             }
             enum "195.38750" {
               description "195.38750 THz/1534.35 nm 6.25/12.5GHz spacing";
             }
             enum "195.39375" {
               description "195.39375 THz/1534.30 nm 6.25GHz spacing";
             }
             enum "195.40000" {
               description "195.40000 THz/1534.25 nm 6.25/12.5/50/100GHz spacing";
             }
             enum "195.40625" {
               description "195.40625 THz/1534.20 nm 6.25GHz spacing";
             }
             enum "195.41250" {
               description "195.41250 THz/1534.15 nm 6.25/12.5GHz spacing";
             }
             enum "195.41875" {
               description "195.41875 THz/1534.10 nm 6.25GHz spacing";
             }
             enum "195.42500" {
               description "195.42500 THz/1534.05 nm 6.25/12.5/75GHz spacing";
             }
             enum "195.43125" {
               description "195.43125 THz/1534.00 nm 6.25GHz spacing";
             }
             enum "195.43750" {
               description "195.43750 THz/1533.96 nm 6.25/12.5GHz spacing";
             }
             enum "195.44375" {
               description "195.44375 THz/1533.91 nm 6.25GHz spacing";
             }
             enum "195.45000" {
               description "195.45000 THz/1533.86 nm 6.25/12.5/50GHz spacing";
             }
             enum "195.45625" {
               description "195.45625 THz/1533.81 nm 6.25GHz spacing";
             }
             enum "195.46250" {
               description "195.46250 THz/1533.76 nm 6.25/12.5GHz spacing";
             }
             enum "195.46875" {
               description "195.46875 THz/1533.71 nm 6.25GHz spacing";
             }
             enum "195.47500" {
               description "195.47500 THz/1533.66 nm 6.25/12.5GHz spacing";
             }
             enum "195.48125" {
               description "195.48125 THz/1533.61 nm 6.25GHz spacing";
             }
             enum "195.48750" {
               description "195.48750 THz/1533.56 nm 6.25/12.5GHz spacing";
             }
             enum "195.49375" {
               description "195.49375 THz/1533.51 nm 6.25GHz spacing";
             }
             enum "195.50000" {
               description "195.50000 THz/1533.47 nm 6.25/12.5/50/75/100GHz spacing";
             }
             enum "195.50625" {
               description "195.50625 THz/1533.42 nm 6.25GHz spacing";
             }
             enum "195.51250" {
               description "195.51250 THz/1533.37 nm 6.25/12.5GHz spacing";
             }
             enum "195.51875" {
               description "195.51875 THz/1533.32 nm 6.25GHz spacing";
             }
             enum "195.52500" {
               description "195.52500 THz/1533.27 nm 6.25/12.5GHz spacing";
             }
             enum "195.53125" {
               description "195.53125 THz/1533.22 nm 6.25GHz spacing";
             }
             enum "195.53750" {
               description "195.53750 THz/1533.17 nm 6.25/12.5GHz spacing";
             }
             enum "195.54375" {
               description "195.54375 THz/1533.12 nm 6.25GHz spacing";
             }
             enum "195.55000" {
               description "195.55000 THz/1533.07 nm 6.25/12.5/50GHz spacing";
             }
             enum "195.55625" {
               description "195.55625 THz/1533.02 nm 6.25GHz spacing";
             }
             enum "195.56250" {
               description "195.56250 THz/1532.98 nm 6.25/12.5GHz spacing";
             }
             enum "195.56875" {
               description "195.56875 THz/1532.93 nm 6.25GHz spacing";
             }
             enum "195.57500" {
               description "195.57500 THz/1532.88 nm 6.25/12.5/75GHz spacing";
             }
             enum "195.58125" {
               description "195.58125 THz/1532.83 nm 6.25GHz spacing";
             }
             enum "195.58750" {
               description "195.58750 THz/1532.78 nm 6.25/12.5GHz spacing";
             }
             enum "195.59375" {
               description "195.59375 THz/1532.73 nm 6.25GHz spacing";
             }
             enum "195.60000" {
               description "195.60000 THz/1532.68 nm 6.25/12.5/50/100GHz spacing";
             }
             enum "195.60625" {
               description "195.60625 THz/1532.63 nm 6.25GHz spacing";
             }
             enum "195.61250" {
               description "195.61250 THz/1532.58 nm 6.25/12.5GHz spacing";
             }
             enum "195.61875" {
               description "195.61875 THz/1532.53 nm 6.25GHz spacing";
             }
             enum "195.62500" {
               description "195.62500 THz/1532.49 nm 6.25/12.5GHz spacing";
             }
             enum "195.63125" {
               description "195.63125 THz/1532.44 nm 6.25GHz spacing";
             }
             enum "195.63750" {
               description "195.63750 THz/1532.39 nm 6.25/12.5GHz spacing";
             }
             enum "195.64375" {
               description "195.64375 THz/1532.34 nm 6.25GHz spacing";
             }
             enum "195.65000" {
               description "195.65000 THz/1532.29 nm 6.25/12.5/50/75GHz spacing";
             }
             enum "195.65625" {
               description "195.65625 THz/1532.24 nm 6.25GHz spacing";
             }
             enum "195.66250" {
               description "195.66250 THz/1532.19 nm 6.25/12.5GHz spacing";
             }
             enum "195.66875" {
               description "195.66875 THz/1532.14 nm 6.25GHz spacing";
             }
             enum "195.67500" {
               description "195.67500 THz/1532.09 nm 6.25/12.5GHz spacing";
             }
             enum "195.68125" {
               description "195.68125 THz/1532.04 nm 6.25GHz spacing";
             }
             enum "195.68750" {
               description "195.68750 THz/1532.00 nm 6.25/12.5GHz spacing";
             }
             enum "195.69375" {
               description "195.69375 THz/1531.95 nm 6.25GHz spacing";
             }
             enum "195.70000" {
               description "195.70000 THz/1531.90 nm 6.25/12.5/50/100GHz spacing";
             }
             enum "195.70625" {
               description "195.70625 THz/1531.85 nm 6.25GHz spacing";
             }
             enum "195.71250" {
               description "195.71250 THz/1531.80 nm 6.25/12.5GHz spacing";
             }
             enum "195.71875" {
               description "195.71875 THz/1531.75 nm 6.25GHz spacing";
             }
             enum "195.72500" {
               description "195.72500 THz/1531.70 nm 6.25/12.5/75GHz spacing";
             }
             enum "195.73125" {
               description "195.73125 THz/1531.65 nm 6.25GHz spacing";
             }
             enum "195.73750" {
               description "195.73750 THz/1531.60 nm 6.25/12.5GHz spacing";
             }
             enum "195.74375" {
               description "195.74375 THz/1531.56 nm 6.25GHz spacing";
             }
             enum "195.75000" {
               description "195.75000 THz/1531.51 nm 6.25/12.5/50GHz spacing";
             }
             enum "195.75625" {
               description "195.75625 THz/1531.46 nm 6.25GHz spacing";
             }
             enum "195.76250" {
               description "195.76250 THz/1531.41 nm 6.25/12.5GHz spacing";
             }
             enum "195.76875" {
               description "195.76875 THz/1531.36 nm 6.25GHz spacing";
             }
             enum "195.77500" {
               description "195.77500 THz/1531.31 nm 6.25/12.5GHz spacing";
             }
             enum "195.78125" {
               description "195.78125 THz/1531.26 nm 6.25GHz spacing";
             }
             enum "195.78750" {
               description "195.78750 THz/1531.21 nm 6.25/12.5GHz spacing";
             }
             enum "195.79375" {
               description "195.79375 THz/1531.16 nm 6.25GHz spacing";
             }
             enum "195.80000" {
               description "195.80000 THz/1531.12 nm 6.25/12.5/50/75/100GHz spacing";
             }
             enum "195.80625" {
               description "195.80625 THz/1531.07 nm 6.25GHz spacing";
             }
             enum "195.81250" {
               description "195.81250 THz/1531.02 nm 6.25/12.5GHz spacing";
             }
             enum "195.81875" {
               description "195.81875 THz/1530.97 nm 6.25GHz spacing";
             }
             enum "195.82500" {
               description "195.82500 THz/1530.92 nm 6.25/12.5GHz spacing";
             }
             enum "195.83125" {
               description "195.83125 THz/1530.87 nm 6.25GHz spacing";
             }
             enum "195.83750" {
               description "195.83750 THz/1530.82 nm 6.25/12.5GHz spacing";
             }
             enum "195.84375" {
               description "195.84375 THz/1530.77 nm 6.25GHz spacing";
             }
             enum "195.85000" {
               description "195.85000 THz/1530.72 nm 6.25/12.5/50GHz spacing";
             }
             enum "195.85625" {
               description "195.85625 THz/1530.68 nm 6.25GHz spacing";
             }
             enum "195.86250" {
               description "195.86250 THz/1530.63 nm 6.25/12.5GHz spacing";
             }
             enum "195.86875" {
               description "195.86875 THz/1530.58 nm 6.25GHz spacing";
             }
             enum "195.87500" {
               description "195.87500 THz/1530.53 nm 6.25/12.5/75GHz spacing";
             }
             enum "195.88125" {
               description "195.88125 THz/1530.48 nm 6.25GHz spacing";
             }
             enum "195.88750" {
               description "195.88750 THz/1530.43 nm 6.25/12.5GHz spacing";
             }
             enum "195.89375" {
               description "195.89375 THz/1530.38 nm 6.25GHz spacing";
             }
             enum "195.90000" {
               description "195.90000 THz/1530.33 nm 6.25/12.5/50/100GHz spacing";
             }
             enum "195.90625" {
               description "195.90625 THz/1530.29 nm 6.25GHz spacing";
             }
             enum "195.91250" {
               description "195.91250 THz/1530.24 nm 6.25/12.5GHz spacing";
             }
             enum "195.91875" {
               description "195.91875 THz/1530.19 nm 6.25GHz spacing";
             }
             enum "195.92500" {
               description "195.92500 THz/1530.14 nm 6.25/12.5GHz spacing";
             }
             enum "195.93125" {
               description "195.93125 THz/1530.09 nm 6.25GHz spacing";
             }
             enum "195.93750" {
               description "195.93750 THz/1530.04 nm 6.25/12.5GHz spacing";
             }
             enum "195.94375" {
               description "195.94375 THz/1529.99 nm 6.25GHz spacing";
             }
             enum "195.95000" {
               description "195.95000 THz/1529.94 nm 6.25/12.5/50/75GHz spacing";
             }
             enum "195.95625" {
               description "195.95625 THz/1529.89 nm 6.25GHz spacing";
             }
             enum "195.96250" {
               description "195.96250 THz/1529.85 nm 6.25/12.5GHz spacing";
             }
             enum "195.96875" {
               description "195.96875 THz/1529.80 nm 6.25GHz spacing";
             }
             enum "195.97500" {
               description "195.97500 THz/1529.75 nm 6.25/12.5GHz spacing";
             }
             enum "195.98125" {
               description "195.98125 THz/1529.70 nm 6.25GHz spacing";
             }
             enum "195.98750" {
               description "195.98750 THz/1529.65 nm 6.25/12.5GHz spacing";
             }
             enum "195.99375" {
               description "195.99375 THz/1529.60 nm 6.25GHz spacing";
             }
             enum "196.00000" {
               description "196.00000 THz/1529.55 nm 6.25/12.5/50/100GHz spacing";
             }
             enum "196.00625" {
               description "196.00625 THz/1529.50 nm 6.25GHz spacing";
             }
             enum "196.01250" {
               description "196.01250 THz/1529.46 nm 6.25/12.5GHz spacing";
             }
             enum "196.01875" {
               description "196.01875 THz/1529.41 nm 6.25GHz spacing";
             }
             enum "196.02500" {
               description "196.02500 THz/1529.36 nm 6.25/12.5/75GHz spacing";
             }
             enum "196.03125" {
               description "196.03125 THz/1529.31 nm 6.25GHz spacing";
             }
             enum "196.03750" {
               description "196.03750 THz/1529.26 nm 6.25/12.5GHz spacing";
             }
             enum "196.04375" {
               description "196.04375 THz/1529.21 nm 6.25GHz spacing";
             }
             enum "196.05000" {
               description "196.05000 THz/1529.16 nm 6.25/12.5/50GHz spacing";
             }
             enum "196.05625" {
               description "196.05625 THz/1529.11 nm 6.25GHz spacing";
             }
             enum "196.06250" {
               description "196.06250 THz/1529.07 nm 6.25/12.5GHz spacing";
             }
             enum "196.06875" {
               description "196.06875 THz/1529.02 nm 6.25GHz spacing";
             }
             enum "196.07500" {
               description "196.07500 THz/1528.97 nm 6.25/12.5GHz spacing";
             }
             enum "196.08125" {
               description "196.08125 THz/1528.92 nm 6.25GHz spacing";
             }
             enum "196.08750" {
               description "196.08750 THz/1528.87 nm 6.25/12.5GHz spacing";
             }
             enum "196.09375" {
               description "196.09375 THz/1528.82 nm 6.25GHz spacing";
             }
             enum "196.10000" {
               description "196.10000 THz/1528.77 nm 6.25/12.5/50/75/100GHz spacing";
             }
             enum "196.15040" {
               description "196.15040 THz/1528.38 nm 50Ghz spacing";
             }
           }
         }
       }
     }
     leaf tx-power {
       description "Transmit laser output power";
       units "dBm";
       type string {
       }
     }
     choice laser-enable-choice {
       leaf laser-enable {
         description "Enable transmit laser";
         type empty;
       }
       leaf no-laser-enable {
         description "Don't enable transmit laser";
         type empty;
       }
     }
   }
   grouping odu-attributes {
     description "Optical Data Unit configuration attributes";
     uses apply-advanced;
     leaf rate {
       description "Specific type of ODU, according to data rate";
       type enumeration {
         enum "odu4" {
           description "ODU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     container tti {
       description "Configuration of OTU trail trace identifier";
       presence "enable tti";
       uses otn-tti-attributes;
     }
     container degrade {
       description "Configuration of OTU degrade defect detection";
       presence "enable degrade";
       uses otn-degrade;
     }
     leaf exp-payload-type {
       description "Expected OPU payload type";
       type union {
         type uint8;
         type string {
           pattern "<.*>|$.*";
         }
       }
     }
     container prbs {
       description "Configuration of framed pseudorandom binary sequence test signal";
       presence "enable prbs";
       uses prbs-config;
     }
   }
   grouping otn-degrade {
     description "Configuration of degrade defect detection";
     uses apply-advanced;
     leaf degm {
       description "Number of consecutive intervals error rate above threshold";
       type union {
         type string {
           pattern "<.*>|$.*";
         }
         type uint16 {
           range "2 .. 10";
         }
       }
     }
     leaf degthr {
       description "Threshold - percentage errored blocks, ex. 1.23 = 1.23%";
       type string {
       }
     }
   }
   grouping otn-tti-attributes {
     description "Configuration of OTN trail trace identifier";
     uses apply-advanced;
     leaf sapi {
       description "Transmitted source access point identifier field";
       type string {
         length "0 .. 15";
       }
     }
     leaf dapi {
       description "Transmitted destination access point identifier field";
       type string {
         length "0 .. 15";
       }
     }
     leaf operator {
       description "Transmitted operator field";
       type string {
         length "0 .. 32";
       }
     }
     leaf exp-sapi {
       description "Expected received source access point identifier field";
       type string {
         length "0 .. 15";
       }
     }
     leaf exp-dapi {
       description "Expected received destination access point identifier field";
       type string {
         length "0 .. 15";
       }
     }
     leaf tim-detect-mode {
       description "Trace input mismatch defect detection mode";
       type enumeration {
         enum "disabled" {
           description "Detection of trace input mismatch defect disabled";
         }
         enum "sapi-only" {
           description "Detection of trace input mismatch defect on SAPI field only";
         }
         enum "dapi-only" {
           description "Detection of trace input mismatch defect on DAPI field only";
         }
         enum "sapi-and-dapi" {
           description "Detection of trace input mismatch defect on both SAPI and DAPI fields";
         }
       }
     }
     choice tim-act-enable-choice {
       leaf tim-act-enable {
         description "Enable trace input mismatch consequential actions";
         type empty;
       }
       leaf no-tim-act-enable {
         description "Don't enable trace input mismatch consequential actions";
         type empty;
       }
     }
   }
   grouping otu-attributes {
     description "Optical transmission unit configuration attributes";
     uses apply-advanced;
     leaf rate {
       description "Specific type of OTU, according to data rate";
       type enumeration {
         enum "otu4" {
           description "OTU4 for 100 Gbps";
         }
       }
     }
     choice is-ma-choice {
       leaf is-ma {
         description "Link is enabled for maintenance tasks, alarms are masked";
         type empty;
       }
       leaf no-is-ma {
         description "Don't link is enabled for maintenance tasks, alarms are masked";
         type empty;
       }
     }
     leaf fec {
       description "Forward error correction type";
       type enumeration {
         enum "none" {
           description "No forward error correction applied";
         }
         enum "gfec" {
           description "ITU-T G.709 standard forward error correction";
         }
         enum "hgfec" {
           description "High gain FEC";
         }
       }
     }
     leaf loopback {
       description "Enabled loopback mode";
       type enumeration {
         enum "none" {
           description "No loopback mode active";
         }
         enum "local" {
           description "Local loopback (host side)";
         }
         enum "line" {
           description "Line loopback (network side)";
         }
       }
     }
     container tti {
       description "Configuration of OTU trail trace identifier";
       presence "enable tti";
       uses otn-tti-attributes;
     }
     container degrade {
       description "Configuration of OTU degrade defect detection";
       presence "enable degrade";
       uses otn-degrade;
     }
   }
   grouping output-plugin {
     leaf name {
       description "Plugin name";
       type string;
     }
     uses apply-advanced;
     list parameters {
       key name;
       ordered-by user;
       description "List of key:value parameters for plugin";
       uses parameter-pair;
     }
   }
   grouping override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf no-arp {
       description "Disable DHCP ARP table population";
       status deprecated;
       type empty;
     }
     leaf bootp-support {
       description "Allow processing of bootp requests";
       type empty;
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container delay-offer {
       description "Filter options for dhcp-server";
       uses dhcpv4-filter-option;
     }
     container process-inform {
       presence "enable process-inform";
       description "Process INFORM PDUs";
       uses apply-advanced;
       leaf pool {
         description "Pool name for family inet";
         type string {
           length "1 .. 64";
         }
       }
     }
     container include-option-82 {
       description "Include option-82 in reply packets";
       uses apply-advanced;
       leaf nak {
         description "Include option-82 in NAK";
         type empty;
       }
       leaf forcerenew {
         description "Include option-82 in FORCERENEW";
         type empty;
       }
     }
     leaf delete-binding-on-renegotiation {
       description "Delete binding on renegotiation";
       type empty;
     }
     leaf allow-no-end-option {
       description "Allow packets without end-of-option";
       type empty;
     }
     leaf asymmetric-lease-time {
       description "Use a reduced lease time for the client. In seconds";
       units "seconds";
       type union {
         type string {
           pattern "<.*>|$.*";
         }
         type uint32 {
           range "600 .. 86400";
         }
       }
     }
     leaf protocol-attributes {
       description "DHCPv4 attributes to use as defined under access protocol-attributes";
       type string {
         length "1 .. 64";
       }
     }
     leaf dual-stack {
       description "Dual stack group to use";
       type string {
         length "1 .. 64";
       }
     }
     leaf nak-unknown-rebind {
       description "Nak unknown rebind requests";
       type empty;
     }
     leaf nak-unknown-renew {
       description "Nak unknown renew requests";
       type empty;
     }
     leaf layer2-unicast-replies {
       description "Do not broadcast client responses";
       type empty;
     }
   }
   grouping dhcpv4-filter-option {
     description "Generic DHCPv4 filter processing";
     uses apply-advanced;
     leaf delay-time {
       description "Time delay between discover and offer";
       default "3";
       units "seconds";
       type union {
         type string {
           pattern "<.*>|$.*";
         }
         type uint32 {
           range "1 .. 30";
         }
       }
     }
     container based-on {
       description "Option number";
       uses apply-advanced;
       container option-82 {
         presence "enable option-82";
         description "Option 82";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-60 {
         presence "enable option-60";
         description "Option 60";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-77 {
         presence "enable option-77";
         description "Option 77";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping override-type {
     description "DHCP override processing";
     uses apply-advanced;
     leaf no-unicast-replies {
       description "Overwrite unicast bit in incoming packet, when present";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       status deprecated;
       type string {
         length "1 .. 252";
       }
     }
     leaf include-option-82-in-vsa {
       description "Include option 82 in Dhcp-Options RADIUS VSA";
       type empty;
     }
     leaf layer2-unicast-replies {
       description "Do not broadcast client responses";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       type empty;
     }
     leaf bootp-support {
       description "Allows relay of bootp req and reply";
       type empty;
     }
     leaf dual-stack {
       description "Dual stack group to use.";
       type string {
         length "1 .. 64";
       }
     }
     leaf nak-unknown-rebind {
       description "Nak unknown rebind requests";
       type empty;
     }
     leaf nak-unknown-renew {
       description "Nak unknown renew requests";
       type empty;
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf apply-secondary-as-giaddr {
       description "Enable DHCP relay to use secondary gateway ip for relay interfaces";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping packet-capture-egress-intf-type {
     uses apply-advanced;
     list interface {
       key name;
       description "Interface options";
       leaf name {
         description "Interface name";
         type union {
           type jt:interface-device;
           type string {
             pattern "<.*>|$.*";
           }
         }
       }
       uses apply-advanced;
     }
   }
   grouping packet_accounting_output_type {
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list cflowd {
       key name;
       description "Cflowd collector where flow records are sent";
       uses cflowd_packet_accounting_type;
     }
     list interface {
       key name;
       description "Interfaces used to send monitored information";
       uses packet_export_intf_type;
     }
   }
   grouping cflowd_packet_accounting_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf version {
       description "Format of exported cflowd aggregates";
       default "5";
       type enumeration {
         enum "5" {
           description "Export cflowd aggregates in version 5 format";
         }
         enum "8" {
           description "Export cflowd aggregates in version 8 format";
         }
       }
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
   }
   grouping packet_export_intf_type {
     leaf name {
       description "Interfaces used to send monitored information";
       type union {
         type jt:interface-unit;
         type string {
           pattern "<.*>|$.*";
         }
       }
     }
     uses apply-advanced;
     leaf engine-id {
       description "Identity (number) of this accounting interface";
       type union {
         type uint8;
         type string {
           pattern "<.*>|$.*";
         }
       }
     }
     leaf engine-type {
       description "Type (number) of this accounting interface";
       type union {
         type uint8;
         type string {
           pattern "<.*>|$.*";
         }
       }
     }
     leaf source-address {
       description "Address to use for generating monitored packets";
       type jt:ipaddr;
     }
   }
   grouping parameter-pair {
     leaf name {
       description "Parameter key";
       type string;
     }
     uses apply-advanced;
     leaf value {
       description "Parameter value";
       type string;
     }
   }
   grouping peer-group {
     leaf name {
       description "IP address for this peer";
       type jt:ipv4addr;
     }
     uses apply-advanced;
     leaf local-ip-addr {
       description "Local IP address to use for this peer alone.";
       type jt:ipv4addr;
     }
     leaf session-establishment-hold-time {
       description "Time within which connection must succeed with this peer";
       units "seconds";
       type union {
         type string {
           pattern "<.*>|$.*";
         }
         type uint32 {
           range "45 .. 600";
         }
       }
     }
     container backup-liveness-detection {
       presence "enable backup-liveness-detection";
       description "Backup liveness detection";
       uses apply-advanced;
       leaf backup-peer-ip {
         description "Backup livelness detection peer's IP address";
         type jt:ipv4addr;
       }
       leaf routing-instance {
         description "Name of the routing instance through which Backup liveness detection peer's IP reachable";
         type string {
           length "1 .. 128";
         }
       }
     }
     container liveness-detection {
       presence "enable liveness-detection";
       description "Bidirectional Forwarding Detection options for the peer";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
     }
     leaf authentication-key {
       description "MD5 authentication key";
       type string {
         length "1 .. 126";
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     description "Filter to apply to tracing";
     leaf match-on {
       description "Argument on which to match";
       type enumeration {
         enum "prefix" {
           description "Filter based on prefix";
         }
       }
       mandatory true;
     }
     leaf-list policy {
       ordered-by user;
       description "Filter policy";
       type jt:policy-algebra;
     }
   }
   grouping pim_rp_group_range_type {
     leaf name {
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping pm-rspan-vlan {
     description "RSPAN vlan for pm";
     leaf name {
       description "VLAN name or VLAN id";
       type string {
       }
     }
     uses apply-advanced;
     leaf no-tag {
       description "Removes extra RSPAN tag from mirrored packets";
       type empty;
     }
   }
   grouping pm_family_input_type {
     description "Input options for port mirroring";
     uses apply-advanced;
     leaf rate {
       description "Ratio of packets to be sampled (1 out of N)";
       type union {
         type string {
           pattern "<.*>|$.*";
         }
         type uint32;
       }
     }
     leaf run-length {
       description "Number of samples after initial trigger";
       type union {
         type string {
           pattern "<.*>|$.*";
         }
         type uint32 {
           range "0 .. 20";
         }
       }
     }
     leaf maximum-packet-length {
       description "Maximum length of the mirrored packet";
       default "0";
       units "bytes";
       type union {
         type string {
           pattern "<.*>|$.*";
         }
         type uint32 {
           range "0 .. 9216";
         }
       }
     }
   }
   grouping ppp_options_type {
     uses apply-advanced;
     leaf dynamic-profile {
       description "Dynamic profile name";
       type string;
     }
     container chap {
       presence "enable chap";
       description "Challenge Handshake Authentication Protocol options";
       uses apply-advanced;
       choice access-data {
         case case_1 {
           leaf access-profile {
             description "Profile containing client list and access parameters";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
     }
     container pap {
       presence "enable pap";
       description "Password Authentication Protocol options";
       uses apply-advanced;
       choice access-data {
         case case_1 {
           leaf access-profile {
             description "Profile containing client list and access parameters";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         type empty;
       }
     }
     container compression {
       description "Set compression options";
       leaf acfc {
         description "Negotiate Address/Control field compression";
         type empty;
       }
       leaf pfc {
         description "Negotiate Protocol field compression";
         type empty;
       }
     }
     leaf lcp-restart-timer {
       description "LCP restart timer";
       units "milliseconds";
       type union {
         type string {
           pattern "<.*>|$.*";
         }
         type uint16 {
           range "20 .. 10000";
         }
       }
     }
     leaf ncp-restart-timer {
       description "NCP restart timer";
       units "milliseconds";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       type union {
         type string {
           pattern "<.*>|$.*";
         }
         type uint8 {
           range "1 .. 60";
         }
       }
     }
     leaf lcp-max-conf-req {
       description "Maximum LCP Conf-Req to be sent, 0 means infinite";
       type union {
         type string {
           pattern "<.*>|$.*";
         }
         type uint32 {
           range "0 .. 65535";
         }
       }
     }
     leaf ncp-max-conf-req {
       description "Maximum NCP Conf-Req to be sent, 0 means infinite";
       type union {
         type string {
           pattern "<.*>|$.*";
         }
         type uint32 {
           range "0 .. 65535";
         }
       }
     }
     leaf on-demand-ip-address {
       description "Enable On-Demand IPv4 address allocation and de-allocation";
       type empty;
     }
     leaf aaa-options {
       description "Attach AAA options name to dynamic-profile";
       type string {
         length "1 .. 63";
       }
     }
     leaf service-profile {
       description "Default service profile";
       type string {
         length "1 .. 128";
       }
     }
     container initiate-ncp {
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mtu {
       description "The Maximum Transfer Unit size in bytes";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
     leaf lcp-connection-update {
       description "Enable LCP connection update request to peer";
       type empty;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping prbs-config {
     description "Configuration of pseudorandom binary sequence test signal";
     uses apply-advanced;
     choice enable-prbs-choice {
       leaf enable-prbs {
         description "Enable PRBS test pattern generation and monitoring";
         type empty;
       }
       leaf no-enable-prbs {
         description "Don't enable PRBS test pattern generation and monitoring";
         type empty;
       }
     }
     leaf direction {
       description "Direction of generated and received PRBS test signal";
       default "line";
       type enumeration {
         enum "local" {
           description "Test signal generated towards and received from host-side";
         }
         enum "line" {
           description "Test signal generated towards and received from network-side";
         }
       }
     }
     leaf pattern {
       description "Pattern to use for PRBS test signal";
       default "prbs-31";
       type enumeration {
         enum "prbs-31" {
           description "2^31 polynomial PRBS test signal, as per G.709";
         }
         enum "prbs-23" {
           description "2^23 polynomial PRBS test signal, SONET/SDH framed";
         }
         enum "prbs-15" {
           description "2^15 polynomial PRBS test signal";
         }
         enum "prbs-7" {
           description "2^7 polynomial PRBS test signal";
         }
       }
     }
     choice invert-choice {
       leaf invert {
         description "Invert the test pattern";
         type empty;
       }
       leaf no-invert {
         description "Don't invert the test pattern";
         type empty;
       }
     }
   }
   grouping prefix_action {
     leaf name {
       description "Prefix action name";
       type string {
       }
     }
     uses apply-advanced;
     leaf policer {
       description "Police the packet using a set of named policer";
       type string {
       }
     }
     leaf count {
       description "Enable counters";
       type empty;
     }
     leaf filter-specific {
       description "Filter specific, else term specific";
       type empty;
     }
     leaf subnet-prefix-length {
       description "Prefix length for the total address range";
       type union {
         type string {
           pattern "<.*>|$.*";
         }
         type uint32 {
           range "0 .. 32";
         }
       }
     }
     choice source_or_dest {
       case case_1 {
         leaf source-prefix-length {
           description "Source prefix range";
           type union {
             type string {
               pattern "<.*>|$.*";
             }
             type uint32 {
               range "0 .. 32";
             }
           }
         }
       }
       case case_2 {
         leaf destination-prefix-length {
           description "Destination prefix range";
           type union {
             type string {
               pattern "<.*>|$.*";
             }
             type uint32 {
               range "0 .. 32";
             }
           }
         }
       }
     }
   }
   grouping prefix_count_type {
     description "Number of BGP prefixes limit";
     uses apply-advanced;
     leaf count {
       description "Number of BGP prefixes limit";
       type union {
         type string {
           pattern "<.*>|$.*";
         }
         type uint32 {
           range "0 .. 10000000";
         }
       }
       mandatory true;
     }
     choice count-operator {
       case case_1 {
         leaf orhigher {
           description "Match higher or equal values";
           type empty;
         }
       }
     }
   }
   grouping prefix_list_items {
     leaf name {
       description "Address prefix";
       type jt:ipprefix-only;
     }
     uses apply-advanced;
   }
   grouping programmable-rpd-type {
     uses apply-advanced;
     container traceoptions {
       description "Trace options";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "client" {
               description "Client events";
             }
             enum "japi" {
               description "JAPI related traces";
             }
             enum "routing-interface" {
               description "Routing interface traces";
             }
             enum "te-path-compute" {
               description "TE Path Computation traces";
             }
             enum "statistics" {
               description "Statistics related traces";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     container purge-timeout {
       presence "enable purge-timeout";
       description "Purge timeout for all programmable-rpd clients in seconds";
       choice purge-parm {
         case case_1 {
           leaf never {
             description "Client programmed objects are never purged";
             type empty;
           }
         }
         case case_2 {
           leaf timeout {
             description "Timeout value, in seconds, for purging client programmed objects";
             units "seconds";
             type union {
               type string {
                 pattern "<.*>|$.*";
               }
               type uint32 {
                 range "1 .. 604800";
               }
             }
           }
         }
       }
     }
     list client {
       key name;
       ordered-by user;
       description "Programmable-rpd client options";
       leaf name {
         description "Client ID";
         type string {
           length "1 .. 255";
         }
       }
       uses apply-advanced;
       list interface-notification {
         key name;
         ordered-by user;
         description "Interfaces for notification";
         leaf name {
           description "Interface";
           type string {
             length "1 .. 32";
           }
         }
         uses apply-advanced;
       }
     }
     container rib-service {
       presence "enable rib-service";
       description "RIB service API options";
       uses apply-advanced;
       container dynamic-next-hop-interface {
         presence "enable dynamic-next-hop-interface";
         description "Update routes for next-hop interface changes";
         uses apply-advanced;
         choice enable-disable {
           case case_1 {
             leaf disable {
               description "Disable dynamic next-hop interface handling";
               type empty;
             }
           }
         }
       }
     }
     leaf stats-sampling-interval {
       description "Sampling interval for programmable rpd statisitics";
       default "30";
       units "seconds";
       type union {
         type string {
           pattern "<.*>|$.*";
         }
         type uint32 {
           range "30 .. 3600";
         }
       }
     }
     leaf stats-aggregation-interval {
       description "Aggregation interval for programmable rpd statistics";
       default "60";
       units "seconds";
       type union {
         type string {
           pattern "<.*>|$.*";
         }
         type uint32 {
           range "60 .. 3600";
         }
       }
     }
     leaf no-rpc-recording {
       description "Do not turn on rpc recording";
       type empty;
     }
     container rpc-recording {
       presence "enable rpc-recording";
       description "Recording options";
       uses apply-advanced;
       leaf size {
         description "Memory size reserved for recording";
         type string;
       }
       leaf files {
         description "Maximum number of dump files";
         default "4";
         type union {
           type string {
             pattern "<.*>|$.*";
           }
           type uint32 {
             range "1 .. 50";
           }
         }
       }
     }
   }
   grouping qualified_nh_obj {
     leaf name {
       description "Next hop to destination";
       type union {
         type jt:ipaddr-or-interface;
         type string {
           pattern "<.*>|$.*";
         }
       }
       mandatory true;
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf order {
       description "Order of qualified next hop";
       type union {
         type string {
           pattern "<.*>|$.*";
         }
         type uint16 {
           range "1 .. 65535";
         }
       }
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       leaf inline-disable {
         description "Disable inline mode for this BFD session";
         type empty;
       }
       leaf pdu-size {
         description "BFD transport protocol payload size";
         default "24";
         type union {
           type string {
             pattern "<.*>|$.*";
           }
           type uint32 {
             range "24 .. 16000";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       container echo {
         description "Echo mode parameters";
         uses apply-advanced;
         leaf minimum-interval {
           description "Minimum transmit and receive interval";
           units "milliseconds";
           type union {
             type string {
               pattern "<.*>|$.*";
             }
             type uint32 {
               range "100 .. 255000";
             }
           }
           mandatory true;
         }
       }
       container echo-lite {
         description "Echo-lite more parameters";
         uses apply-advanced;
         leaf minimum-interval {
           description "Minimum transmit and receive interval";
           units "milliseconds";
           type union {
             type string {
               pattern "<.*>|$.*";
             }
             type uint32 {
               range "1 .. 255000";
             }
           }
           mandatory true;
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping reconfigure-trigger-type {
     description "DHCP reconfigure trigger";
     uses apply-advanced;
     leaf radius-disconnect {
       description "Trigger DHCP reconfigure by radius initiated disconnect";
       type empty;
     }
   }
   grouping reconfigure-type {
     description "DHCP reconfigure processing";
     uses apply-advanced;
     leaf clear-on-abort {
       description "Delete client on reconfiguration abort";
       type empty;
     }
     leaf defer-nack-on-abort {
       description "Defer client NACK on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping relay-bulk-leasequery-v4-type {
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       container vlan-id-only {
         presence "enable vlan-id-only";
         description "Use only VLAN id";
         uses apply-advanced;
       }
       leaf no-vlan-interface-name {
         description "Not include vlan or interface name";
         type empty;
       }
       leaf include-irb-and-l2 {
         description "Include IRB and L2 interface name";
         type empty;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       container hostname-only {
         presence "enable hostname-only";
         description "Include hostname only";
         uses apply-advanced;
       }
       container user-defined {
         presence "enable user-defined";
         description "Include user defined string";
         uses apply-advanced;
         leaf string {
           description "Set user-defined character string description";
           type string {
             length "1 .. 252";
           }
         }
         leaf hex-string {
           description "Set user-defined hexadecimal string description";
           type string {
             length "1 .. 510";
           }
         }
       }
       leaf keep-incoming-remote-id {
         description "Keep incoming remote identifier";
         type empty;
       }
       leaf use-string {
         description "Use raw string instead of the default remote id";
         status deprecated;
         type string;
       }
     }
     leaf server-id-override {
       description "Add link-selection and server-id sub-options on packets to server";
       type empty;
     }
     leaf link-selection {
       description "Add link-selection suboption on packets to server";
       type empty;
     }
     leaf exclude-relay-agent-identifier {
       description "Exclude relay agent identifier from packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
           mandatory true;
         }
       }
     }
     leaf protocol-instance-name {
       description "Name of protocol instance under routing instance";
       type string;
     }
     list route {
       key name;
       description "Individual route options";
       leaf name {
         description "Destination prefix";
         type jt:ipprefix;
       }
       uses apply-advanced;
       leaf description {
         description "Description for aggregate routes";
         type string {
         }
       }
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
       container algorithm {
         description "Algorithm number";
         leaf number {
           description "Algorithm number";
           type union {
             type string {
               pattern "<.*>|$.*";
             }
             type uint32 {
               range "0 .. 255";
             }
           }
           mandatory true;
         }
       }
     }
   }
   grouping rib_group_inet_type {
     description "Routing table group";
     leaf ribgroup-name {
       description "Name of the routing table group";
       type string;
       mandatory true;
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_list_items {
     leaf name {
       description "RIB name or wildcard";
       type string;
     }
     uses apply-advanced;
   }
   grouping rib_static_metric_type {
     leaf metric-value {
       description "Metric value";
       type union {
         type uint32;
         type string {
           pattern "<.*>|$.*";
         }
       }
       mandatory true;
     }
     leaf type {
       description "Metric type";
       type union {
         type string {
           pattern "<.*>|$.*";
         }
         type uint32 {
           range "1 .. 16";
         }
       }
     }
   }
   grouping rip_filter_obj {
     description "Filter to apply to tracing";
     leaf match-on {
       description "Argument on which to match";
       type enumeration {
         enum "prefix" {
           description "Filter based on prefix";
         }
       }
       mandatory true;
     }
     leaf-list policy {
       ordered-by user;
       description "Filter policy";
       type jt:policy-algebra;
     }
   }
   grouping rmopd-traceoptions {
     description "Trace options for remote-monitoring";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping route_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     leaf get-route-range {
       description "Get the range";
       type empty;
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping route_record_traceoptions {
     description "Traceoptions for sampling route record";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of route-record to enable debuging output";
       leaf name {
         type enumeration {
           enum "parse" {
             description "Trace parsing code";
           }
           enum "all" {
             description "Trace all area of jflow-service code";
           }
         }
       }
     }
   }
   grouping rpd-rib-export-group-type {
     description "RIB export group";
     leaf name {
       description "RIB export group name";
       type string;
     }
     uses apply-advanced;
     container traceoptions {
       description "Trace options";
       uses apply-advanced;
       container file {
         description "Trace file options";
         leaf filename {
           description "Name of file in which to write trace information";
           type string {
             length "1 .. 1024";
           }
           mandatory true;
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "export" {
               description "Export processing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf-list to-rib {
       ordered-by user;
       description "Import routing table";
       type string;
     }
     leaf-list policy {
       ordered-by user;
       description "Attribute drop policy";
       type jt:policy-algebra;
     }
   }
   grouping rpd_rib_group_type {
     description "Routing table group";
     leaf name {
       description "Routing table group";
       type string;
     }
     uses apply-advanced;
     leaf export-rib {
       description "Export routing table";
       type string;
     }
     leaf-list import-rib {
       ordered-by user;
       description "Import routing table";
       type string;
     }
     leaf-list import-policy {
       ordered-by user;
       description "Import policy";
       type jt:policy-algebra;
     }
   }
   grouping rtf_prefix_list_items {
     leaf name {
       description "Family route-target prefix";
       type string {
         length "1 .. 63";
       }
     }
     uses apply-advanced;
   }
   grouping sampling_family_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_sampling_inet6_sampling_type;
     }
     list interface {
       key name;
       description "Interfaces used to send monitored information";
       max-elements 1;
       uses packet_export_intf_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
         mandatory true;
       }
       uses apply-advanced;
     }
   }
   grouping cflowd_sampling_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
   }
   grouping packet_export_inline {
     uses apply-advanced;
     leaf source-address {
       description "Address to use for generating monitored packets";
       type jt:ipaddr;
       mandatory true;
     }
     leaf flow-export-rate {
       description "Flow export rate of monitored packets in kpps";
       type union {
         type string {
           pattern "<.*>|$.*";
         }
         type uint32 {
           range "1 .. 3200";
         }
       }
     }
   }
   grouping sampling_family_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_global_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_global_mpls_sampling_type;
     }
     list interface {
       key name;
       description "Interfaces used to send monitored information";
       max-elements 1;
       uses packet_export_intf_type;
     }
   }
   grouping cflowd_global_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
   }
   grouping sampling_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
     container family {
       presence "enable family";
       description "Protocol family";
       status deprecated;
       container inet {
         description "Sampling parameters for IPv4";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
     }
   }
   grouping sampling_instance_inet_global_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
         mandatory true;
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_inet_type;
     }
     list interface {
       key name;
       description "Interfaces used to send monitored information";
       max-elements 1;
       uses packet_export_intf_type;
     }
     list extension-service {
       key name;
       ordered-by user;
       description "Define the customer specific sampling configuration";
       leaf name {
         description "Customer prefixed sampling service name";
         type string {
           length "1 .. 63";
         }
         mandatory true;
       }
       uses apply-advanced;
     }
   }
   grouping cflowd_sampling_inet_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
         mandatory true;
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_type;
     }
     list interface {
       key name;
       description "Interfaces used to send monitored information";
       max-elements 1;
       uses packet_export_intf_type;
     }
     list extension-service {
       key name;
       ordered-by user;
       description "Define the customer specific sampling configuration";
       leaf name {
         description "Customer prefixed sampling service name";
         type string {
           length "1 .. 63";
         }
         mandatory true;
       }
       uses apply-advanced;
     }
   }
   grouping cflowd_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
       mandatory true;
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_traceoptions_type {
     description "Configure packet sampling traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
   }
   grouping satellite-policy-options {
     uses apply-advanced;
     list extended-ports-template {
       key name;
       ordered-by user;
       description "Extended ports template";
       leaf name {
         type string {
           length "1 .. 32";
         }
       }
       uses apply-advanced;
       list pic {
         key name;
         description "PIC attributes";
         uses satellite-pic-type;
       }
     }
     list port-group-alias {
       key name;
       ordered-by user;
       description "Port group alias";
       leaf name {
         type string {
           length "1 .. 32";
         }
       }
       uses apply-advanced;
       list pic {
         key name;
         ordered-by user;
         description "Satellite PIC information";
         leaf name {
           description "PIC identifier";
           type union {
             type int32;
             type string {
               pattern "<.*>|$.*";
             }
           }
         }
         uses apply-advanced;
         leaf-list port {
           ordered-by user;
           description "Port id or range or all";
           type union {
             type string {
               pattern "<.*>|$.*";
             }
             type uint32 {
               range "0 .. 1024";
             }
           }
         }
       }
     }
     list chassis-group-alias {
       key name;
       ordered-by user;
       description "Chassis group alias";
       leaf name {
         description "Chassis group alias name";
         type string {
           length "1 .. 32";
         }
       }
       uses apply-advanced;
       leaf prefer-primary {
         description "Primary mode chassis will be preferred";
         type empty;
       }
       list chassis-id {
         key name;
         ordered-by user;
         description "List of chassis-ids";
         leaf name {
           description "Chassis ID";
           type union {
             type string {
               pattern "<.*>|$.*";
             }
             type uint32 {
               range "1 .. 255";
             }
           }
         }
         uses apply-advanced;
         container mode {
           description "Mode Primary or Backup";
           uses apply-advanced;
           choice mode-choice {
             case case_1 {
               leaf primary {
                 description "Primary Mode";
                 type empty;
               }
             }
             case case_2 {
               leaf backup {
                 description "Backup Mode";
                 type empty;
               }
             }
           }
         }
         list core-interface {
           key name;
           ordered-by user;
           description "Core interface";
           leaf name {
             description "Core interface name";
             type union {
               type jt:interface-device;
               type string {
                 pattern "<.*>|$.*";
               }
             }
           }
           uses apply-advanced;
         }
       }
     }
     list extended-ports-policy {
       key name;
       ordered-by user;
       description "Define a extended-ports-policy";
       leaf name {
         description "Policy name";
         type string {
           length "1 .. 32";
         }
       }
       uses apply-advanced;
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           leaf extended-ports-template {
             description "Apply extended ports template to satellite matching conditions defined in this term";
             type string;
             mandatory true;
           }
         }
       }
     }
     list candidate-uplink-port-policy {
       key name;
       ordered-by user;
       description "Define a candidate uplink-port policy";
       leaf name {
         description "Policy name";
         type string {
           length "1 .. 32";
         }
       }
       uses apply-advanced;
       leaf uplink-port-group {
         description "Uplink port group alias name";
         type string;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           leaf uplink-port-group {
             description "Uplink port group alias name";
             type string;
           }
           leaf minimum-links {
             description "Minimum child links to keep extended-ports UP";
             type union {
               type string {
                 pattern "<.*>|$.*";
               }
               type uint16 {
                 range "1 .. 32";
               }
             }
           }
           leaf holddown {
             description "Time to hold down after uplink failure";
             units "seconds";
             type union {
               type string {
                 pattern "<.*>|$.*";
               }
               type uint32 {
                 range "1 .. 600";
               }
             }
           }
         }
       }
     }
     list environment-monitoring-policy {
       key name;
       ordered-by user;
       description "Define a environment monitoring policy";
       leaf name {
         description "Policy name";
         type string {
           length "1 .. 32";
         }
       }
       uses apply-advanced;
       container alarm {
         presence "enable alarm";
         description "Policy default alarm policy";
         uses apply-advanced;
         leaf linkdown {
           description "Policy default linkdown alarm";
           type enumeration {
             enum "ignore" {
               description "Ignore ethernet linkdown";
             }
             enum "red" {
               description "Raise major alarm for ethernet linkdown";
             }
             enum "yellow" {
               description "Raise minor alarm for ethernet linkdown";
             }
           }
           mandatory true;
         }
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           container alarm {
             presence "enable alarm";
             description "Term alarm policy";
             uses apply-advanced;
             leaf linkdown {
               description "Set linkdown alarm";
               type enumeration {
                 enum "ignore" {
                   description "Ignore ethernet linkdown";
                 }
                 enum "red" {
                   description "Raise major alarm for ethernet linkdown";
                 }
                 enum "yellow" {
                   description "Raise minor alarm for ethernet linkdown";
                 }
               }
               mandatory true;
             }
           }
         }
       }
     }
     list forwarding-policy {
       key name;
       ordered-by user;
       description "Define forwarding policy for extended ports";
       leaf name {
         description "Policy name";
         type string {
           length "1 .. 32";
         }
       }
       uses apply-advanced;
       list port-group-extended {
         key name;
         ordered-by user;
         description "Define a extend port group mapping";
         uses port-extend-type;
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           list port-group-extended {
             key name;
             ordered-by user;
             description "Define a extend port group mapping";
             uses port-extend-type;
           }
         }
       }
     }
   }
   grouping port-extend-type {
     leaf name {
       description "Extended port group alias name policy applied on";
       type string;
     }
     uses apply-advanced;
     leaf filter {
       description "Assign a filter for uplink selection";
       type string;
     }
     container port-group-uplink {
       description "Define a uplink port group mapping";
       uses apply-advanced;
       leaf port-group-uplink-alias {
         description "Uplink port group alias name used for uplink pinning mode";
         type string;
         mandatory true;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
     }
     container mirror-ingress {
       description "Define a ingress port mirror";
       uses apply-advanced;
       leaf port-group-mirror {
         description "Mirror port group alias name for local port mirroring";
         type string;
       }
     }
     container mirror-egress {
       description "Define a egress port mirror";
       uses apply-advanced;
       leaf port-group-mirror {
         description "Mirror port group alias name for local port mirroring";
         type string;
       }
     }
   }
   grouping satellite-pic-type {
     leaf name {
       description "PIC slot number";
       type union {
         type string {
           pattern "<.*>|$.*";
         }
         type uint32 {
           range "0 .. 4";
         }
       }
     }
     uses apply-advanced;
     list port {
       key name;
       description "Port number";
       uses satellite-pic-port-attr;
     }
     list port-range {
       key "port-range-low port-range-high";
       ordered-by user;
       description "Physical ports to channelize";
       leaf port-range-low {
         description "Port range low number";
         type union {
           type string {
             pattern "<.*>|$.*";
           }
           type uint32 {
             range "0 .. 127";
           }
         }
         mandatory true;
       }
       leaf port-range-high {
         description "Port range high number";
         type union {
           type string {
             pattern "<.*>|$.*";
           }
           type uint32 {
             range "0 .. 127";
           }
         }
         mandatory true;
       }
       uses apply-advanced;
       leaf channel-speed {
         description "Port channel speed";
         type enumeration {
           enum "10g" {
             description "Set the port speed to 10G";
           }
           enum "disable-auto-speed-detection" {
             description "Disables automatic speed detection";
           }
         }
       }
     }
   }
   grouping satellite-pic-port-attr {
     leaf name {
       description "Port number";
       type union {
         type string {
           pattern "<.*>|$.*";
         }
         type uint32 {
           range "0 .. 127";
         }
       }
     }
     uses apply-advanced;
     leaf channel-speed {
       description "Port channel speed";
       type enumeration {
         enum "10g" {
           description "Set the port speed to 10G";
         }
         enum "25g" {
           description "Set the port speed to 25G";
         }
         enum "50g" {
           description "Set the port speed to 50G";
         }
         enum "disable-auto-speed-detection" {
           description "Disables automatic speed detection";
         }
       }
     }
   }
   grouping sec-object {
     description "Specify security-name";
     uses apply-advanced;
     leaf security-name {
       description "Specify v3 security-name";
       type string {
         length "1 .. 32";
       }
       mandatory true;
     }
     leaf context {
       description "Specify context name associated to this security-name";
       type string;
       mandatory true;
     }
   }
   grouping security-authentication-key-chains {
     uses apply-advanced;
     list key-chain {
       key name;
       description "Key chain configuration";
       leaf name {
         description "Name of authentication key chain";
         type string {
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           type union {
             type string {
               pattern "<.*>|$.*";
             }
             type uint32 {
               range "0 .. 63";
             }
           }
         }
         uses apply-advanced;
         leaf secret {
           description "Authentication key";
           type string {
             length "1 .. 126";
           }
           mandatory true;
         }
         leaf key-name {
           description "Key name in hexadecimal format used for macsec";
           type string {
             length "2 .. 64";
           }
         }
         leaf start-time {
           description "Start time for key transmission (YYYY-MM-DD.HH:MM)";
           type jt:time;
           mandatory true;
         }
         leaf algorithm {
           description "Authentication algorithm";
           default "md5";
           type enumeration {
             enum "md5" {
               description "Message Digest 5";
             }
             enum "hmac-sha-1" {
               description "Hash-based Message Authentication Code (SHA1) (96 bits)";
             }
             enum "ao" {
               description "TCP Authentication Option";
             }
             enum "sha-1" {
               description "SHA1";
             }
             enum "hmac-sha2-224" {
               description "Hash-based message authentication code (SHA2-224)";
             }
             enum "hmac-sha2-256" {
               description "Hash-based message authentication code (SHA2-256)";
             }
             enum "hmac-sha2-384" {
               description "Hash-based message authentication code (SHA2-384)";
             }
             enum "hmac-sha2-512" {
               description "Hash-based message authentication code (SHA2-512)";
             }
           }
         }
         leaf fallback {
           description "Fallback authentication algorithm";
           type enumeration {
             enum "hmac-sha-1" {
               description "Hash-based Message Authentication
                        Code (SHA1) (96 bits)";
             }
             enum "sha-1" {
               description "SHA1";
             }
           }
         }
         leaf options {
           description "Protocol's transmission encoding format";
           default "basic";
           type enumeration {
             enum "basic" {
               description "Rudimentary encoding format";
             }
             enum "isis-enhanced" {
               description "RFC 5310 based encoding";
             }
           }
         }
         container ao-attribute {
           description "TCP Authentication option attributes";
           uses apply-advanced;
           leaf send-id {
             description "Send id for TCP-AO entry";
             type union {
               type string {
                 pattern "<.*>|$.*";
               }
               type uint32 {
                 range "0 .. 255";
               }
             }
             mandatory true;
           }
           leaf recv-id {
             description "Recv id for TCP-AO entry";
             type union {
               type string {
                 pattern "<.*>|$.*";
               }
               type uint32 {
                 range "0 .. 255";
               }
             }
             mandatory true;
           }
           leaf tcp-ao-option {
             description "Include TCP-AO option within message header";
             default "disabled";
             type enumeration {
               enum "enabled" {
                 description "Include the TCP-AO option";
               }
               enum "disabled" {
                 description "Not include the TCP-AO option";
               }
             }
           }
           leaf cryptographic-algorithm {
             description "Cryptographic algorithm for TCP-AO Traffic key and MAC digest generation";
             default "hmac-sha-1-96";
             type enumeration {
               enum "hmac-sha-1-96" {
                 description "Hash-based Message Authentication Code (SHA1) (96 bits)";
               }
               enum "aes-128-cmac-96" {
                 description "Cipher-based Message Authentication Code (AES128) (96 bits)";
               }
             }
           }
         }
       }
     }
   }
   grouping security-group-vpn {
     uses apply-advanced;
     container member {
       description "Group VPN member configuration";
       uses gvpn-member;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
         mandatory true;
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
           case case_4 {
             leaf distinguished-name {
               description "Use a distinguished name specified in local certificate";
               type empty;
             }
           }
         }
       }
       leaf local-address {
         description "Local IPv4 address for group member";
         type jt:ipv4addr;
         mandatory true;
       }
       leaf routing-instance {
         description "Name of routing instance that hosts local address";
         default "default";
         type string;
       }
     }
   }
   grouping gvpn-ike-policy {
     leaf name {
       description "Name of policy";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       type string {
         length "1 .. 32";
       }
     }
     container certificate {
       description "Certificate configuration";
       uses apply-advanced;
       leaf local-certificate {
         description "Local certificate identifier";
         type string {
         }
       }
       container trusted-ca {
         description "Specify the CA to use";
         status deprecated;
         choice ca {
           case case_1 {
             leaf ca-index {
               description "Index of the preferred CA to use";
               type union {
                 type uint32;
                 type string {
                   pattern "<.*>|$.*";
                 }
               }
             }
           }
           case case_2 {
             leaf use-all {
               description "Use all configured CAs";
               type empty;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
     }
     leaf proposal-set {
       description "Types of default IKE proposal-set";
       type enumeration {
         enum "basic" {
           description "IKE proposal-set for basic";
         }
         enum "compatible" {
           description "IKE proposal-set for compatible";
         }
         enum "standard" {
           description "IKE proposal-set for standard";
         }
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping gvpn-member-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
       }
       mandatory true;
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping ipsec-gvpn-member-template {
     description "Configure a Group VPN";
     leaf name {
       description "Name of the VPN";
       type string {
         length "1 .. 32";
       }
     }
     uses apply-advanced;
     leaf ike-gateway {
       description "Name of IKE gateway";
       type string {
         length "1 .. 32";
       }
       mandatory true;
     }
     leaf group {
       description "Enable Group VPN by defining group id";
       type union {
         type string {
           pattern "<.*>|$.*";
         }
         type uint32 {
           range "1 .. 65535";
         }
       }
       mandatory true;
     }
     leaf match-direction {
       description "Direction for which the rule match is applied";
       type enumeration {
         enum "input" {
           description "Match on input to interface";
         }
         enum "output" {
           description "Match on output from interface";
         }
       }
       mandatory true;
     }
     leaf tunnel-mtu {
       description "Maximum transmit packet size";
       default "1500";
       type union {
         type string {
           pattern "<.*>|$.*";
         }
         type uint32 {
           range "256 .. 9192";
         }
       }
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     leaf forward-policy-mismatch {
       description "Enables forwarding of policy mismatch packets";
       type empty;
     }
     container fail-open {
       description "List of fail open rules";
       uses ipsec_gvpn_fail_open_rule_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       type string {
         length "1 .. 63";
       }
     }
     uses apply-advanced;
     container source-address {
       description "Match IP source address";
       presence "enable source-address";
       uses ipsec_gvpn_addr_object;
     }
     container destination-address {
       description "Match IP destination address";
       presence "enable destination-address";
       uses ipsec_gvpn_addr_object;
     }
   }
   grouping ipsec_gvpn_addr_object {
     uses apply-advanced;
     leaf address {
       description "Prefix to match";
       type jt:ipv4prefix-only;
     }
   }
   grouping security-ike {
     uses apply-advanced;
     container traceoptions {
       description "Trace options for IPSec key management";
       uses security-traceoptions;
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
         mandatory true;
       }
       choice remote-identifier {
         case case_1 {
           leaf-list address {
             ordered-by user;
             description "Addresses or hostnames of peer:1 primary, upto 4 backups";
             type string;
           }
         }
         case case_2 {
           container dynamic {
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf hostname {
                   description "Use a fully-qualified domain name";
                   type string;
                 }
               }
               case case_3 {
                 leaf inet {
                   description "Use an IPV4 address to identify the dynamic peer";
                   type jt:ipv4addr;
                 }
               }
               case case_4 {
                 leaf inet6 {
                   description "Use an IPV6 address to identify the dynamic peer";
                   type jt:ipv6addr;
                 }
               }
               case case_5 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                 }
               }
             }
           }
         }
       }
       container dead-peer-detection {
         presence "enable dead-peer-detection";
         description "Enable RFC-3706 DPD";
         uses apply-advanced;
         leaf always-send {
           description "Send DPD messages periodically, regardless of traffic";
           type empty;
         }
         leaf interval {
           description "The interval at which to send DPD messages";
           default "10";
           units "seconds";
           type union {
             type string {
               pattern "<.*>|$.*";
             }
             type uint32 {
               range "10 .. 60";
             }
           }
         }
         leaf threshold {
           description "Maximum number of DPD retransmissions";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "5";
         units "seconds";
         type union {
           type string {
             pattern "<.*>|$.*";
           }
           type uint32 {
             range "1 .. 300";
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container inet6 {
               description "Use an IPv6 address";
               uses apply-advanced;
               leaf identity-ipv6 {
                 description "The local IPv6 identity";
                 type jt:ipv6addr;
               }
             }
           }
           case case_3 {
             container hostname {
               description "Use a fully-qualified domain name";
               uses apply-advanced;
               leaf identity-hostname {
                 description "The local hostname";
                 type string;
               }
             }
           }
           case case_4 {
             container user-at-hostname {
               description "Use an e-mail address";
               uses apply-advanced;
               leaf identity-user {
                 description "The local user-FQDN";
                 type string;
               }
             }
           }
           case case_5 {
             leaf distinguished-name {
               description "Use a distinguished name specified in local certificate";
               type empty;
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container inet6 {
               description "Use an IPv6 address";
               uses apply-advanced;
               leaf identity-ipv6 {
                 description "The remote IPv6 identity";
                 type jt:ipv6addr;
               }
             }
           }
           case case_3 {
             container hostname {
               description "Use a fully-qualified domain name";
               uses apply-advanced;
               leaf identity-hostname {
                 description "The remote hostname";
                 type string;
               }
             }
           }
           case case_4 {
             container user-at-hostname {
               description "Use an e-mail address";
               uses apply-advanced;
               leaf identity-user {
                 description "The remote user-FQDN";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
         }
       }
       leaf external-interface {
         description "External interface for IKE negotiations";
         type union {
           type jt:interface-unit;
           type string {
             pattern "<.*>|$.*";
           }
         }
         mandatory true;
       }
       container xauth {
         description "Use extended authentication";
         leaf access-profile {
           description "Access profile that contains authentication information";
           type string;
           mandatory true;
         }
       }
       leaf general-ikeid {
         description "Accept peer IKE-ID in general";
         type empty;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
     }
   }
   grouping ike-policy {
     leaf name {
       description "IKE peer address";
       type jt:ipv4addr;
     }
     uses apply-advanced;
     leaf mode {
       description "Define the IKE first phase mode";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       type string {
         length "1 .. 32";
       }
     }
     leaf local-certificate {
       description "File to read certificate from";
       type string {
         length "1 .. 255";
       }
     }
     leaf local-key-pair {
       description "File to read key-pair from";
       type string {
         length "1 .. 255";
       }
     }
     leaf encoding {
       description "Encoding to use for certificate or CRL on disk";
       default "binary";
       type enumeration {
         enum "binary" {
           description "DER encoding";
         }
         enum "pem" {
           description "Privacy-enhanced-mail encoding, base64";
         }
       }
     }
     leaf identity {
       description "Define the remote certificate name";
       type string {
         length "1 .. 32";
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (254 bit modulus)";
         }
         enum "ecdsa-signatures-384" {
           description "ECDSA signatures (384 bit modulus)";
         }
       }
       mandatory true;
     }
     leaf dh-group {
       description "Define Diffie-Hellman group";
       type enumeration {
         enum "group1" {
           description "Diffie-Hellman Group1";
         }
         enum "group2" {
           description "Diffie-Hellman Group2";
         }
         enum "group5" {
           description "Diffie-Hellman Group5";
         }
         enum "group14" {
           description "Diffie-Hellman Group14";
         }
         enum "group15" {
           description "Diffie-Hellman Group15";
         }
         enum "group16" {
           description "Diffie-Hellman Group16";
         }
         enum "group19" {
           description "Diffie-Hellman Group19";
         }
         enum "group20" {
           description "Diffie-Hellman Group20";
         }
         enum "group24" {
           description "Diffie-Hellman Group24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping security-ipsec-vpn {
     uses apply-advanced;
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define an IPSec security association";
       uses ipsec-sa;
     }
     container internal {
       presence "enable internal";
       description "Define an IPSec SA for internal RE-RE communication";
       uses apply-advanced;
       container security-association {
         description "Define an IPSec security association";
         presence "enable security-association";
         uses ipsec-internal-sa;
       }
     }
     container trusted-channel {
       presence "enable trusted-channel";
       description "Define an IPSec SA for trusted-channel communication";
       uses apply-advanced;
       container security-association {
         description "Define an IPSec security association";
         presence "enable security-association";
         uses ipsec-trusted-channel-sa;
       }
       leaf-list port-exclusion-list {
         ordered-by user;
         description "Define port exlusion list";
         type union {
           type string {
             pattern "<.*>|$.*";
           }
           type uint32 {
             range "1 .. 65535";
           }
         }
       }
     }
   }
   grouping ipsec-internal-sa {
     uses apply-advanced;
     leaf description {
       description "Text description of internal security association";
       type string {
         length "1 .. 80";
       }
     }
     container manual {
       description "Define a manual security association";
       uses apply-advanced;
       list direction {
         key name;
         ordered-by user;
         description "Define the direction of the security association";
         leaf name {
           type enumeration {
             enum "inbound" {
               description "Inbound security association";
             }
             enum "outbound" {
               description "Outbound security association";
             }
             enum "bidirectional" {
               description "Bidirectional security association";
             }
           }
         }
         uses apply-advanced;
         leaf protocol {
           description "Define an IPSec protocol for the security association";
           type enumeration {
             enum "ah" {
               description "Authentication header";
             }
             enum "esp" {
               description "Encapsulated Security Payload header";
             }
             enum "bundle" {
               description "Bundle (AH authentication plus ESP encryption)";
             }
           }
           mandatory true;
         }
         leaf spi {
           description "Define security parameter index";
           type union {
             type string {
               pattern "<.*>|$.*";
             }
             type uint32 {
               range "256 .. 16639";
             }
           }
           mandatory true;
         }
         leaf auxiliary-spi {
           description "ESP security parameter index for IPSec SA bundle";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
             mandatory true;
           }
           container key {
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
             mandatory true;
           }
           container key {
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                   }
                 }
               }
             }
           }
         }
       }
     }
   }
   grouping ipsec-policy {
     leaf name {
       description "Name of the IPSec policy";
       type string {
         length "1 .. 32";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group1";
           }
           enum "group2" {
             description "Diffie-Hellman Group2";
           }
           enum "group5" {
             description "Diffie-Hellman Group5";
           }
           enum "group14" {
             description "Diffie-Hellman Group14";
           }
           enum "group15" {
             description "Diffie-Hellman Group15";
           }
           enum "group16" {
             description "Diffie-Hellman Group16";
           }
           enum "group19" {
             description "Diffie-Hellman Group19";
           }
           enum "group20" {
             description "Diffie-Hellman Group20";
           }
           enum "group24" {
             description "Diffie-Hellman Group24";
           }
         }
       }
     }
     leaf-list proposals {
       ordered-by user;
       description "Name of the proposal";
       type string {
         length "1 .. 32";
       }
     }
     leaf proposal-set {
       description "Types of default IPSEC proposal-set";
       type enumeration {
         enum "basic" {
           description "IPSEC basic proposal-set";
         }
         enum "compatible" {
           description "IPSEC compatible proposal-set";
         }
         enum "standard" {
           description "IPSEC standard proposal-set";
         }
       }
     }
   }
   grouping ipsec-proposal {
     leaf name {
       description "Name of the IPSec proposal";
       type string {
         length "1 .. 32";
       }
     }
     uses apply-advanced;
     leaf description {
       description "Text description of IPSec proposal";
       type string {
         length "1 .. 80";
       }
     }
     leaf protocol {
       description "Define an IPSec protocol for the proposal";
       type enumeration {
         enum "ah" {
           description "Authentication header";
         }
         enum "esp" {
           description "Encapsulated Security Payload header";
         }
         enum "bundle" {
           description "Bundle (AH authentication plus ESP encryption)";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
         }
         enum "hmac-sha-256-96" {
           description "HMAC-SHA-256-96 authentication algorithm (non-RFC compliant)";
         }
         enum "hmac-sha2-256" {
           description "HMAC-SHA2-256 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm with 16 octet ICV";
         }
         enum "aes-192-gcm" {
           description "AES-GCM 192-bit encryption algorithm with 16 octet ICV";
         }
         enum "aes-256-gcm" {
           description "AES-GCM 256-bit encryption algorithm with 16 octet ICV";
         }
       }
     }
     leaf lifetime-seconds {
       description "Lifetime, in seconds";
       units "seconds";
       type union {
         type string {
           pattern "<.*>|$.*";
         }
         type uint32 {
           range "180 .. 86400";
         }
       }
     }
   }
   grouping ipsec-sa {
     leaf name {
       description "Name of IPSec security association";
       type string {
         length "1 .. 32";
       }
     }
     uses apply-advanced;
     leaf description {
       description "Text description of security association";
       type string {
         length "1 .. 80";
       }
     }
     leaf mode {
       description "Define security association mode";
       default "tunnel";
       type enumeration {
         enum "transport" {
           description "Transport mode";
         }
         enum "tunnel" {
           description "Tunnel mode";
         }
       }
     }
     choice sa_choice {
       case case_1 {
         container manual {
           description "Define a manual security association";
           uses apply-advanced;
           list direction {
             key name;
             ordered-by user;
             description "Define the direction of the security association";
             leaf name {
               type enumeration {
                 enum "inbound" {
                   description "Inbound security association";
                 }
                 enum "outbound" {
                   description "Outbound security association";
                 }
                 enum "bidirectional" {
                   description "Bidirectional security association";
                 }
               }
             }
             uses apply-advanced;
             leaf protocol {
               description "Define an IPSec protocol for the security association";
               type enumeration {
                 enum "ah" {
                   description "Authentication header";
                 }
                 enum "esp" {
                   description "Encapsulated Security Payload header";
                 }
                 enum "bundle" {
                   description "Bundle (AH authentication plus ESP encryption)";
                 }
               }
               mandatory true;
             }
             leaf spi {
               description "Define security parameter index";
               type union {
                 type string {
                   pattern "<.*>|$.*";
                 }
                 type uint32 {
                   range "256 .. 16639";
                 }
               }
               mandatory true;
             }
             leaf auxiliary-spi {
               description "ESP security parameter index for IPSec SA bundle";
               type union {
                 type string {
                   pattern "<.*>|$.*";
                 }
                 type uint32 {
                   range "256 .. 16639";
                 }
               }
             }
             container authentication {
               description "Define authentication parameters";
               uses apply-advanced;
               leaf algorithm {
                 description "Define authentication algorithm";
                 type enumeration {
                   enum "hmac-md5-96" {
                     description "HMAC-MD5-96 authentication algorithm";
                   }
                   enum "hmac-sha1-96" {
                     description "HMAC-SHA1-96 authentication algorithm";
                   }
                   enum "hmac-sha2-256" {
                     description "HMAC-SHA2-256 authentication algorithm";
                   }
                   enum "hmac-sha-256-128" {
                     description "HMAC-SHA-256-128 authentication algorithm";
                   }
                 }
                 mandatory true;
               }
               container key {
                 description "Define an authentication key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                       }
                     }
                   }
                 }
               }
             }
             container encryption {
               description "Define encryption parameters";
               uses apply-advanced;
               leaf algorithm {
                 description "Define encryption algorithm";
                 type enumeration {
                   enum "des-cbc" {
                     description "DES-CBC encryption algorithm";
                   }
                   enum "3des-cbc" {
                     description "3DES-CBC encryption algorithm";
                   }
                   enum "aes-128-cbc" {
                     description "AES-CBC 128-bit encryption algorithm";
                   }
                   enum "aes-192-cbc" {
                     description "AES-CBC 192-bit encryption algorithm";
                   }
                   enum "aes-256-cbc" {
                     description "AES-CBC 256-bit encryption algorithm";
                   }
                 }
                 mandatory true;
               }
               container key {
                 description "Define an encryption key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                       }
                     }
                   }
                 }
               }
             }
           }
         }
       }
       case case_2 {
         container dynamic {
           description "Define a dynamic security association";
           uses apply-advanced;
           leaf replay-window-size {
             description "Define replay protection window size";
             type enumeration {
               enum "32" {
                 description "32-packet window size";
               }
               enum "64" {
                 description "64-packet window size";
               }
             }
           }
           leaf ipsec-policy {
             description "Name of the IPSec policy";
             type string {
               length "1 .. 32";
             }
           }
         }
       }
     }
   }
   grouping ipsec-traceoptions {
     description "Data-plane IPSec tracing options";
     uses apply-advanced;
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-trusted-channel-sa {
     uses apply-advanced;
     leaf description {
       description "Text description of trusted channel security association";
       type string {
         length "1 .. 80";
       }
     }
     container manual {
       description "Define a manual security association";
       uses apply-advanced;
       list direction {
         key name;
         ordered-by user;
         description "Define the direction of the security association";
         leaf name {
           type enumeration {
             enum "inbound" {
               description "Inbound security association";
             }
             enum "outbound" {
               description "Outbound security association";
             }
             enum "bidirectional" {
               description "Bidirectional security association";
             }
           }
         }
         uses apply-advanced;
         leaf protocol {
           description "Define an IPSec protocol for the security association";
           type enumeration {
             enum "ah" {
               description "Authentication header";
             }
             enum "esp" {
               description "Encapsulated Security Payload header";
             }
             enum "bundle" {
               description "Bundle (AH authentication plus ESP encryption)";
             }
           }
           mandatory true;
         }
         leaf spi {
           description "Define security parameter index";
           type union {
             type string {
               pattern "<.*>|$.*";
             }
             type uint32 {
               range "256 .. 16639";
             }
           }
           mandatory true;
         }
         leaf auxiliary-spi {
           description "ESP security parameter index for IPSec SA bundle";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
             mandatory true;
           }
           container key {
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
             mandatory true;
           }
           container key {
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                   }
                 }
               }
             }
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       type string {
         length "1 .. 32";
       }
     }
     uses apply-advanced;
     leaf bind-interface {
       description "Bind to tunnel interface (route-based VPN)";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container vpn-monitor {
       description "Monitor VPN liveliness";
       presence "enable vpn-monitor";
       uses ipsec-template-monitor;
     }
     choice negotiation {
       case case_1 {
         container manual {
           description "Define a manual security association";
           uses apply-advanced;
           leaf gateway {
             description "Define the IPSec peer";
             type jt:hostname;
           }
           leaf external-interface {
             description "External interface for the security association";
             type union {
               type jt:interface-unit;
               type string {
                 pattern "<.*>|$.*";
               }
             }
             mandatory true;
           }
           leaf protocol {
             description "Define an IPSec protocol for the security association";
             type enumeration {
               enum "ah" {
                 description "Authentication header";
               }
               enum "esp" {
                 description "Encapsulated Security Payload header";
               }
             }
             mandatory true;
           }
           leaf spi {
             description "Define security parameter index";
             type union {
               type string {
                 pattern "<.*>|$.*";
               }
               type uint32 {
                 range "256 .. 16639";
               }
             }
             mandatory true;
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
               }
               mandatory true;
             }
             container key {
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
               }
               mandatory true;
             }
             container key {
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
         }
       }
       case case_2 {
         container ike {
           description "Define an IKE-keyed IPSec vpn";
           uses apply-advanced;
           leaf gateway {
             description "Name of remote gateway";
             type string {
               length "1 .. 32";
             }
             mandatory true;
           }
           leaf idle-time {
             description "Idle time to delete SA";
             units "seconds";
             type union {
               type string {
                 pattern "<.*>|$.*";
               }
               type uint32 {
                 range "60 .. 999999";
               }
             }
           }
           leaf no-anti-replay {
             description "Disable the anti-replay check";
             type empty;
           }
           container proxy-identity {
             description "IPSec proxy-id to use in IKE negotiations";
             presence "enable proxy-identity";
             uses ipsec-template-proxy-id;
           }
           leaf ipsec-policy {
             description "Name of the IPSec policy";
             type string {
               length "1 .. 32";
             }
             mandatory true;
           }
           leaf install-interval {
             description "Delay installation of rekeyed outbound SAs on initiator";
             default "1";
             units "seconds";
             type union {
               type string {
                 pattern "<.*>|$.*";
               }
               type uint32 {
                 range "0 .. 10";
               }
             }
           }
         }
       }
     }
     leaf establish-tunnels {
       description "Define the criteria to establish tunnels";
       default "on-traffic";
       type enumeration {
         enum "immediately" {
           description "Establish tunnels immediately";
         }
         enum "on-traffic" {
           description "Establish tunnels on traffic";
         }
       }
     }
   }
   grouping ipsec-template-monitor {
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-macsec {
     uses apply-advanced;
     container traceoptions {
       description "Tracing options for debugging protocol operation";
       presence "enable traceoptions";
       uses macsec-trace-options;
     }
     leaf sak-kek {
       description "Key Encryption Key for SAK in hexadecimal format";
       type string {
         length "1 .. 64";
       }
     }
     list connectivity-association {
       key name;
       ordered-by user;
       description "Configure connectivity association properties";
       leaf name {
         description "Connectivity association name";
         type string {
           length "1 .. 32";
         }
       }
       uses apply-advanced;
       leaf security-mode {
         description "Connectivity association mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
         mandatory true;
       }
       leaf sak-hash-128 {
         description "Configure to generate 128bit SAK hash to program HW";
         type empty;
       }
       list secure-channel {
         key name;
         ordered-by user;
         description "Configure secure channel properties";
         leaf name {
           description "Secure channel name";
           type string;
         }
         uses apply-advanced;
         container id {
           description "Secure channel identifier";
           uses apply-advanced;
           leaf mac-address {
             description "MAC addresses";
             type jt:mac-addr;
             mandatory true;
           }
           leaf port-id {
             description "Port identifier";
             type union {
               type string {
                 pattern "<.*>|$.*";
               }
               type uint32 {
                 range "1 .. 65535";
               }
             }
             mandatory true;
           }
         }
         leaf direction {
           description "Secure channel direction";
           type enumeration {
             enum "inbound" {
             }
             enum "outbound" {
             }
           }
           mandatory true;
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             type union {
               type string {
                 pattern "<.*>|$.*";
               }
               type uint32 {
                 range "0 .. 3";
               }
             }
           }
           uses apply-advanced;
           leaf key {
             description "Security association key in hexadecimal format of length 32";
             type string {
               length 32;
             }
           }
         }
       }
       container mka {
         presence "enable mka";
         description "Configure MAC Security Key Agreement protocol properties";
         uses apply-advanced;
         leaf transmit-interval {
           description "Configure MKA periodic transmit interval";
           default "2000";
           units "milliseconds";
           type union {
             type string {
               pattern "<.*>|$.*";
             }
             type uint32 {
               range "2000 .. 6000";
             }
           }
         }
         leaf sak-rekey-interval {
           description "Configure SAK rekeying interval";
           units "seconds";
           type union {
             type string {
               pattern "<.*>|$.*";
             }
             type uint32 {
               range "60 .. 86400";
             }
           }
         }
         leaf bounded-delay {
           description "Configure Bounded Hello Time";
           type empty;
         }
         leaf suspend-on-request {
           description "Configure on key-server to accept suspend-on-request during gres or issu";
           type empty;
         }
         leaf key-server-priority {
           description "Configure MKA key server priority";
           default "16";
           type union {
             type string {
               pattern "<.*>|$.*";
             }
             type uint32 {
               range "0 .. 255";
             }
           }
         }
         leaf should-secure {
           description "Allows non-secure traffic if MKA session fails";
           type empty;
         }
         leaf eapol-address {
           description "Configure EAPOL destination group address";
           default "pae";
           type string;
         }
         leaf disable-icv-indicator {
           description "Configure to disable ICV indicator TLV on MKA protocol";
           type empty;
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
           mandatory true;
         }
       }
       leaf no-encryption {
         description "Disable encryption";
         type empty;
       }
       leaf disable-preceding-key {
         description "Disable CA preceding key duing key switch-over";
         type empty;
       }
       leaf offset {
         description "Confidentiality offset";
         default "0";
         type enumeration {
           enum "0" {
             description "Confidentiality provided for all octets of data";
           }
           enum "30" {
             description "Confidentiality not provided for initial 30 octets of data";
           }
           enum "50" {
             description "Confidentiality not provided for initial 50 octets of data";
           }
         }
       }
       leaf include-sci {
         description "Include secure channel identifier in MAC Security PDU";
         type empty;
       }
       container pre-shared-key {
         presence "enable pre-shared-key";
         description "Configure pre-shared connectivity association key";
         uses apply-advanced;
         leaf ckn {
           description "Connectivity association key name in hexadecimal format";
           type string {
             length "2 .. 64";
           }
           mandatory true;
         }
         leaf cak {
           description "Connectivity association key in hexadecimal format";
           type string {
             length "1 .. 64";
           }
           mandatory true;
         }
       }
       container fallback-key {
         presence "enable fallback-key";
         description "Configure fallback key for connectivity association";
         uses apply-advanced;
         leaf ckn {
           description "Connectivity association fallback key name in hexadecimal format";
           type string {
             length "2 .. 64";
           }
           mandatory true;
         }
         leaf cak {
           description "Connectivity association fallback key secret in hexadecimal format";
           type string {
             length "1 .. 64";
           }
           mandatory true;
         }
       }
       leaf pre-shared-key-chain {
         description "Pre-shared key chain name for connectivity association";
         type string {
         }
       }
       list exclude-protocol {
         key name;
         ordered-by user;
         description "Configure protocols to exclude from MAC Security";
         leaf name {
           type enumeration {
             enum "cdp" {
               description "Cisco Discovery Protocol";
             }
             enum "lldp" {
               description "Link Level Discovery Protocol";
             }
             enum "lacp" {
               description "Link Aggregation Control Protocol";
             }
           }
         }
       }
     }
     leaf centralized {
       description "MACsec in centralized mode";
       type empty;
     }
     leaf enable-auto-mtu-update {
       description "Auto-update MTU on MACsec interfaces, may cause link flap";
       type empty;
     }
     list interfaces {
       key name;
       description "Interfaces on which macsec configuration is applied";
       leaf name {
         type union {
           type jt:interface-device;
           type string {
             pattern "<.*>|$.*";
           }
         }
       }
       uses apply-advanced;
       leaf connectivity-association {
         description "Connectivity association name";
         type string;
       }
       leaf pre-shared-key-chain {
         description "Pre-shared key chain name for connectivity association";
         type string {
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
           mandatory true;
         }
       }
       container traceoptions {
         description "Tracing options of MKA protocol";
         presence "enable traceoptions";
         uses mka-trace-options;
       }
     }
   }
   grouping macsec-trace-options {
     description "Trace options for MACSec Protocol";
     uses apply-advanced;
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "config" {
             description "Trace configuration messages";
           }
           enum "debug" {
             description "Trace debug messages";
           }
           enum "telemetry" {
             description "Trace telemetry messages";
           }
           enum "normal" {
             description "Trace normal messages";
           }
           enum "all" {
             description "Trace all";
           }
         }
       }
     }
   }
   grouping mka-trace-options {
     description "Trace options for MKA protocol";
     uses apply-advanced;
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-model-access {
     description "Security access configuration";
     leaf name {
       description "SNMPv3 VACM security model";
       type enumeration {
         enum "any" {
           description "Any security model";
         }
         enum "usm" {
           description "User-based security model";
         }
         enum "v1" {
           description "SNMPv1 model";
         }
         enum "v2c" {
           description "SNMPv2c model";
         }
       }
     }
     uses apply-advanced;
     list security-level {
       key name;
       ordered-by user;
       description "Security level access configuration";
       leaf name {
         description "SNMPv3 VACM security level";
         type enumeration {
           enum "none" {
             description "None (noAuthNoPriv)";
           }
           enum "authentication" {
             description "Authentication (authNoPriv)";
           }
           enum "privacy" {
             description "Privacy and authentication (authPriv)";
           }
         }
       }
       uses apply-advanced;
       leaf context-match {
         description "Type of match to perform on context-prefix";
         default "exact";
         type enumeration {
           enum "exact" {
             description "Exact match of prefix and context name";
           }
           enum "prefix" {
             description "Only match the context prefix";
           }
         }
       }
       leaf read-view {
         description "View used for read access";
         type string {
         }
       }
       leaf write-view {
         description "View used for write access";
         type string {
         }
       }
       leaf notify-view {
         description "View used to notifications";
         type string {
         }
       }
     }
   }
   grouping security-pki {
     uses apply-advanced;
     list ca-profile {
       key name;
       ordered-by user;
       description "Certificate authority profile configuration";
       leaf name {
         description "Name of certificate authority profile";
         type string {
           length "1 .. 32";
         }
       }
       uses apply-advanced;
       leaf ca-identity {
         description "Certificate authority identifier";
         type string;
         mandatory true;
       }
       leaf source-address {
         description "Use specified address as source address";
         type jt:ipaddr;
       }
       leaf proxy-profile {
         description "Use specified proxy server";
         type string;
       }
       leaf routing-instance {
         description "Use specified routing instance";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             leaf on-download-failure {
               description "Check revocation status with existing CRL file if present, otherwise skip. This feature must be enabled for manual CRL download.";
               type empty;
             }
           }
           list url {
             key name;
             ordered-by user;
             leaf name {
               description "URL of CRL distribution point for certificate authority";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         type string {
           length "1 .. 63";
         }
       }
       uses apply-advanced;
       leaf-list ca-profiles {
         ordered-by user;
         description "Name of the CA profiles (maximum 20)";
         type string {
           length "1 .. 63";
         }
         max-elements 20;
       }
     }
     list ca-profile-group {
       key name;
       ordered-by user;
       description "Certificate Authority profile group configuration";
       leaf name {
         description "Name of CA group";
         type string {
           length "1 .. 32";
         }
       }
       uses apply-advanced;
       leaf cert-base-count {
         description "Index of the latest add CA certificate in the group.";
         type union {
           type string {
             pattern "<.*>|$.*";
           }
           type uint32 {
             range "0 .. 2048";
           }
         }
       }
     }
     container default-trusted-ca-certs {
       presence "enable default-trusted-ca-certs";
       description "Default trusted CA certs automatic download configuration";
       uses apply-advanced;
       container automatic-download {
         presence "enable automatic-download";
         description "Automatic download of CA certs configuration";
         uses apply-advanced;
         leaf deactivate {
           description "Disable default ca cert automatic download";
           type empty;
         }
         container interval {
           presence "enable interval";
           description "Configure default trusted CA certs automatic download interval";
           uses apply-advanced;
           choice interval-options {
             case case_1 {
               leaf hours {
                 units "hours";
                 type union {
                   type string {
                     pattern "<.*>|$.*";
                   }
                   type uint32 {
                     range "0 .. 336";
                   }
                 }
               }
             }
           }
         }
         leaf url {
           description "HTTP URL for OCSP access location";
           type string {
             length "1 .. 500";
           }
         }
         leaf routing-instance {
           description "Routing instance for trusted CA cert download";
           type string;
         }
       }
     }
     container trap {
       presence "enable trap";
       description "Trap options for PKI certificates";
       uses apply-advanced;
       list certificate-id {
         key name;
         ordered-by user;
         description "Local certificate identifier";
         leaf name {
           description "Local cert id";
           type string;
         }
         uses apply-advanced;
         leaf days {
           description "Number of days to generate trap (default 60)";
           default "60";
           type union {
             type string {
               pattern "<.*>|$.*";
             }
             type uint32 {
               range "1 .. 100";
             }
           }
         }
       }
       list ca-identity {
         key name;
         ordered-by user;
         description "CA identity";
         leaf name {
           description "CA profile";
           type string;
         }
         uses apply-advanced;
         leaf days {
           description "Number of days to generate trap (default 60)";
           default "60";
           type union {
             type string {
               pattern "<.*>|$.*";
             }
             type uint32 {
               range "1 .. 100";
             }
           }
         }
       }
       container all-certificates {
         presence "enable all-certificates";
         description "Trap config for all certificates";
         uses apply-advanced;
         leaf days {
           description "Number of days to generate trap (default 60)";
           default "60";
           type union {
             type string {
               pattern "<.*>|$.*";
             }
             type uint32 {
               range "1 .. 100";
             }
           }
         }
       }
     }
     container auto-re-enrollment {
       description "Auto re-enroll of certificate";
       uses apply-advanced;
       container acme {
         presence "enable acme";
         description "ACME auto re-enrollment configuration";
         uses apply-advanced;
         list certificate-id {
           key name;
           ordered-by user;
           description "Acme auto re-enrollment configuration for certificate-id";
           leaf name {
             description "Certificate identifier that needs auto re-enrollment";
             type string {
             }
             mandatory true;
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf acme-key-id {
             description "Acme account key identifier";
             type string {
             }
             mandatory true;
           }
           leaf ca-profile-name {
             description "Name of certificate authority profile";
             type string {
             }
             mandatory true;
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             type string {
             }
             mandatory true;
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             type string {
             }
             mandatory true;
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             type string {
             }
             mandatory true;
           }
           uses apply-advanced;
           container re-enroll-time {
             presence "enable re-enroll-time";
             description "Re-enroll time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             type string {
             }
             mandatory true;
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         status deprecated;
         leaf name {
           description "Certificate identifier that needs auto re-enrollment";
           type string {
           }
           mandatory true;
         }
         uses apply-advanced;
         container re-enroll-time {
           presence "enable re-enroll-time";
           description "Re-enroll trigger time in days <value> | hours <value> | percentage <value>";
           uses apply-advanced;
           choice re-enroll-time-options {
             case case_1 {
               leaf days {
                 description "Re-enrollment trigger time in days ahead of expiration";
                 type union {
                   type uint32;
                   type string {
                     pattern "<.*>|$.*";
                   }
                 }
               }
             }
             case case_2 {
               leaf hours {
                 description "Re-enrollment trigger time in hours ahead of expiration";
                 type union {
                   type uint32;
                   type string {
                     pattern "<.*>|$.*";
                   }
                 }
               }
             }
             case case_3 {
               leaf percent {
                 description "Re-enrollment trigger time before expiration as percentage";
                 type union {
                   type string {
                     pattern "<.*>|$.*";
                   }
                   type uint32 {
                     range "1 .. 99";
                   }
                 }
               }
             }
           }
         }
         leaf ca-profile-name {
           description "Name of certificate authority profile";
           type string {
           }
           mandatory true;
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
       }
     }
     container traceoptions {
       description "PKI trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "certificate-verification" {
               description "PKI certificate verification tracing";
             }
             enum "online-crl-check" {
               description "PKI online crl tracing";
             }
             enum "enrollment" {
               description "PKI certificate enrollment tracing";
             }
             enum "acme-enrollment" {
               description "PKI acme based certificate enrollment tracing";
             }
             enum "all" {
               description "Trace with all flags enabled";
             }
           }
         }
       }
     }
     container acme-account-key {
       description "ACME account key";
       uses apply-advanced;
       list acme-key-id {
         key name;
         ordered-by user;
         description "ACME account key identifier";
         leaf name {
           description "ACME key identifier which is used as account key";
           type string;
         }
         uses apply-advanced;
       }
     }
   }
   grouping security-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     list flag {
       key name;
       ordered-by user;
       description "Tracing parameters for IKE";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
   }
   grouping server-active-leasequery-type {
     description "Allow active leasequery";
     uses apply-advanced;
     leaf timeout {
       description "Read/write timeout in seconds";
       default "120";
       units "seconds";
       type union {
         type string {
           pattern "<.*>|$.*";
         }
         type uint32 {
           range "10 .. 3600";
         }
       }
     }
     leaf idle-timeout {
       description "Idle-timeout in seconds";
       default "60";
       units "seconds";
       type union {
         type string {
           pattern "<.*>|$.*";
         }
         type uint32 {
           range "10 .. 3600";
         }
       }
     }
   }
   grouping server-bulk-leasequery-type {
     description "Allow bulk leasequery";
     uses apply-advanced;
     leaf max-connections {
       description "Max TCP connections allowed at a time";
       default "3";
       type union {
         type string {
           pattern "<.*>|$.*";
         }
         type uint32 {
           range "1 .. 10";
         }
       }
     }
     leaf timeout {
       description "Timeout for blocked connection";
       default "120";
       units "seconds";
       type union {
         type string {
           pattern "<.*>|$.*";
         }
         type uint32 {
           range "1 .. 1000";
         }
       }
     }
     leaf max-empty-replies {
       description "Maximum number of empty replies for a connection";
       default "5";
       units "seconds";
       type union {
         type string {
           pattern "<.*>|$.*";
         }
         type uint32 {
           range "1 .. 100";
         }
       }
     }
     leaf restricted-requestor {
       description "Allow bulk leasequery only from restricted requestors";
       type empty;
     }
   }
   grouping server-group-type {
     uses apply-advanced;
     list server-group {
       key name;
       description "One or more server groups";
       leaf name {
         description "Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping server-leasequery-type {
     description "Allow leasequery";
     uses apply-advanced;
     leaf restricted-requestor {
       description "Allow leasequery only from restricted requestors";
       type empty;
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping server-v6-option-ascii-hex {
     uses apply-advanced;
     list ascii {
       key name;
       description "ASCII string";
       leaf name {
         description "ASCII string";
         type string {
           length "1 .. 256";
         }
       }
       uses apply-advanced;
     }
     list hexadecimal {
       key name;
       description "Hexadecimal string";
       leaf name {
         description "Hexadecimal string";
         type string {
           length "1 .. 512";
         }
       }
       uses apply-advanced;
     }
   }
   grouping service_device_pool_object {
     leaf name {
       description "Service device pool name";
       type string {
         length "1 .. 63";
       }
     }
     uses apply-advanced;
     list interface {
       key name;
       ordered-by user;
       description "Service device name";
       leaf name {
         type string;
         mandatory true;
       }
       uses apply-advanced;
     }
   }
   grouping service_interface_pool_object {
     leaf name {
       description "Service interface pool name";
       type string {
         length "1 .. 63";
       }
     }
     uses apply-advanced;
     list interface {
       key name;
       ordered-by user;
       description "Service interface name";
       leaf name {
         type union {
           type jt:interface-unit;
           type string {
             pattern "<.*>|$.*";
           }
         }
         mandatory true;
       }
       uses apply-advanced;
     }
   }
   grouping si-ip-address-list-object {
     leaf name {
       description "Name of ip-address list";
       type string {
         length "1 .. 64";
       }
     }
     uses apply-advanced;
     leaf-list ipv4 {
       ordered-by user;
       description "List of ipv4 addresses";
       type jt:ipv4addr;
     }
     leaf-list ipv6 {
       ordered-by user;
       description "List of ipv6 addresses";
       type jt:ipv6addr;
     }
   }
   grouping smpl-analyzer-type {
     leaf name {
       description "Analyzer name";
       type string {
         length "1 .. 63";
       }
     }
     uses apply-advanced;
     container input {
       description "Ports and VLANs to monitor";
       uses smpl-analyzer-input-type;
     }
     container output {
       description "Outgoing port or VLAN for mirrored packets";
       uses smpl-analyzer-output-type;
     }
   }
   grouping smpl-analyzer-input-type {
     uses apply-advanced;
     container ingress {
       description "Ports and VLANs to monitor incoming traffic";
       uses smpl-analyzer-ingress-type;
     }
     container egress {
       description "Ports and VLANs to monitor outgoing traffic";
       uses smpl-analyzer-egress-type;
     }
   }
   grouping smpl-analyzer-egress-type {
     uses apply-advanced;
     list interface {
       key name;
       ordered-by user;
       description "Port to monitor outgoing traffic";
       uses analyzer-egress-interface-type;
     }
     list routing-instance {
       key name;
       description "Routing instances";
       uses analyzer-egress-routing-instance-type;
     }
     list vlan {
       key name;
       ordered-by user;
       description "VLAN to monitor outgoing traffic";
       uses analyzer-egress-vlan-type;
     }
   }
   grouping analyzer-egress-interface-type {
     leaf name {
       description "Logical interface name";
       type string;
     }
     uses apply-advanced;
   }
   grouping analyzer-egress-routing-instance-type {
     leaf name {
       description "Routing instance name";
       type string {
       }
     }
     uses apply-advanced;
     list vlan {
       key name;
       ordered-by user;
       description "VLAN to monitor outgoing traffic";
       uses analyzer-egress-vlan-type;
     }
   }
   grouping analyzer-egress-vlan-type {
     leaf name {
       description "VLAN name, VLAN id or VLAN range string";
       type string;
     }
     uses apply-advanced;
   }
   grouping smpl-analyzer-ingress-type {
     uses apply-advanced;
     list interface {
       key name;
       ordered-by user;
       description "Port to monitor incoming traffic";
       uses analyzer-ingress-interface-type;
     }
     list routing-instance {
       key name;
       description "Routing instances";
       uses analyzer-ingress-routing-instance-type;
     }
     list vlan {
       key name;
       ordered-by user;
       description "VLAN to monitor incoming traffic";
       uses analyzer-ingress-vlan-type;
     }
   }
   grouping analyzer-ingress-interface-type {
     leaf name {
       description "Logical interface name";
       type string;
     }
     uses apply-advanced;
   }
   grouping analyzer-ingress-routing-instance-type {
     leaf name {
       description "Routing instance name";
       type string {
       }
     }
     uses apply-advanced;
     list vlan {
       key name;
       ordered-by user;
       description "VLAN to monitor incoming traffic";
       uses analyzer-ingress-vlan-type;
     }
   }
   grouping analyzer-ingress-vlan-type {
     leaf name {
       description "VLAN name, VLAN id or VLAN range string";
       type string;
     }
     uses apply-advanced;
   }
   grouping smpl-analyzer-output-type {
     uses apply-advanced;
     choice interface_or_vlan {
       case case_1 {
         leaf interface {
           description "Outgoing port for mirrored packets";
           type union {
             type jt:interface-name;
             type string {
               pattern "<.*>|$.*";
             }
           }
         }
       }
       case case_2 {
         leaf ip-address {
           description "ERSPAN Destination IP Address";
           type jt:ipv4addr;
         }
       }
       case case_3 {
         leaf ipv6-address {
           description "ERSPAN Destination IPv6 Address";
           type jt:ipv6addr;
         }
       }
       case case_4 {
       }
       case case_5 {
         list routing-instance {
           key name;
           description "Routing instances";
           max-elements 1;
           uses output-routing-instance-type;
         }
       }
       case case_6 {
         list vlan {
           key name;
           description "Outgoing VLAN for mirrored packets";
           max-elements 1;
           uses pm-rspan-vlan;
         }
       }
       case case_7 {
       }
     }
   }
   grouping output-routing-instance-type {
     leaf name {
       description "Routing instance name";
       type string {
       }
     }
     uses apply-advanced;
     choice ipaddr_or_vlan {
       case case_1 {
         leaf ip-address {
           description "ERSPAN Destination IP Address";
           type jt:ipv4addr;
         }
       }
       case case_2 {
         leaf ipv6-address {
           description "ERSPAN Destination IPv6 Address";
           type jt:ipv6addr;
         }
       }
       case case_3 {
         list vlan {
           key name;
           description "Outgoing VLAN for mirrored packets";
           max-elements 1;
           uses pm-rspan-vlan;
         }
       }
       case case_4 {
       }
     }
   }
   grouping sonet_options_type {
     uses apply-advanced;
     leaf vtmapping {
       description "VT mapping mode";
       type enumeration {
         enum "klm" {
           description "KLM mode";
         }
         enum "itu-t" {
           description "ITU-T mode";
         }
       }
     }
     leaf fcs {
       description "Frame checksum";
       type enumeration {
         enum "32" {
           description "32-bit mode";
         }
         enum "16" {
           description "16-bit mode";
         }
       }
     }
     leaf path-trace {
       description "Path trace string";
       type string;
     }
     leaf loopback {
       description "Loopback mode";
       type enumeration {
         enum "local" {
           description "Local loopback";
         }
         enum "remote" {
           description "Remote loopback";
         }
       }
     }
     container trigger {
       description "Defect triggers";
       uses apply-advanced;
       container lol {
         description "LOL defect trigger";
         choice lol_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container pll {
         description "PLL defect trigger";
         choice pll_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container lof {
         description "LOF defect trigger";
         choice lof_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container los {
         description "LOS defect trigger";
         choice los_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container ais-l {
         description "AIS-L defect trigger";
         choice ais_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container rfi-l {
         description "RFI-L defect trigger";
         choice rfi_l_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container ber-sd {
         description "BER-SD defect trigger";
         uses apply-advanced;
         choice ber_sd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container ber-sf {
         description "BER-SF defect trigger";
         uses apply-advanced;
         choice ber_sf_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container ais-p {
         description "AIS-P defect trigger";
         choice ais_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container lop-p {
         description "LOP-P defect trigger";
         choice lop_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container rfi-p {
         description "RFI-P defect trigger";
         choice rfi_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container uneq-p {
         description "UNEQ-P defect trigger";
         choice uneq_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container plm-p {
         description "PLM-P defect trigger";
         choice plm_p_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container locd {
         description "LOCD defect trigger (ATM only)";
         choice locd_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
       container lcdp {
         description "LCD-P defect trigger (Ethernet WAN only)";
         choice lcdp_choices {
           case case_1 {
             leaf ignore {
               description "Ignore the defect";
               type empty;
             }
           }
           case case_2 {
             container hold-time {
               description "Delay before marking interface up or down for defect";
               leaf up {
                 description "Delay before marking interface up when defect is absent";
                 units "milliseconds";
                 type union {
                   type string {
                     pattern "<.*>|$.*";
                   }
                   type uint32 {
                     range "1 .. 65534";
                   }
                 }
                 mandatory true;
               }
               leaf down {
                 description "Delay before marking interface down when defect occurs";
                 units "milliseconds";
                 type union {
                   type string {
                     pattern "<.*>|$.*";
                   }
                   type uint32 {
                     range "1 .. 65534";
                   }
                 }
                 mandatory true;
               }
             }
           }
         }
       }
     }
     container aps {
       description "Automatic Protection Switching";
       uses aps_type;
     }
     choice payload_scrambler_choices {
       case case_1 {
         container payload-scrambler {
           presence "enable payload-scrambler";
           description "Enable payload scrambling";
           choice payload-choice {
           }
         }
       }
       case case_2 {
         leaf no-payload-scrambler {
           description "Do not enable payload scrambling";
           type empty;
         }
       }
     }
     choice z0-increment-choice {
       leaf z0-increment {
         description "Increment Z0 in SDH mode";
         type empty;
       }
       leaf no-z0-increment {
         description "Don't increment Z0 in SDH mode";
         type empty;
       }
     }
     choice loop-timing-choice {
       leaf loop-timing {
         description "Set loop timing for STM-1";
         type empty;
       }
       leaf no-loop-timing {
         description "Don't set loop timing for STM-1";
         type empty;
       }
     }
     container bytes {
       description "Set SONET header bytes";
       uses apply-advanced;
       leaf e1-quiet {
         description "E1-quiet value";
         type union {
           type string {
             pattern "<.*>|$.*";
           }
           type uint32 {
             range "0 .. 255";
           }
         }
       }
       leaf f1 {
         description "F1 user value";
         type union {
           type string {
             pattern "<.*>|$.*";
           }
           type uint32 {
             range "0 .. 255";
           }
         }
       }
       leaf f2 {
         description "F2 user value";
         type union {
           type string {
             pattern "<.*>|$.*";
           }
           type uint32 {
             range "0 .. 255";
           }
         }
       }
       leaf s1 {
         description "S1/Z1 value (stratum clock by convention)";
         type union {
           type string {
             pattern "<.*>|$.*";
           }
           type uint32 {
             range "0 .. 255";
           }
         }
       }
       leaf z3 {
         description "Z3 user value";
         type union {
           type string {
             pattern "<.*>|$.*";
           }
           type uint32 {
             range "0 .. 255";
           }
         }
       }
       leaf z4 {
         description "Z4 user value";
         type union {
           type string {
             pattern "<.*>|$.*";
           }
           type uint32 {
             range "0 .. 255";
           }
         }
       }
       leaf c2 {
         description "C2 user value";
         type union {
           type string {
             pattern "<.*>|$.*";
           }
           type uint32 {
             range "0 .. 255";
           }
         }
       }
     }
     leaf rfc-2615 {
       description "RFC 2615 compliance";
       type empty;
     }
     leaf aggregate {
       description "Join a SONET aggregate";
       type union {
         type jt:interface-device;
         type string {
           pattern "<.*>|$.*";
         }
       }
     }
     container mpls {
       description "MPLS options";
       uses mpls_ifd_options;
     }
   }
   grouping source-class-name-object {
     leaf name {
       description "Class name";
       type string;
     }
   }
   grouping source_address_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
         case case_8 {
           container effective-aigp {
             presence "enable effective-aigp";
             description "Track the effective AIGP metric (BGP only)";
             leaf metric_offset {
               description "Metric offset for MED";
               type union {
                 type int32;
                 type string {
                   pattern "<.*>|$.*";
                 }
               }
             }
           }
         }
         case case_9 {
           container minimum-effective-aigp {
             presence "enable minimum-effective-aigp";
             description "Track the minimum effective AIGP metric (BGP only)";
             leaf metric_offset {
               description "Metric offset for MED";
               type union {
                 type int32;
                 type string {
                   pattern "<.*>|$.*";
                 }
               }
             }
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container credibility {
       description "TED credibility value for entries from BGP-TE";
       uses apply-advanced;
       choice metric_action {
         case case_1 {
           leaf credibility {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       uses apply-advanced;
       list algorithm {
         key name;
         description "Set prefix segment attributes for strict/flex algorithm ";
         max-elements 15;
         leaf name {
           description "Set prefix segment for strict/flex algorithm";
           type union {
             type string {
               pattern "<.*>|$.*";
             }
             type uint32 {
               range "1 .. 255";
             }
           }
           mandatory true;
         }
         leaf index {
           description "Set prefix segment index id";
           type union {
             type string {
               pattern "<.*>|$.*";
             }
             type uint32 {
               range "0 .. 1048575";
             }
           }
           mandatory true;
         }
         leaf node-segment {
           description "Set node segment flag for this prefix segment";
           type empty;
         }
       }
       leaf index {
         description "Set prefix segment index id";
         type union {
           type string {
             pattern "<.*>|$.*";
           }
           type uint32 {
             range "0 .. 1048575";
           }
         }
       }
       leaf node-segment {
         description "Set node segment flag for default prefix segment";
         type empty;
       }
       leaf redistribute {
         description "Redistribute prefix-segment from route entry";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf fib-install-priority {
       description "Set Fib Instalation priority of a route";
       type enumeration {
         enum "high" {
           description "Set Fib install priority  to high";
         }
         enum "medium" {
           description "Set Fib install priority to medium ";
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container srv6 {
       description "Configure SID with 128 bit address";
       leaf sid {
         description "IPv6 Address";
         type jt:ipv6addr;
       }
       leaf locator {
         description "Name of locator";
         type string;
       }
       choice locator_type {
         case case_1 {
           leaf micro-dt4-sid {
             description "Micro SID type dt4";
             type empty;
           }
         }
         case case_2 {
           leaf micro-dt6-sid {
             description "Micro SID type dt6";
             type empty;
           }
         }
         case case_3 {
           leaf micro-dt46-sid {
             description "Micro SID type dt46";
             type empty;
           }
         }
         case case_4 {
           leaf end-dtm-sid {
             description "SID type dtm";
             type empty;
           }
         }
       }
     }
     container aigp-originate {
       presence "enable aigp-originate";
       description "Originate a BGP AIGP attribute";
       leaf effective-metric {
         description "Metric associated with non-BGP route";
         type empty;
       }
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf community-name {
         description "Name to identify a BGP community";
         type string;
       }
     }
     list inline-community {
       key "choice-ident choice-value inline-community-member";
       ordered-by user;
       description "Set BGP community properties associated with a route inline";
       leaf choice-ident {
         type enumeration {
           enum "equal-literal" {
           }
           enum "set" {
           }
           enum "plus-literal" {
           }
           enum "add" {
           }
           enum "minus-literal" {
           }
           enum "delete" {
           }
         }
       }
       leaf choice-value {
         type string;
       }
       leaf inline-community-member {
         description "Inline BGP community members";
         type string;
       }
     }
     list tunnel-attribute {
       key "choice-ident choice-value tunnel-attribute-name";
       ordered-by user;
       description "BGP tunnel attribute associated with a route";
       leaf choice-ident {
         type enumeration {
           enum "set" {
           }
           enum "remove" {
           }
         }
       }
       leaf choice-value {
         type string;
       }
       leaf tunnel-attribute-name {
         description "Name of a tunnel attribute , or 'all'";
         type string;
       }
     }
     container assisted-replication {
       presence "enable assisted-replication";
       description "Deterministic AR replicator knobs";
       uses apply-advanced;
       leaf-list replicator-ip {
         description "Set deterministic AR replicator ip for the flow";
         type jt:ipaddr;
         max-elements 1;
       }
       leaf strict {
         description "Do not use any other replicator";
         type empty;
       }
       leaf-list fallback-replicator-ip {
         description "Set Fallback replicator-ip";
         type jt:ipaddr;
         max-elements 1;
       }
     }
     leaf damping {
       description "Define BGP route flap damping parameters";
       type string;
     }
     container aggregate-bandwidth {
       presence "enable aggregate-bandwidth";
       description "Advertise aggregate outbound link bandwidth";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
       leaf divide-equal {
         description "Divide-equal";
         type empty;
       }
     }
     container aggregate-weight {
       presence "enable aggregate-weight";
       description "Advertise aggregate outbound count";
       uses apply-advanced;
       leaf multiplier {
         description "Adjust the aggregate-weight by multiplying it with a given value, default is 1";
         default "1";
         type union {
           type string {
             pattern "<.*>|$.*";
           }
           type uint16 {
             range "1 .. 32";
           }
         }
       }
     }
     container auto-link-bandwidth {
       presence "enable auto-link-bandwidth";
       description "Auto sense and attach link bandwidth community";
       uses apply-advanced;
       choice transitive-type {
         case case_1 {
           leaf transitive {
             description "Transitive flag for link bandwidth";
             type empty;
           }
         }
         case case_2 {
           leaf non-transitive {
             description "Non-Transitive flag for link bandwidth";
             type empty;
           }
         }
       }
     }
     leaf limit-bandwidth {
       description "Limit advertised aggregate outbound link bandwidth";
       type union {
         type uint64;
         type string {
           pattern "<.*>|$.*";
         }
       }
     }
     leaf no-entropy-label-capability {
       description "Don't advertise entropy label capability";
       type empty;
     }
     leaf as-path-prepend {
       description "Prepend AS numbers to an AS path (BGP only)";
       type string;
     }
     leaf as-path-replace {
       description "Replace sequence of AS numbers/'private' with local AS";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           container local-as {
             presence "enable local-as";
             description "Prepend local AS";
             leaf count {
               description "Repeat count";
               type union {
                 type string {
                   pattern "<.*>|$.*";
                 }
                 type uint32 {
                   range "1 .. 32";
                 }
               }
             }
           }
         }
         case case_3 {
           container asn {
             presence "enable asn";
             description "Prepend AS";
             uses apply-advanced;
             leaf as-value {
               description "AS value";
               type union {
                 type uint32;
                 type string {
                   pattern "<.*>|$.*";
                 }
               }
               mandatory true;
             }
             leaf count {
               description "Repeat count";
               type union {
                 type string {
                   pattern "<.*>|$.*";
                 }
                 type uint32 {
                   range "1 .. 32";
                 }
               }
             }
           }
         }
         case case_4 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
       leaf no-resolution {
         description "Don't resolve nexthop reachability";
         type empty;
       }
     }
     container install-nexthop {
       description "Choose the next hop to be used for forwarding";
       choice strict_type {
         case case_1 {
           leaf strict {
             description "Do not use any other available next hops";
             type empty;
           }
         }
         case case_2 {
           leaf strict-named-lsp {
             description "Do not use any other non-lsp next hops";
             type empty;
           }
         }
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
         case case_5 {
           leaf non-lsp-nexthop {
             description "Next-hop with non-lsp";
             type empty;
           }
         }
         case case_6 {
           leaf non-labelled-nexthop {
             description "Next-hop without tag";
             type empty;
           }
         }
         case case_7 {
           leaf overlay-vxlan-interfaces {
             description "Next-hop for vxlan interfaces";
             type empty;
           }
         }
         case case_8 {
           leaf macsec-interfaces {
             description "Next-hop for MACsec interfaces";
             type empty;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container fallback {
           description "Backup option";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
               case case_5 {
                 leaf non-lsp-nexthop {
                   description "Next-hop with non-lsp";
                   type empty;
                 }
               }
               case case_6 {
                 leaf non-labelled-nexthop {
                   description "Next-hop without tag";
                   type empty;
                 }
               }
               case case_7 {
                 leaf overlay-vxlan-interfaces {
                   description "Next-hop for vxlan interfaces";
                   type empty;
                 }
               }
               case case_8 {
                 leaf macsec-interfaces {
                   description "Next-hop for MACsec interfaces";
                   type empty;
                 }
               }
             }
           }
         }
       }
       container fallback {
         description "Backup option ";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
           case case_5 {
             leaf non-lsp-nexthop {
               description "Next-hop with non-lsp";
               type empty;
             }
           }
           case case_6 {
             leaf non-labelled-nexthop {
               description "Next-hop without tag";
               type empty;
             }
           }
           case case_7 {
             leaf overlay-vxlan-interfaces {
               description "Next-hop for vxlan interfaces";
               type empty;
             }
           }
           case case_8 {
             leaf macsec-interfaces {
               description "Next-hop for MACsec interfaces";
               type empty;
             }
           }
         }
         container except {
           description "Do not choose to install matching next hops";
           uses apply-advanced;
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
             case case_5 {
               leaf non-lsp-nexthop {
                 description "Next-hop with non-lsp";
                 type empty;
               }
             }
             case case_6 {
               leaf non-labelled-nexthop {
                 description "Next-hop without tag";
                 type empty;
               }
             }
             case case_7 {
               leaf overlay-vxlan-interfaces {
                 description "Next-hop for vxlan interfaces";
                 type empty;
               }
             }
             case case_8 {
               leaf macsec-interfaces {
                 description "Next-hop for MACsec interfaces";
                 type empty;
               }
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis deprecated, use per-flow instead";
             type empty;
           }
         }
         case case_2 {
           leaf per-flow {
             description "Load balance on a per-flow basis";
             type empty;
           }
         }
         case case_3 {
         }
         case case_4 {
         }
         case case_5 {
           leaf consistent-hash {
             description "Give a prefix consistent load-balancing";
             type empty;
           }
         }
         case case_6 {
         }
         case case_7 {
         }
         case case_8 {
         }
         case case_9 {
         }
         case case_10 {
         }
         case case_11 {
         }
       }
     }
     container advertise-locator {
       presence "enable advertise-locator";
       description "Advertise SRv6 Locator";
       uses apply-advanced;
       leaf internal {
         description "Advertise locator as Interal route";
         type empty;
       }
     }
     leaf set-down-bit {
       description "Set down bit";
       type empty;
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf tunnel-end-point-address {
       description "Set tunnel end-point address of tunnel";
       type jt:ipaddr;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf source-routing-path-template {
       description "Spring-te template to apply";
       type string {
       }
     }
     leaf label-allocation-fallback-reject {
       description "Suppress prefix export when label allocation fails";
       type empty;
     }
     leaf resolution-map {
       description "Set resolution map modes";
       type string;
     }
     leaf ignore-service-label {
       description "Ignore service labels";
       type empty;
     }
     container prefix-attribute-flags {
       presence "enable prefix-attribute-flags";
       description "Set ISIS prefix attribute flags sub TLV";
       uses apply-advanced;
       leaf node-segment-flag {
         description "Set node segment flag ";
         type empty;
       }
       leaf external-prefix-flag {
         description "Set external prefix flag ";
         type empty;
       }
       leaf anycast-flag {
         description "Set anycast flag ";
         type empty;
       }
       leaf entropy-label-capability-flag {
         description "Set entropy label capability flag ";
         type empty;
       }
     }
     container ipv4-source-router-id {
       presence "enable ipv4-source-router-id";
       description "Set IPv4 source router id in advertisement";
       uses apply-advanced;
       leaf router-id {
         description "Specify IPv4 address";
         type jt:ipaddr;
       }
     }
     container ipv6-source-router-id {
       presence "enable ipv6-source-router-id";
       description "Set IPv6 source router id in advertisement";
       uses apply-advanced;
       leaf router-id {
         description "Specify IPv6 address";
         type jt:ipv6addr;
       }
     }
     leaf request-long-lived-ack {
       description "Advertise route after forwarding is programmed";
       type empty;
     }
     leaf send-withdrawal-on-route-change {
       description "Withdraw route if change is not acked from forwarding";
       type empty;
     }
     container slice {
       description "Configure Policy Slice action";
       leaf slice-name {
         description "Slice Name";
         type string {
           length "1 .. 64";
         }
       }
     }
     leaf filter {
       description "Set firewall-filter name";
       type string {
       }
     }
     leaf strip-as-path {
       description "Remove the incoming BGP as-path and replace with local AS";
       type empty;
     }
     container request-acknowledgements {
       description "Set request acknowledgement";
       leaf nexthop-ack {
         description "Set nexthop acknowledgement ";
         type empty;
       }
       leaf route-ack {
         description "Set route acknowledgement ";
         type empty;
       }
     }
     container rib-export-strip {
       description "Strip attributes from a route";
       uses apply-advanced;
       leaf cluster-list {
         description "Strip cluster list from the route";
         type empty;
       }
     }
     list tunnel-termination-profile {
       key name;
       ordered-by user;
       description "Tunnel termination profiles associated with a route";
       leaf name {
         description "Name of a tunnel termination profile";
         type string;
       }
     }
     leaf flow-route-accounting {
       description "Enable accounting for flow routes";
       type empty;
     }
     leaf otc-local-role {
       description "Override local role without negotiation";
       type enumeration {
         enum "provider" {
           description "Provider role";
         }
         enum "peer" {
           description "Peer role";
         }
         enum "customer" {
           description "Customer role";
         }
         enum "route-server" {
           description "Route server role";
         }
         enum "route-server-client" {
           description "Route server client role";
         }
       }
     }
   }
   grouping spring-te-template-map {
     description "SPRING-TE template color map";
     leaf name {
       description "Name of SPRING-TE template";
       type string;
       mandatory true;
     }
     uses apply-advanced;
     choice colors {
       case case_1 {
         leaf-list color {
           description "Set of color list to be mapped to corresponding SPRING-TE template";
           type union {
             type uint32;
             type string {
               pattern "<.*>|$.*";
             }
           }
         }
       }
       case case_2 {
         leaf color-any {
           description "Map any color to corresponding SPRING-TE template";
           type empty;
         }
       }
     }
   }
   grouping springte_lsp_nh_obj {
     uses apply-advanced;
     leaf nexthop {
       description "SPRING-TE LSP to use to reach destination";
       type string {
         length "1 .. 128";
       }
       mandatory true;
     }
     container lsp-source {
       description "Source of tunnel creation";
       uses apply-advanced;
       choice lsp-src-choice {
         case case_1 {
           leaf pcep {
             description "Path computation element protocol";
             type empty;
           }
         }
         case case_2 {
           leaf static {
             description "Static configuration";
             type empty;
           }
         }
         case case_3 {
           leaf dtm {
             description "Dynamic tunnel module";
             type empty;
           }
         }
         case case_4 {
           leaf bgp {
             description "BGP SRTE";
             type empty;
           }
         }
       }
     }
   }
   grouping stp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping stp-trace-options {
     description "Trace options for Spanning Tree Protocol";
     uses apply-advanced;
     container file {
       description "Trace file options";
       leaf filename {
         description "Name of file in which to write trace information";
         type string {
           length "1 .. 1024";
         }
         mandatory true;
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "events" {
             description "Trace events to the protocol state machine";
           }
           enum "bpdu" {
             description "Trace BPDU reception and transmission";
           }
           enum "timers" {
             description "Trace protocol timers";
           }
           enum "port-information-state-machine" {
             description "Trace port information state machine";
           }
           enum "port-receive-state-machine" {
             description "Trace port receive state machine";
           }
           enum "port-role-select-state-machine" {
             description "Trace port role selection state machine";
           }
           enum "port-role-transit-state-machine" {
             description "Trace port role transit state machine";
           }
           enum "port-state-transit-state-machine" {
             description "Trace port state transit state machine";
           }
           enum "port-migration-state-machine" {
             description "Trace port migration state machine";
           }
           enum "port-transmit-state-machine" {
             description "Trace port transmit state machine";
           }
           enum "topology-change-state-machine" {
             description "Trace topology change state machine";
           }
           enum "bridge-detection-state-machine" {
             description "Trace Bridge detection state machine";
           }
           enum "state-machine-variables" {
             description "Trace when state machine variables change";
           }
           enum "ppmd" {
             description "Trace state and events for ppmd process";
           }
           enum "all-failures" {
             description "Trace all failure conditions";
           }
           enum "all" {
             description "Trace all";
           }
         }
       }
       leaf disable {
         description "Disable this trace flag";
         type empty;
       }
     }
   }
   grouping subscription-type {
     uses apply-advanced;
     leaf link-subscription {
       description "Link bandwidth percentage for RSVP reservation";
       default "100";
       type string;
     }
     leaf ct0 {
       description "Subscription percentage for traffic class 0";
       default "100";
       type string;
     }
     leaf ct1 {
       description "Subscription percentage for traffic class 1";
       default "100";
       type string;
     }
     leaf ct2 {
       description "Subscription percentage for traffic class 2";
       default "100";
       type string;
     }
     leaf ct3 {
       description "Subscription percentage for traffic class 3";
       default "100";
       type string;
     }
     list priority {
       key priority-value;
       ordered-by user;
       description "Subscription percentage for a specific priority";
       leaf priority-value {
         description "Priority for which subscription percent is being configured";
         type union {
           type string {
             pattern "<.*>|$.*";
           }
           type uint32 {
             range "0 .. 7";
           }
         }
       }
       uses apply-advanced;
       leaf percent {
         description "Subscription percent for the specific priority";
         type string;
       }
     }
   }
   grouping system-id-ip-map {
     leaf name {
       type jt:mac-unicast;
     }
     uses apply-advanced;
     leaf ip-address {
       description "Peer ID (IP Address)";
       type jt:ipv4prefix;
     }
   }
   grouping tunnel_end_point {
     description "Define a tunnel end point";
     leaf name {
       description "Tunnel end-point identifier (ASCII string)";
       type string {
       }
     }
     uses apply-advanced;
     choice l3-protocol {
       case case_1 {
         container ipv6 {
           presence "enable ipv6";
           description "Enter an IPv6 tunnel";
           uses apply-advanced;
           leaf source-address {
             description "Tunnel source address";
             type jt:ipv6addr;
           }
           leaf destination-address {
             description "Tunnel destination address";
             type jt:ipv6prefix;
           }
         }
       }
       case case_2 {
         container ipv4 {
           presence "enable ipv4";
           description "Enter an IPv4 tunnel";
           uses apply-advanced;
           leaf source-address {
             description "Tunnel source address";
             type jt:ipv4addr;
             mandatory true;
           }
           leaf destination-address {
             description "Tunnel destination address";
             type jt:ipv4prefix;
             mandatory true;
           }
         }
       }
     }
     choice tunnel-protocol {
       case case_1 {
         container gre {
           presence "enable gre";
           description "Tunnel is GRE";
           uses apply-advanced;
           leaf key {
             description "Key for authentication";
             type union {
               type uint32;
               type string {
                 pattern "<.*>|$.*";
               }
             }
           }
         }
       }
       case case_2 {
         container gre-in-udp {
           presence "enable gre-in-udp";
           description "Tunnel is GRE-in-UDP";
           uses apply-advanced;
           leaf source-port {
             description "UDP source port";
             type union {
               type string {
                 pattern "<.*>|$.*";
               }
               type uint32 {
                 range "0 .. 65535";
               }
             }
             mandatory true;
           }
           leaf destination-port {
             description "UDP destination port";
             type union {
               type string {
                 pattern "<.*>|$.*";
               }
               type uint32 {
                 range "0 .. 65535";
               }
             }
             mandatory true;
           }
           leaf key {
             description "GRE key for authentication";
             type union {
               type uint32;
               type string {
                 pattern "<.*>|$.*";
               }
             }
           }
         }
       }
     }
   }
   grouping ufd-group-type {
     description "Uplink failure detection group type";
     leaf name {
       description "Uplink failure detection group name";
       type string {
         length "2 .. 64";
       }
     }
     uses apply-advanced;
     list link-to-monitor {
       key name;
       ordered-by user;
       description "Uplinks to be monitored";
       leaf name {
         description "Interface to be monitored";
         type union {
           type jt:interface-unit;
           type string {
             pattern "<.*>|$.*";
           }
         }
       }
       uses apply-advanced;
     }
     list link-to-disable {
       key name;
       ordered-by user;
       description "Downlinks to disable";
       leaf name {
         description "Interface to disable";
         type union {
           type jt:interface-unit;
           type string {
             pattern "<.*>|$.*";
           }
         }
       }
       uses apply-advanced;
     }
     leaf debounce-interval {
       description "Delay before bring up of the link-to-disable port";
       units "seconds";
       type union {
         type string {
           pattern "<.*>|$.*";
         }
         type uint32 {
           range "5 .. 300";
         }
       }
     }
   }
   grouping upgrade-group-fpcs {
     description "Upgrade group fpcs";
     leaf name {
       description "Member identifier";
       type union {
         type string {
           pattern "<.*>|$.*";
         }
         type int32;
       }
     }
     uses apply-advanced;
     leaf-list fpcs {
       description "FPCs to be upgraded as a group in this member";
       type union {
         type string {
           pattern "<.*>|$.*";
         }
         type uint32;
       }
     }
   }
   grouping urlf-profile-object {
     leaf name {
       description "Name of profile";
       type string {
         length "1 .. 64";
       }
     }
     uses apply-advanced;
     leaf feed-name {
       description "Name of feed";
       type string {
         length "1 .. 64";
       }
     }
     leaf url-filter-database {
       description "Full path of the file";
       type string {
         length "1 .. 1024";
       }
     }
     leaf global-dns-filter-stats-log-timer {
       description "Global DNS filtering statistics log timer in minutes";
       default "5";
       units "minutes";
       type union {
         type string {
           pattern "<.*>|$.*";
         }
         type uint32 {
           range "0 .. 60";
         }
       }
     }
     container security-intelligence-policy {
       presence "enable security-intelligence-policy";
       description "Use the database supplied by security intelligence for blacklisted traffic.";
       uses apply-advanced;
       leaf file-type {
         type enumeration {
           enum "txt" {
             description "Policy DB is a text file";
           }
           enum "json" {
             description "Policy DB is in json format";
           }
         }
         mandatory true;
       }
       container whitelist {
         presence "enable whitelist";
         description "Specify ip-addresses to be whitelisted";
         uses apply-advanced;
         choice address-list {
           case case_1 {
             leaf ip-address-list {
               description "Ip address list";
               type string {
                 length "1 .. 63";
               }
             }
           }
           case case_2 {
             leaf filename {
               description "Full path of file containing whitelist ip-addresses";
               type string {
                 length "1 .. 1024";
               }
             }
           }
         }
       }
       container blacklist {
         presence "enable blacklist";
         description "Specify ip-addresses to be blacklisted";
         uses apply-advanced;
         choice address-list {
           case case_1 {
             leaf ip-address-list {
               description "Ip address list";
               type string {
                 length "1 .. 63";
               }
             }
           }
           case case_2 {
             leaf filename {
               description "Full path of file containing blacklist ip-addresses";
               type string {
                 length "1 .. 1024";
               }
             }
           }
         }
       }
       list threat-level {
         key name;
         ordered-by user;
         description "Define a URL filtering threat level";
         max-elements 10;
         uses threat-level-object;
       }
       container geo-ip {
         presence "enable geo-ip";
         description "GeoIP configuration";
         uses apply-advanced;
         container rule {
           description "GeoIP profile rule";
           uses apply-advanced;
           container match {
             uses apply-advanced;
             leaf-list country {
               ordered-by user;
               description "GeoIP Country List";
               type string;
             }
           }
           container then {
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     container dns-filter {
       description "DNS filter information";
       presence "enable dns-filter";
       uses dns-filter-object;
     }
     list url-filter-template {
       key name;
       ordered-by user;
       description "URL filter template";
       max-elements 8000;
       uses urlf-template-object;
     }
     list dns-filter-template {
       key name;
       ordered-by user;
       description "DNS filter template";
       max-elements 8000;
       uses dnsf-template-object;
     }
   }
   grouping dns-filter-object {
     uses apply-advanced;
     leaf database-file {
       description "Full path of the DNS filter database file";
       type string {
         length "1 .. 1024";
       }
     }
     leaf-list dns-server {
       ordered-by user;
       description "One or more DNS servers addresses";
       type jt:ipaddr;
       max-elements 20;
     }
     container hash-key {
       description "Define hash key for domains key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
     }
     leaf statistics-log-timer {
       description "DNS log timer in minutes";
       default "5";
       units "minutes";
       type union {
         type string {
           pattern "<.*>|$.*";
         }
         type uint32 {
           range "0 .. 60";
         }
       }
     }
     leaf dns-resp-ttl {
       description "TTL to be used in DNS response";
       default "1800";
       units "seconds";
       type union {
         type string {
           pattern "<.*>|$.*";
         }
         type uint32 {
           range "0 .. 3600";
         }
       }
     }
     leaf wildcarding-level {
       description "Wildcarding level for exact match";
       default "2";
       type union {
         type string {
           pattern "<.*>|$.*";
         }
         type uint32 {
           range "0 .. 10";
         }
       }
     }
     leaf txt-resp-err-code {
       description "Text response error code";
       default "Refused";
       type enumeration {
         enum "Noerror" {
           description "No error response";
         }
         enum "Refused" {
           description "Refuse the DNS Query";
         }
       }
     }
     leaf srv-resp-err-code {
       description "Server response error code";
       default "Refused";
       type enumeration {
         enum "Noerror" {
           description "No error response";
         }
         enum "Refused" {
           description "Refuse the DNS Query";
         }
       }
     }
   }
   grouping dnsf-template-object {
     leaf name {
       description "Name of template";
       type string {
         length "1 .. 64";
       }
     }
     uses apply-advanced;
     leaf feed-name {
       description "Name of feed";
       type string {
         length "1 .. 64";
       }
     }
     container dns-filter {
       description "DNS filter information";
       presence "enable dns-filter";
       uses dns-filter-object;
     }
     leaf-list client-interfaces {
       ordered-by user;
       description "Client facing interfaces on which the dns filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf client-routing-instance {
       description "Routing instance name";
       type string;
     }
     leaf server-routing-instance {
       description "Routing instance name";
       type string;
     }
     list term {
       key name;
       ordered-by user;
       description "Define a DNS filtering term";
       max-elements 64;
       leaf name {
         description "Term name";
         type string {
           length "1 .. 64";
         }
       }
       uses apply-advanced;
       leaf feed-name {
         description "Name of feed";
         type string {
           length "1 .. 64";
         }
       }
       container from {
         description "Define match criteria";
         uses dnsf-match-object;
       }
       container then {
         presence "enable then";
         description "Action to take if the 'from' condition is matched";
         uses apply-advanced;
         choice dns-filter-action {
           case case_1 {
             leaf dns-sinkhole {
               description "DNS sinkhole";
               type empty;
             }
           }
         }
       }
     }
   }
   grouping dnsf-match-object {
     uses apply-advanced;
     leaf-list src-ip-prefix {
       ordered-by user;
       description "Source IP Prefix list specification";
       type jt:ipprefix;
       max-elements 64;
     }
   }
   grouping threat-level-object {
     leaf name {
       description "Threat level value";
       type union {
         type string {
           pattern "<.*>|$.*";
         }
         type uint32 {
           range "1 .. 10";
         }
       }
     }
     uses apply-advanced;
     container policy-map {
       description "CoS Policy-map describing the user-attribute for a threat-level";
       uses apply-advanced;
       leaf pname {
         description "Policy-map name";
         type string {
           length "1 .. 64";
         }
       }
     }
     container threat-action {
       presence "enable threat-action";
       description "Action to be taken for the given threat level ";
       uses apply-advanced;
       choice secintl-action {
         case case_1 {
           leaf accept {
             description "Accept";
             type empty;
           }
         }
         case case_2 {
           leaf log {
             description "Log";
             type empty;
           }
         }
         case case_3 {
           leaf drop {
             description "Drop";
             type empty;
           }
         }
         case case_4 {
           leaf drop-and-log {
             description "Drop and log";
             type empty;
           }
         }
         case case_5 {
           leaf drop-and-sample {
             description "Drop and sample";
             type empty;
           }
         }
         case case_6 {
           leaf drop-log-and-sample {
             description "Drop log and sample";
             type empty;
           }
         }
         case case_7 {
           leaf log-and-sample {
             description "Log and sample";
             type empty;
           }
         }
         case case_8 {
           leaf sample {
             description "Push packets to sampling collector";
             type empty;
           }
         }
       }
     }
   }
   grouping urlf-template-object {
     leaf name {
       description "Name of template";
       type string {
         length "1 .. 64";
       }
     }
     uses apply-advanced;
     leaf-list client-interfaces {
       ordered-by user;
       description "Client facing interfaces on which the url filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf dns-source-interface {
       description "Interface on which the DNS queries are originated";
       type union {
         type jt:interface-unit;
         type string {
           pattern "<.*>|$.*";
         }
       }
     }
     leaf dns-routing-instance {
       description "Routing instance for DNS queries";
       type string;
     }
     leaf client-routing-instance {
       description "Routing instance name";
       type string;
       mandatory true;
     }
     leaf-list dns-server {
       ordered-by user;
       description "One or more DNS servers addresses";
       type jt:ipaddr;
       max-elements 2;
     }
     leaf dns-resolution-interval {
       description "DNS resolution timer in minutes";
       default "1440";
       units "minutes";
       type union {
         type string {
           pattern "<.*>|$.*";
         }
         type uint32 {
           range "60 .. 1440";
         }
       }
     }
     leaf dns-retries {
       description "DNS resolution attempts";
       default "3";
       type union {
         type string {
           pattern "<.*>|$.*";
         }
         type uint32 {
           range "1 .. 5";
         }
       }
     }
     leaf dns-resolution-rate {
       description "DNS resolution rate per chunk interval";
       default "50";
       type union {
         type string {
           pattern "<.*>|$.*";
         }
         type uint32 {
           range "50 .. 100";
         }
       }
     }
     leaf url-filter-database {
       description "Full path of the file";
       type string {
         length "1 .. 1024";
       }
     }
     leaf disable-url-ip-filtering {
       description "Disable filtering of IPs belonging to blocklisted domains";
       type empty;
     }
     leaf disable-https-filtering {
       description "Disable HTTPS based packets filtering - permit-all-https-packets";
       type empty;
     }
     container security-intelligence-policy {
       presence "enable security-intelligence-policy";
       description "Use the database supplied by security intelligence";
       uses apply-advanced;
       list threat-level {
         key name;
         ordered-by user;
         description "Define a URL filtering threat level";
         max-elements 10;
         uses template-threat-level-object;
       }
       container geo-ip {
         presence "enable geo-ip";
         description "GeoIP Template Rule configuration";
         uses apply-advanced;
         container rule {
           description "GeoIP Template";
           uses apply-advanced;
           container match {
             uses apply-advanced;
             leaf-list group {
               ordered-by user;
               description "GeoIP Country List";
               type string;
             }
           }
           container then {
             presence "enable then";
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     list term {
       key name;
       ordered-by user;
       description "Define a url filtering term";
       max-elements 8;
       leaf name {
         description "Term name";
         type string {
           length "1 .. 64";
         }
       }
       uses apply-advanced;
       container from {
         description "Define match criteria";
         uses urlf-match-object;
       }
       container then {
         presence "enable then";
         description "Action to take if the 'from' condition is matched";
         uses apply-advanced;
         choice url-filter-action {
           case case_1 {
             leaf redirect-url {
               description "Redirect URL";
               type string {
                 length "1 .. 1024";
               }
             }
           }
           case case_2 {
             leaf custom-page {
               description "Custome page string";
               type string {
                 length "1 .. 1025";
               }
             }
           }
           case case_3 {
             leaf http-status-code {
               description "HTTP status code value";
               type union {
                 type string {
                   pattern "<.*>|$.*";
                 }
                 type uint16 {
                   range "400 .. 599";
                 }
               }
             }
           }
           case case_4 {
             leaf tcp-reset {
               description "TCP Reset";
               type empty;
             }
           }
           case case_5 {
             leaf accept {
               description "Accept";
               type empty;
             }
           }
         }
       }
     }
   }
   grouping template-threat-level-object {
     leaf name {
       description "Threat level value";
       type union {
         type string {
           pattern "<.*>|$.*";
         }
         type uint32 {
           range "1 .. 10";
         }
       }
     }
     uses apply-advanced;
     container policy-map {
       description "CoS Policy-map describing the user-attribute for a threat-level";
       uses apply-advanced;
       leaf pname {
         description "Policy-map name";
         type string {
           length "1 .. 64";
         }
       }
     }
     container threat-action {
       presence "enable threat-action";
       description "Action to be taken for the given threat level ";
       uses apply-advanced;
       choice secintl-action {
         case case_1 {
           leaf drop-and-sample {
             description "Drop and sample";
             type empty;
           }
         }
         case case_2 {
           leaf sample {
             description "Push packets to sampling collector";
             type empty;
           }
         }
         case case_3 {
           leaf log {
             description "Log";
             type empty;
           }
         }
         case case_4 {
           leaf drop-and-log {
             description "Drop and log";
             type empty;
           }
         }
         case case_5 {
           leaf drop-log-and-sample {
             description "Drop,log and sample";
             type empty;
           }
         }
         case case_6 {
           leaf log-and-sample {
             description "Log and sample";
             type empty;
           }
         }
       }
     }
   }
   grouping urlf-match-object {
     uses apply-advanced;
     leaf-list src-ip-prefix {
       ordered-by user;
       description "Source IP Prefix list specification";
       type jt:ipprefix;
       max-elements 48;
     }
     leaf-list dest-ports {
       ordered-by user;
       description " Destination port list specification";
       type union {
         type string {
           pattern "<.*>|$.*";
         }
         type uint16 {
           range "1 .. 65535";
         }
       }
       max-elements 10;
     }
   }
   grouping urlf-traceoptions-object {
     description "URL filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         units "bytes";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace url filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping v3-user-config {
     description "SNMPv3 user configuration";
     leaf name {
       description "User name";
       type string {
         length "1 .. 32";
       }
     }
     uses apply-advanced;
     choice authentication {
       case case_1 {
         container authentication-md5 {
           description "Configure MD5 authentication";
           uses auth-object;
         }
       }
       case case_2 {
         container authentication-sha {
           description "Configure SHA authentication";
           uses auth-object;
         }
       }
       case case_3 {
         container authentication-sha224 {
           description "Configure SHA224 authentication";
           uses auth-object;
         }
       }
       case case_4 {
         container authentication-sha256 {
           description "Configure SHA256 authentication";
           uses auth-object;
         }
       }
       case case_5 {
         container authentication-sha384 {
           description "Configure SHA384 authentication";
           uses auth-object;
         }
       }
       case case_6 {
         container authentication-sha512 {
           description "Configure SHA512 authentication";
           uses auth-object;
         }
       }
       case case_7 {
         leaf authentication-none {
           description "Set no authentication for the user";
           type empty;
         }
       }
     }
     choice privacy {
       case case_1 {
         container privacy-des {
           description "Configure DES privacy";
           status deprecated;
           uses priv-object;
         }
       }
       case case_2 {
         container privacy-3des {
           description "Configure Triple DES privacy";
           uses priv-object;
         }
       }
       case case_3 {
         container privacy-aes128 {
           description "Configure AES128 privacy";
           uses priv-object;
         }
       }
       case case_4 {
         container privacy-aes256 {
           description "Configure AES256 privacy";
           uses priv-object;
         }
       }
       case case_5 {
         leaf privacy-none {
           description "Set no privacy for the user";
           type empty;
         }
       }
     }
   }
   grouping auth-object {
     description "Authentication parameters";
     uses apply-advanced;
     leaf authentication-password {
       description "User's authentication password";
       type string {
         length "8 .. 1024";
       }
     }
     leaf authentication-key {
       description "Encrypted key used for user authentication";
       type jt:unreadable;
     }
   }
   grouping priv-object {
     description "Privacy parameters";
     uses apply-advanced;
     leaf privacy-password {
       description "User's privacy password";
       type string {
         length "8 .. 1024";
       }
     }
     leaf privacy-key {
       description "Encrypted key used for user privacy";
       type jt:unreadable;
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container user-defined {
       presence "enable user-defined";
       description "Include user defined string";
       uses apply-advanced;
       leaf string {
         description "Set user-defined character string description";
         type string {
           length "1 .. 252";
         }
       }
       leaf hex-string {
         description "Set user-defined hexadecimal string description";
         type string {
           length "1 .. 510";
         }
       }
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       description "One or more server groups";
       leaf name {
         description "DHCPv6 Server group name";
         type string {
           length "1 .. 64";
         }
       }
       uses apply-advanced;
       list address {
         key name;
         description "IP Address of one or more DHCP servers";
         max-elements 32;
         leaf name {
           description "IP Address of DHCP server";
           type jt:ipaddr;
         }
         uses apply-advanced;
       }
     }
   }
   grouping vlan-group-types {
     description "802.1x Vlan Group";
     leaf name {
       description "VLAN group name";
       type string {
         length "2 .. 64";
       }
     }
     uses apply-advanced;
     leaf-list vlan-id-list {
       description "List of vlan-ids for VLAN group";
       type jt:vlan-range;
     }
   }
   grouping vlan-policy {
     description "Virtual LAN";
     leaf name {
       description "VLAN id";
       type string;
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
   }
   grouping vlan-types {
     description "Virtual LAN";
     leaf name {
       description "VLAN name";
       type string {
         length "2 .. 64";
       }
     }
     uses apply-advanced;
     leaf description {
       description "Text description of VLANs";
       type string {
       }
     }
     leaf activate-on-local-ports {
       description "Activate VLAN only if configured on interface or assigned by NAC to DOT1XD clients.";
       type empty;
     }
     choice vlan-identifier-choice {
       case case_1 {
         leaf vlan-id {
           description "IEEE 802.1q VLAN identifier for VLAN";
           type string;
         }
       }
       case case_2 {
         leaf-list vlan-id-list {
           description "Create VLAN for each of the vlan-id specified in the vlan-id-list";
           type jt:vlan-range;
         }
       }
       case case_3 {
         container vlan-tags {
           presence "enable vlan-tags";
           description "IEEE 802.1q VLAN tags for VLANs";
           leaf outer {
             description "[tpid.]vlan-id, tpid format is 0xNNNN and is optional";
             type string {
             }
             mandatory true;
           }
           leaf inner {
             description "[tpid.]vlan-id, tpid format is 0xNNNN and is optional";
             type string {
             }
           }
         }
       }
     }
     list interface {
       key name;
       ordered-by user;
       description "Interface name for this VLAN";
       leaf name {
         type string;
       }
       uses apply-advanced;
     }
     leaf l3-interface {
       description "L3 interface name for this vlans";
       type union {
         type jt:interface-unit;
         type string {
           pattern "<.*>|$.*";
         }
       }
     }
     container forwarding-options {
       description "Forwarding options configuration";
       uses juniper-ethernet-switching-forwarding-options;
     }
     container multicast-snooping-options {
       description "Multicast snooping option configuration";
       uses juniper-multicast-snooping-options;
     }
     container switch-options {
       description "VLANs switch-options configuration";
       uses juniper-protocols-vlan;
     }
     leaf domain-type {
       description "Type of VLANs SVLAN/DVLAN";
       type enumeration {
         enum "bridge" {
           description "Forwarding instance";
         }
       }
     }
     leaf no-irb-layer-2-copy {
       description "Disable transmission of layer-2 copy of packets of IRB routing-interface";
       type empty;
     }
     leaf service-id {
       description "Service id required if VLAN is of type MC-AE, and vlan-id all or vlan-id none or vlan-tags is configured";
       type union {
         type string {
           pattern "<.*>|$.*";
         }
         type uint32 {
           range "1 .. 65535";
         }
       }
     }
     leaf mcae-mac-synchronize {
       description "Enable IRB MAC synchronization in this VLAN";
       type empty;
     }
     leaf mcae-mac-flush {
       description "Enable IRB MAC flush in a/s mode for this VLAN on MCAE link up";
       type empty;
     }
     leaf private-vlan {
       description "Type of secondary vlan for private vlan";
       type enumeration {
         enum "isolated" {
           description "Isolated vlan";
         }
         enum "community" {
           description "Community vlan";
         }
       }
     }
     leaf isolated-vlan {
       description "VLAN id or name";
       type string {
       }
     }
     leaf-list community-vlans {
       ordered-by user;
       description "List of VLAN id or name";
       type string;
     }
     container vxlan {
       uses apply-advanced;
       leaf ovsdb-managed {
         description "Bridge-domain is managed remotely via VXLAN OVSDB Controller";
         type empty;
       }
       leaf vni {
         description "VXLAN identifier";
         type union {
           type string {
             pattern "<.*>|$.*";
           }
           type uint32 {
             range "0 .. 16777214";
           }
         }
         mandatory true;
       }
       leaf translation-vni {
         description "Translated VXLAN identifier";
         type union {
           type string {
             pattern "<.*>|$.*";
           }
           type uint32 {
             range "1 .. 16777214";
           }
         }
       }
       leaf multicast-group {
         description "Multicast group registered for VXLAN segment";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf-list static-remote-vtep-list {
         description "Configure vlan specific static remote VXLAN tunnel endpoints";
         type jt:ipaddr;
         max-elements 1024;
       }
       leaf riot-loopback {
         description "Enable loopback on RIOT platform";
         type empty;
       }
     }
   }
   grouping juniper-ethernet-switching-forwarding-options {
     uses apply-advanced;
     container filter {
       description "Filtering for ethernet switching forwarding table";
       uses apply-advanced;
       leaf input {
         description "Name of input filter to apply for forwarded packets";
         type string;
       }
       leaf output {
         description "Name of output filter to apply for forwarded packets";
         type string;
       }
     }
     container flood {
       description "Filtering for ethernet switching flood table";
       uses apply-advanced;
       leaf input {
         description "Name of input filter to apply for ethernet switching flood packets";
         type string;
       }
     }
     container dhcp-relay {
       description "Dynamic Host Configuration Protocol relay configuration";
       status deprecated;
       uses jdhcp-relay-type;
     }
     container dhcp-security {
       description "DHCP access security configuration";
       presence "enable dhcp-security";
       uses jdhcp-security-type;
     }
   }
   grouping jdhcp-security-type {
     description "DHCP access security configuration";
     uses apply-advanced;
     leaf no-dhcp-snooping {
       description "Disable dhcp snooping";
       type empty;
     }
     leaf arp-inspection {
       description "Enable dynamic ARP inspection";
       type empty;
     }
     leaf ip-source-guard {
       description "Enable IP source guard";
       type empty;
     }
     leaf no-dhcpv6-snooping {
       description "Disable DHCPv6 snooping";
       type empty;
     }
     leaf neighbor-discovery-inspection {
       description "Enable neighbor discovery inspection";
       type empty;
     }
     leaf ipv6-source-guard {
       description "Enable IPv6 source guard";
       type empty;
     }
     leaf light-weight-dhcpv6-relay {
       description "Enable light weight dhcpv6 relay";
       type empty;
     }
     list group {
       key name;
       description "Define a DHCP security group for overriding defaults";
       uses ds-group;
     }
     container option-82 {
       description "DHCP option-82 processing for snooped packets";
       presence "enable option-82";
       uses security-option-82-type;
     }
     container dhcpv6-options {
       description "DHCPv6 option processing for snooped packets";
       presence "enable dhcpv6-options";
       uses security-dhcpv6-options-type;
     }
     leaf mine-dhcp-client-options {
       description "Start storing incoming DHCP client options";
       type empty;
     }
     leaf mine-dhcpv6-client-options {
       description "Start storing incoming DHCPv6 client options";
       type empty;
     }
     leaf trust-all {
       description "Mark all ports as trusted for dhcp security";
       type empty;
     }
     leaf retain-binding-on-renegotiation {
       description "Retain existing IANA binding on renegotiation";
       type empty;
     }
   }
   grouping ds-group {
     description "DHCP security groups";
     leaf name {
       description "Group name";
       type string {
         length "1 .. 64";
       }
     }
     uses apply-advanced;
     container overrides {
       description "DHCP override processing";
       presence "enable overrides";
       uses ds-override-type;
     }
     list interface {
       key name;
       description "One or more interfaces";
       leaf name {
         description "Interface name";
         type union {
           type jt:interface-name;
           type string {
             pattern "<.*>|$.*";
           }
         }
       }
       uses apply-advanced;
       list static-ip {
         key name;
         ordered-by user;
         description "Static IP address configuration";
         uses ip-mac-static;
       }
       list static-ipv6 {
         key name;
         ordered-by user;
         description "Static IPv6 address configuration";
         uses ipv6-mac-static;
       }
     }
   }
   grouping ds-override-type {
     description "Dynamic ARP Inspection override processing";
     uses apply-advanced;
     leaf trusted {
       description "Make this trusted group of interfaces";
       type empty;
     }
     leaf untrusted {
       description "Make this untrusted group of interfaces";
       type empty;
     }
     leaf no-option82 {
       description "Make this group of interfaces not to add option82";
       type empty;
     }
     leaf no-option37 {
       description "Make this group of interfaces not to add option37";
       type empty;
     }
     leaf no-option18 {
       description "Make this group of interfaces not to add option18";
       type empty;
     }
     leaf no-option16 {
       description "Make this group of interfaces not to add option16";
       type empty;
     }
     leaf no-option79 {
       description "Make this group of interfaces not to add option79";
       type empty;
     }
     leaf no-dhcpv6-options {
       description "Make this group of interfaces not to add any DHCPv6 options";
       type empty;
     }
   }
   grouping ip-mac-static {
     leaf name {
       description "IP address";
       type jt:ipaddr;
     }
     leaf mac {
       description "MAC address";
       type jt:mac-addr;
       mandatory true;
     }
   }
   grouping ipv6-mac-static {
     leaf name {
       description "IP address";
       type jt:ipv6addr;
     }
     leaf mac {
       description "MAC address";
       type jt:mac-addr;
       mandatory true;
     }
   }
   grouping juniper-protocols-vlan {
     description "VLANs switch-options configuration";
     uses apply-advanced;
     leaf no-mac-aging {
       description "Disable MAC address aging";
       type empty;
     }
     leaf no-mac-ip-snooping {
       description "Disable MAC+IP snooping";
       type empty;
     }
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum number of MAC+IP bindings learned on the interface";
       uses apply-advanced;
       leaf limit {
         description "Maximum number of MAC+IP bindings per interface";
         type union {
           type string {
             pattern "<.*>|$.*";
           }
           type uint32;
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-mac-ip-learning {
       description "Disable dynamic MAC IP address learning";
       type empty;
     }
     leaf no-normalization {
       description "Disable vlan id normalization for interfaces";
       type empty;
     }
     container port-extender {
       presence "enable port-extender";
       description "Configure port-extender";
       uses apply-advanced;
       leaf mode {
         description "Configure port-extender mode";
         type enumeration {
           enum "aggregation-device" {
             description "Aggregation Device";
           }
           enum "satellite-device" {
             description "Satellite Device";
           }
         }
       }
     }
     leaf drop-unknown-mac-ip {
       description "Drop unknown MAC-IP traffic";
       type empty;
     }
     leaf mac-statistics {
       description "Enable MAC address statistics";
       type empty;
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     container network-isolation-profile {
       description "Network isolation configuration";
       uses apply-advanced;
       list group {
         key name;
         description "Network isolation group";
         leaf name {
           description "Group name";
           type string;
         }
         uses apply-advanced;
       }
     }
     list interface {
       key name;
       description "Interface that connect this site to the VPN";
       leaf name {
         description "Interface name";
         type union {
           type jt:interface-name;
           type string {
             pattern "<.*>|$.*";
           }
         }
       }
       uses apply-advanced;
       container mac-learning-priority {
         description "MAC learning priority for the interface";
         uses apply-advanced;
         leaf priority {
           description "Mac learning priority for the interface";
           type union {
             type string {
               pattern "<.*>|$.*";
             }
             type uint32 {
               range "1 .. 65535";
             }
           }
         }
         leaf packet-action {
           default "discard";
           type enumeration {
             enum "discard" {
               description "Discard the packets and do not learn. Default is forward";
             }
             enum "forward" {
               description "Forward the packet";
             }
           }
         }
       }
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       leaf action-priority {
         description "Blocking priority of this interface on mac move detection";
         type union {
           type string {
             pattern "<.*>|$.*";
           }
           type uint32 {
             range "0 .. 8";
           }
         }
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       list static-mac-ip {
         key name;
         ordered-by user;
         description "Static MAC-IP address bindings";
         leaf name {
           description "IP address";
           type jt:ipaddr;
         }
         uses apply-advanced;
         leaf-list mac-address {
           ordered-by user;
           description "MAC address";
           type jt:mac-unicast;
           max-elements 8;
         }
         leaf router {
           description "Router flag for ipv6 addresses";
           type empty;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
     }
     container traceoptions {
       description "Trace options for this bridge domain";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           units "bytes";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "storm-control" {
               description "Storm-control";
             }
             enum "unknown-unicast-forwarding" {
               description "Trace unknown unicast forwarding events";
             }
             enum "all" {
               description "All operations";
             }
           }
         }
       }
     }
   }
   grouping security-dhcpv6-options-type {
     description "Configure DHCPv6 options";
     uses apply-advanced;
     container option-37 {
       presence "enable option-37";
       description "Configure DHCPv6 remote identifier option";
       uses apply-advanced;
       container prefix {
         description "Configure DHCPv6 remote identifier prefix";
         uses apply-advanced;
         leaf host-name {
           description "Prefix router host name to DHCPv6 remote identifier";
           type empty;
         }
         leaf logical-system-name {
           description "Prefix logical system name to DHCPv6 remote identifier";
           type empty;
         }
         leaf routing-instance-name {
           description "Prefix routing instance name to DHCPv6 remote identifier";
           type empty;
         }
         leaf vlan-name {
           description "Prefix vlan name to DHCPv6 remote identifier";
           type empty;
         }
         leaf vlan-id {
           description "Prefix vlan tag to DHCPv6 remote identifier";
           type empty;
         }
       }
       leaf use-interface-mac {
         description "Add incoming interface's MAC address to DHCPv6 remote identifier";
         type empty;
       }
       leaf use-interface-index {
         description "Add interface index to DHCPv6 remote identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 remote identifier";
         type enumeration {
           enum "logical" {
             description "Use the logical interface description";
           }
           enum "device" {
             description "Use the device interface description";
           }
         }
       }
       leaf use-string {
         description "Add custom string to DHCPv6 remote identifier";
         type string;
       }
     }
     container option-18 {
       presence "enable option-18";
       description "Configure DHCPv6 interface identifier option";
       uses apply-advanced;
       container prefix {
         description "Configure DHCPv6 interface identifier prefix";
         uses apply-advanced;
         leaf host-name {
           description "Prefix router host name to DHCPv6 interface identifier";
           type empty;
         }
         leaf logical-system-name {
           description "Prefix logical system name to DHCPv6 interface identifier";
           type empty;
         }
         leaf routing-instance-name {
           description "Prefix routing instance name to DHCPv6 interface identifier";
           type empty;
         }
         leaf vlan-name {
           description "Prefix vlan name to DHCPv6 interface identifier";
           type empty;
         }
         leaf vlan-id {
           description "Prefix vlan tag to DHCPv6 interface identifier";
           type empty;
         }
       }
       leaf use-interface-mac {
         description "Add incoming interface's MAC address to DHCPv6 circuit identifier";
         type empty;
       }
       leaf use-interface-index {
         description "Add interface index to DHCPv6 interface identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 interface identifier";
         type enumeration {
           enum "logical" {
             description "Use the logical interface description";
           }
           enum "device" {
             description "Use the device interface description";
           }
         }
       }
       leaf use-string {
         description "Add custom string to DHCPv6 interface identifier";
         type string;
       }
     }
     container option-16 {
       presence "enable option-16";
       description "Configure DHCPv6 vendor class identifier option. Overwrite if exists";
       uses apply-advanced;
       leaf use-string {
         description "Add custom string to DHCPv6 vendor identifier";
         type string;
       }
     }
     leaf option-79 {
       description "Configure DHCPv6 client link layer address option";
       type empty;
     }
   }
   grouping security-option-82-type {
     description "DHCP option-82 processing";
     uses apply-advanced;
     container circuit-id {
       presence "enable circuit-id";
       description "Configure DHCP option 82 circuit id";
       uses apply-advanced;
       container prefix {
         description "Configure DHCP option 82 circuit id prefix";
         uses apply-advanced;
         leaf host-name {
           description "Add router host name to DHCP option-82 circuit id";
           type empty;
         }
         leaf logical-system-name {
           description "Add logical system name to DHCP option-82 circuit id";
           type empty;
         }
         leaf routing-instance-name {
           description "Add routing instance name to DHCP option-82 circuit id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
     }
     container remote-id {
       presence "enable remote-id";
       description "Configure DHCP option 82 remote id";
       uses apply-advanced;
       leaf host-name {
         description "Add router host name to DHCP option-82 remote id";
         type empty;
       }
       leaf use-interface-description {
         description "Use interface description instead of interface name";
         type enumeration {
           enum "logical" {
             description "Use the logical interface description";
           }
           enum "device" {
             description "Use the device interface description";
           }
         }
       }
       leaf use-string {
         description "Use raw string instead of the default remote id";
         type string;
       }
       leaf mac {
         description "Add chassis MAC Address to DHCP option-82 remote id";
         type empty;
       }
     }
     container vendor-id {
       presence "enable vendor-id";
       description "Configure DHCP option 82 vendor id";
       uses apply-advanced;
       leaf use-string {
         description "Use raw string instead of the default vendor id";
         default "Juniper Networks";
         type string;
       }
     }
   }
   grouping vlan_map {
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string;
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vpls_filter {
     description "Define an VPLS firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice learn-vlan-id_choice {
           case case_1 {
           }
           case case_2 {
           }
         }
         choice learn-vlan-1p-priority_choice {
           case case_1 {
           }
           case case_2 {
           }
         }
         choice user-vlan-id_choice {
           case case_1 {
           }
           case case_2 {
           }
         }
         choice user-vlan-1p-priority_choice {
           case case_1 {
           }
           case case_2 {
           }
         }
         choice learn-vlan-dei_choice {
           case case_1 {
           }
           case case_2 {
           }
         }
         choice traffic-type_choice {
           case case_1 {
           }
           case case_2 {
           }
         }
         choice ip-protocol_choice {
           case case_1 {
           }
           case case_2 {
           }
         }
         choice dscp_choice {
           case case_1 {
           }
           case case_2 {
           }
         }
         choice ip-precedence_choice {
           case case_1 {
           }
           case case_2 {
           }
         }
         choice source-port_choice {
           case case_1 {
           }
           case case_2 {
           }
         }
         choice destination-port_choice {
           case case_1 {
           }
           case case_2 {
           }
         }
         choice port_choice {
           case case_1 {
           }
           case case_2 {
           }
         }
         choice icmp-code_choice {
           case case_1 {
           }
           case case_2 {
           }
         }
         choice icmp-type_choice {
           case case_1 {
           }
           case case_2 {
           }
         }
         list interface {
           key name;
           ordered-by user;
           description "Match interface name";
           uses match_interface_object;
         }
         list interface-set {
           key name;
           ordered-by user;
           description "Match interface in set";
           uses match_interface_set_object;
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
           }
           case case_3 {
             leaf hierarchical-policer {
               description "Name of hierarchical policer to use to rate-limit traffic";
               type string {
               }
             }
           }
           case case_4 {
           }
           case case_5 {
             leaf policer-charge {
               description "Name of policer-charge used to charge the policer";
               type string {
               }
             }
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to specified instance";
           type string {
           }
         }
         leaf port-mirror {
           description "Port-mirror the packet";
           type empty;
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
       }
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       type enumeration {
         enum "md5" {
           description "HMAC-MD5-96";
         }
         enum "simple" {
           description "Simple password";
         }
       }
     }
     leaf authentication-key {
       description "Authentication key";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           type union {
             type jt:interface-unit;
             type string {
               pattern "<.*>|$.*";
             }
           }
         }
         uses apply-advanced;
         list bandwidth-threshold {
           key name;
           description "Track bandwidth of interface";
           leaf name {
             description "Interface speed below which priority cost is incurred";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         description "Route to track in VRRP group";
         leaf route_address {
           description "Route address";
           type jt:ipprefix-mandatory;
         }
         leaf routing-instance {
           description "Routing instance to which route belongs, or 'default'";
           type string {
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
         mandatory true;
       }
       leaf active-group {
         description "Identifier for VRRP active group";
         type union {
           type string {
             pattern "<.*>|$.*";
           }
           type uint32 {
             range "0 .. 255";
           }
         }
         mandatory true;
       }
     }
     leaf advertisements-threshold {
       description "Number of vrrp advertisements missed before declaring master down";
       type union {
         type string {
           pattern "<.*>|$.*";
         }
         type uint32 {
           range "1 .. 15";
         }
       }
     }
   }
   grouping write-option-82-type {
     uses apply-advanced;
   }
 }
