/*
 * Copyright (c) 2026 Juniper Networks, Inc.
 * All rights reserved.
 */
 module junos-ex-rpc-network-agent {
   namespace "http://yang.juniper.net/junos-ex/rpc/network-agent";

   prefix network-agent;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for network-agent command(s)";

   revision 2026-01-01 {
     description "Junos: 26.2R1.7";
   }

   rpc get-telemetry-subscription-statistics {
     description "Show network agent sensor statistics";
     junos:command "show network-agent statistics";
     input {
       leaf verbosity_level {
         junos:cli-feature "nokeyword";
         default "brief";
         type enumeration {
           enum "brief" {
             description "Display brief output (default)";
           }
           enum "detail" {
             description "Display detailed output";
           }
         }
       }
       leaf subscription-id {
         description "Subscription ID";
         junos:cli-feature "nokeyword";
         default "4294967295";
         type union {
           type string {
             pattern "<.*>|$.*";
           }
           type uint32 {
             range "1 .. 4294967295";
           }
         }
       }
       leaf subscription-type {
         description "Subscription Type";
         junos:cli-feature "nokeyword";
         default "all";
         type enumeration {
           enum "juniper" {
             description "Juniper based subscription";
           }
           enum "gnmi" {
             description "GNMI based subscription";
           }
           enum "all" {
             description "All telemetry subscriptions";
           }
         }
       }
       leaf-list subscription-paths {
         ordered-by user;
         description "Subscription paths for which statistics are to be displayed";
         type string;
       }
     }
     output {
       choice output-tags {
         case actual-tag {
           container subscription-statistics {
             uses subscription-statistics-block;
           }
         }
         case multichassis-tag {
           container multi-routing-engine-results {
             list multi-routing-engine-item {
               leaf re-name {
                 type string;
               }
               choice output-tags {
                 case actual-tag {
                   container subscription-statistics {
                     uses subscription-statistics-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping subscription-statistics-block {
     list subscription-details {
       description
         "Show subscription statistics information";
       leaf subscription-id {
         type uint64;
         description
           "Telemetry subscription ID";
       }
       leaf subscription-type {
         type string;
         description
           "Type of the subscription";
       }
       leaf client-ip-port {
         type string;
         description
           "IP-port of the client";
       }
       leaf gnmi-mode {
         type string;
         description
           "GNMI mode for the subscription";
       }
       leaf subscription-time {
         type string;
         description
           "Time at which the subscription request was received";
       }
       leaf transmit-bps {
         type uint64;
         description
           "Telemetry data rate in bps";
       }
       leaf transmit-pps {
         type uint64;
         description
           "Telemetry data rate in pps";
       }
       leaf fail {
         type string;
         description
           "Failure message for getting subscription statistics";
       }
       list sensor-statistics-brief {
         description
           "Show brief sensor statistics";
         leaf sensor-path {
           type string;
           description
             "Sensor path";
         }
         leaf rep-interval {
           type int32;
           description
             "Reporting interval (in seconds)";
         }
         leaf node-name {
           type string;
           description
             "RE name from which data produced";
         }
         leaf component-name {
           type string;
           description
             "Component(s) servicing the sensor";
         }
         leaf gnmi-sub-mode {
           type string;
           description
             "GNMI SubMode for the subscription";
         }
         leaf component-id {
           type int32;
           description
             "Component ID for PFE sensors";
         }
         list child-sensor-statistics-brief {
           description
             "Show brief child sensor statistics";
           leaf child-sensor-path {
             type string;
             description
               "Child sensor path";
           }
           leaf child-node-name {
             type string;
             description
               "RE name from which data produced";
           }
           leaf child-component-name {
             type string;
             description
               "Child Component servicing the sensor";
           }
           leaf child-component-id {
             type int32;
             description
               "Child component ID for PFE sensors";
           }
           leaf child-gnmi-sub-mode {
             type string;
             description
               "Child GNMI SubMode for the subscription";
           }
           leaf child-rep-interval {
             type int32;
             description
               "Child Reporting interval (in seconds)";
           }
         }
         leaf average-latency {
           type uint32;
           description
             "Average iLatency in milli seconds";
         }
         leaf circular-buffer-used {
           type uint32;
           description
             "Average circular buffer use in percentage";
         }
         leaf bytes-sent {
           type uint64;
           description
             "Number of bytes sent";
         }
         leaf packets-sent {
           type uint64;
           description
             "Number of packets sent";
         }
         leaf packet-drops {
           type uint64;
           description
             "Number of packets dropped";
         }
         leaf initial-sync-bytes-sent {
           type uint64;
           description
             "Number of bytes sent for initial sync";
         }
         leaf initial-sync-packets-sent {
           type uint64;
           description
             "Number of packets sent for initial sync";
         }
         leaf initial-sync-packet-drops {
           type uint64;
           description
             "Number of packets dropped for initial sync";
         }
         leaf initial-sync-average-latency {
           type uint32;
           description
             "Average initial sync iLatency in milli seconds";
         }
         leaf initial-sync-circular-buffer-used {
           type uint32;
           description
             "Average initial sync circular buffer use in percentage";
         }
         list child-sensor-statistics-detail {
           description
             "Show detail sensor statistics";
           leaf child-sensor-path {
             type string;
             description
               "Child sensor path";
           }
           leaf child-node-name {
             type string;
             description
               "RE name from which data produced";
           }
           leaf child-component-name {
             type string;
             description
               "Child Component servicing the sensor";
           }
           leaf child-component-id {
             type int32;
             description
               "Child component ID for PFE sensors";
           }
           leaf child-gnmi-sub-mode {
             type string;
             description
               "Child GNMI SubMode for the subscription";
           }
           leaf child-average-latency {
             type uint32;
             description
               "Child Average iLatency in milli seconds";
           }
           leaf child-bytes-sent {
             type uint64;
             description
               "Number of bytes sent - child sensor";
           }
           leaf child-packets-sent {
             type uint64;
             description
               "Number of packets sent - child sensor";
           }
           leaf child-packet-drops {
             type uint64;
             description
               "Number of packets dropped - child sensor";
           }
           leaf child-initial-sync-bytes-sent {
             type uint64;
             description
               "Number of bytes sent for initial sync - child sensor";
           }
           leaf child-initial-sync-packets-sent {
             type uint64;
             description
               "Number of packets sent for initial sync - child sensor";
           }
           leaf child-initial-sync-packet-drops {
             type uint64;
             description
               "Number of packets dropped for initial sync - child sensor";
           }
           leaf child-initial-sync-average-latency {
             type uint32;
             description
               "Child Average initial sync iLatency in milli seconds";
           }
           leaf child-rep-interval {
             type int32;
             description
               "Child Reporting interval (in seconds)";
           }
         }
       }
       list sensor-statistics-detail {
         description
           "Show detail sensor statistics";
         leaf sensor-path {
           type string;
           description
             "Sensor path";
         }
         leaf rep-interval {
           type int32;
           description
             "Reporting interval (in seconds)";
         }
         leaf node-name {
           type string;
           description
             "RE name from which data produced";
         }
         leaf component-name {
           type string;
           description
             "Component(s) servicing the sensor";
         }
         leaf gnmi-sub-mode {
           type string;
           description
             "GNMI SubMode for the subscription";
         }
         leaf component-id {
           type int32;
           description
             "Component ID for PFE sensors";
         }
         list child-sensor-statistics-detail {
           description
             "Show detail sensor statistics";
           leaf child-sensor-path {
             type string;
             description
               "Child sensor path";
           }
           leaf child-node-name {
             type string;
             description
               "RE name from which data produced";
           }
           leaf child-rep-interval {
             type int32;
             description
               "Child Reporting interval (in seconds)";
           }
           leaf child-component-name {
             type string;
             description
               "Child Component servicing the sensor";
           }
           leaf child-gnmi-sub-mode {
             type string;
             description
               "Child GNMI SubMode for the subscription";
           }
           leaf child-component-id {
             type int32;
             description
               "Child component ID for PFE sensors";
           }
           leaf child-average-latency {
             type uint32;
             description
               "Child Average iLatency in milli seconds";
           }
           leaf child-bytes-sent {
             type uint64;
             description
               "Number of bytes sent - child sensor";
           }
           leaf child-packets-sent {
             type uint64;
             description
               "Number of packets sent - child sensor";
           }
           leaf child-packet-drops {
             type uint64;
             description
               "Number of packets dropped - child sensor";
           }
           leaf child-initial-sync-bytes-sent {
             type uint64;
             description
               "Number of bytes sent for initial sync - child sensor";
           }
           leaf child-initial-sync-packets-sent {
             type uint64;
             description
               "Number of packets sent for initial sync - child sensor";
           }
           leaf child-initial-sync-packet-drops {
             type uint64;
             description
               "Number of packets dropped for initial sync - child sensor";
           }
           leaf child-initial-sync-average-latency {
             type uint32;
             description
               "Child Average initial sync iLatency in milli seconds";
           }
         }
         leaf average-latency {
           type uint32;
           description
             "Average iLatency in milli seconds";
         }
         leaf circular-buffer-used {
           type uint32;
           description
             "Average circular buffer use in percentage";
         }
         leaf bytes-sent {
           type uint64;
           description
             "Number of bytes sent";
         }
         leaf packets-sent {
           type uint64;
           description
             "Number of packets sent";
         }
         leaf packet-drops {
           type uint64;
           description
             "Number of packets dropped";
         }
         leaf initial-sync-bytes-sent {
           type uint64;
           description
             "Number of bytes sent for initial sync";
         }
         leaf initial-sync-packets-sent {
           type uint64;
           description
             "Number of packets sent for initial sync";
         }
         leaf initial-sync-packet-drops {
           type uint64;
           description
             "Number of packets dropped for initial sync";
         }
         leaf initial-sync-average-latency {
           type uint32;
           description
             "Average initial sync iLatency in milli seconds";
         }
         leaf initial-sync-circular-buffer-used {
           type uint32;
           description
             "Average initial sync circular buffer use in percentage";
         }
       }
       leaf simple-int {
         type int32;
       }
     }
   }
 }
