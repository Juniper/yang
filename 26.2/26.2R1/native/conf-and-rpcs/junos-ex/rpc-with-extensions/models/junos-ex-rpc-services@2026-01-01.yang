/*
 * Copyright (c) 2026 Juniper Networks, Inc.
 * All rights reserved.
 */
 module junos-ex-rpc-services {
   namespace "http://yang.juniper.net/junos-ex/rpc/services";

   prefix services;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for services command(s)";

   revision 2026-01-01 {
     description "Junos: 26.2R1.7";
   }

   rpc get-pcef-subscribers {
     description "Show subscriber information";
     junos:command "show services pcef subscribers";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         junos:cli-feature "nokeyword";
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output-tags {
         case output-tag {
           leaf output {
             type string;
           }
         }
         case actual-tag {
           anyxml pcef-subscriber;
         }
         case multichassis-tag {
           anyxml multi-routing-engine-results;
         }
       }
     }
   }
   rpc get-pcef-subscribers-summary {
     description "Display pcef subscriber summary";
     junos:command "show services pcef subscribers summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
     output {
       choice output-tags {
         case output-tag {
           leaf output {
             type string;
           }
         }
         case actual-tag {
           anyxml pcef-subscriber;
         }
         case multichassis-tag {
           anyxml multi-routing-engine-results;
         }
       }
     }
   }
   rpc get-pcef-pic {
     description "Show physical interface card information";
     junos:command "show services pcef pic";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         junos:cli-feature "nokeyword";
         default "terse";
         type enumeration {
           enum "terse" {
             description "Display terse output";
           }
         }
       }
     }
     output {
       choice output-tags {
         case output-tag {
           leaf output {
             type string;
           }
         }
         case actual-tag {
           anyxml pcef-pic;
         }
         case multichassis-tag {
           anyxml multi-routing-engine-results;
         }
       }
     }
   }
   rpc get-ift-global-information {
     description "Show inband telemetry information";
     junos:command "show services inband-flow-telemetry global";
     output {
       choice output-tags {
         case actual-tag {
           container ift-global-information {
             uses ift-global-information-block;
           }
         }
         case multichassis-tag {
           container multi-routing-engine-results {
             list multi-routing-engine-item {
               leaf re-name {
                 type string;
               }
               choice output-tags {
                 case actual-tag {
                   container ift-global-information {
                     uses ift-global-information-block;
                   }
                 }
               }
             }
           }
         }
       }
     }
   }
   rpc get-ift-profile-information {
     description "Show inband telemetry profile details";
     junos:command "show services inband-flow-telemetry profile";
     input {
       leaf profile-name {
         description "Name of the profile";
         junos:cli-feature "nokeyword";
         type string;
       }
     }
     output {
       choice output-tags {
         case actual-tag {
           container ift-profile-information {
             uses ift-profile-information-block;
           }
         }
         case multichassis-tag {
           container multi-routing-engine-results {
             list multi-routing-engine-item {
               leaf re-name {
                 type string;
               }
               choice output-tags {
                 case actual-tag {
                   container ift-profile-information {
                     uses ift-profile-information-block;
                   }
                 }
               }
             }
           }
         }
       }
     }
   }
   rpc get-ift-stats-information {
     description "Show inband telemetry stats information";
     junos:command "show services inband-flow-telemetry stats";
     output {
       choice output-tags {
         case actual-tag {
           container ift-stats-information {
             uses ift-stats-information-block;
           }
         }
         case multichassis-tag {
           container multi-routing-engine-results {
             list multi-routing-engine-item {
               leaf re-name {
                 type string;
               }
               choice output-tags {
                 case actual-tag {
                   container ift-stats-information {
                     uses ift-stats-information-block;
                   }
                 }
               }
             }
           }
         }
       }
     }
   }
   rpc get-fips-pic-status-information {
     description "Show FIPS PIC authorization status";
     junos:command "show services fips pic status";
     output {
       choice output-tags {
         case actual-tag {
           container fips-pic-status-information {
             uses fips-pic-status-information-block;
           }
         }
         case multichassis-tag {
           container multi-routing-engine-results {
             list multi-routing-engine-item {
               leaf re-name {
                 type string;
               }
               choice output-tags {
                 case actual-tag {
                   container fips-pic-status-information {
                     uses fips-pic-status-information-block;
                   }
                 }
               }
             }
           }
         }
       }
     }
   }
   rpc get-lrf-statistics {
     description "Show lrf statistics";
     junos:command "show services lrf statistics";
     output {
       choice output-tags {
         case actual-tag {
           container lrf-statistics-summary {
             uses lrf-statistics-summary-block;
           }
         }
         case multichassis-tag {
           container multi-routing-engine-results {
             list multi-routing-engine-item {
               leaf re-name {
                 type string;
               }
               choice output-tags {
                 case actual-tag {
                   container lrf-statistics-summary {
                     uses lrf-statistics-summary-block;
                   }
                 }
               }
             }
           }
         }
       }
     }
   }
   rpc get-lrf-collector-statistics {
     description "Show lrf collector statistics";
     junos:command "show services lrf collector statistics";
     input {
       leaf collector-name {
         description "Name of collector";
         junos:cli-feature "nokeyword";
         type string;
       }
     }
     output {
       choice output-tags {
         case actual-tag {
           container lrf-collector-statistics-summary {
             uses lrf-collector-statistics-summary-block;
           }
         }
         case multichassis-tag {
           container multi-routing-engine-results {
             list multi-routing-engine-item {
               leaf re-name {
                 type string;
               }
               choice output-tags {
                 case actual-tag {
                   container lrf-collector-statistics-summary {
                     uses lrf-collector-statistics-summary-block;
                   }
                 }
               }
             }
           }
         }
       }
     }
   }
   rpc get-lrf-rule-statistics {
     description "Show lrf rule statistics";
     junos:command "show services lrf rule statistics";
     input {
       leaf rule-name {
         description "Name of rule";
         junos:cli-feature "nokeyword";
         type string;
       }
     }
     output {
       choice output-tags {
         case actual-tag {
           container lrf-rule-statistics-summary {
             uses lrf-rule-statistics-summary-block;
           }
         }
         case multichassis-tag {
           container multi-routing-engine-results {
             list multi-routing-engine-item {
               leaf re-name {
                 type string;
               }
               choice output-tags {
                 case actual-tag {
                   container lrf-rule-statistics-summary {
                     uses lrf-rule-statistics-summary-block;
                   }
                 }
               }
             }
           }
         }
       }
     }
   }
   rpc get-lrf-template {
     description "Show lrf template";
     junos:command "show services lrf template";
     input {
       leaf template-type {
         description "Template type";
         junos:cli-feature "nokeyword";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       choice output-tags {
         case actual-tag {
           container lrf-template {
             uses lrf-template-block;
           }
         }
         case multichassis-tag {
           container multi-routing-engine-results {
             list multi-routing-engine-item {
               leaf re-name {
                 type string;
               }
               choice output-tags {
                 case actual-tag {
                   container lrf-template {
                     uses lrf-template-block;
                   }
                 }
               }
             }
           }
         }
       }
     }
   }
   rpc get-analytics-agent-information {
     description "Show analytics service agent information";
     junos:command "show services analytics agent";
     input {
       leaf level {
         junos:cli-feature "nokeyword";
         default "brief";
         type enumeration {
           enum "detail" {
             description "Display detailed data";
           }
           enum "brief" {
             description "Display brief data (default)";
           }
         }
       }
     }
     output {
       choice output-tags {
         case actual-tag {
           container analytics-agent-information {
             uses analytics-agent-information-block;
           }
         }
         case multichassis-tag {
           container multi-routing-engine-results {
             list multi-routing-engine-item {
               leaf re-name {
                 type string;
               }
               choice output-tags {
                 case actual-tag {
                   container analytics-agent-information {
                     uses analytics-agent-information-block;
                   }
                 }
               }
             }
           }
         }
       }
     }
   }
   rpc get-services-analytics-dialout-statistics {
     description "Show telemetry dialout statistics";
     junos:command "show services analytics dialout statistics";
     output {
       choice output-tags {
         case actual-tag {
           container services-analytics-dialout-statistics {
             uses services-analytics-dialout-statistics-block;
           }
         }
         case multichassis-tag {
           container multi-routing-engine-results {
             list multi-routing-engine-item {
               leaf re-name {
                 type string;
               }
               choice output-tags {
                 case actual-tag {
                   container services-analytics-dialout-statistics {
                     uses services-analytics-dialout-statistics-block;
                   }
                 }
               }
             }
           }
         }
       }
     }
   }
   rpc get-probe-results {
     description "Show probe results";
     junos:command "show services rpm probe-results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       choice output-tags {
         case actual-tag {
           container probe-results {
             uses probe-results-block;
           }
         }
         case multichassis-tag {
           container multi-routing-engine-results {
             list multi-routing-engine-item {
               leaf re-name {
                 type string;
               }
               choice output-tags {
                 case actual-tag {
                   container probe-results {
                     uses probe-results-block;
                   }
                 }
               }
             }
           }
         }
       }
     }
   }
   rpc get-history-results {
     description "Show history results";
     junos:command "show services rpm history-results";
     input {
       leaf verbosity_level {
         junos:cli-feature "nokeyword";
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       choice output-tags {
         case actual-tag {
           container history-results {
             uses history-results-block;
           }
         }
         case multichassis-tag {
           container multi-routing-engine-results {
             list multi-routing-engine-item {
               leaf re-name {
                 type string;
               }
               choice output-tags {
                 case actual-tag {
                   container history-results {
                     uses history-results-block;
                   }
                 }
               }
             }
           }
         }
       }
     }
   }
   rpc get-active-servers {
     description "Show configured servers";
     junos:command "show services rpm active-servers";
     output {
       choice output-tags {
         case actual-tag {
           container active-servers {
             uses active-servers-block;
           }
         }
         case multichassis-tag {
           container multi-routing-engine-results {
             list multi-routing-engine-item {
               leaf re-name {
                 type string;
               }
               choice output-tags {
                 case actual-tag {
                   container active-servers {
                     uses active-servers-block;
                   }
                 }
               }
             }
           }
         }
       }
     }
   }
   rpc get-service-mss-sessions-information {
     description "Show mobile subscriber data sessions";
     junos:command "show services mobile sessions";
     input {
       leaf imsi {
         description "IMSI of subscriber";
         type string {
           length "5 .. 15";
         }
       }
     }
     output {
       choice output-tags {
         case output-tag {
           leaf output {
             type string;
           }
         }
         case actual-tag {
           anyxml service-mss-sessions-information;
         }
         case multichassis-tag {
           anyxml multi-routing-engine-results;
         }
       }
     }
   }
   rpc get-service-hcm-sessions-stats {
     description "Show hcm session statistics";
     junos:command "show services mobile hcm statistics";
     input {
       leaf imsi {
         description "IMSI of subscriber";
         type string {
           length "5 .. 15";
         }
         mandatory true;
       }
     }
     output {
       choice output-tags {
         case output-tag {
           leaf output {
             type string;
           }
         }
         case actual-tag {
           anyxml service-hcm-sessions-stats;
         }
         case multichassis-tag {
           anyxml multi-routing-engine-results;
         }
       }
     }
   }
   rpc get-service-tdf-sessions-information {
     description "Show traffic-detection-function subscriber data sessions";
     junos:command "show services traffic-detection-function sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output-tags {
         case output-tag {
           leaf output {
             type string;
           }
         }
         case actual-tag {
           anyxml service-tdf-sessions-information;
         }
         case multichassis-tag {
           anyxml multi-routing-engine-results;
         }
       }
     }
   }
   rpc get-service-tdf-hcm-sessions-stats {
     description "Show hcm session statistics";
     junos:command "show services traffic-detection-function hcm statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output-tags {
         case output-tag {
           leaf output {
             type string;
           }
         }
         case actual-tag {
           anyxml service-tdf-hcm-sessions-stats;
         }
         case multichassis-tag {
           anyxml multi-routing-engine-results;
         }
       }
     }
   }
   rpc get-global-pcp-statistics-information {
     description "Show global PCP statistics";
     junos:command "show services pcp statistics";
     input {
       leaf interface {
         description "Name of adaptive services interface";
         type string;
       }
       leaf level {
         junos:cli-feature "nokeyword";
         type enumeration {
           enum "protocol" {
             description "Display PCP protocol statistics";
           }
         }
       }
     }
     output {
       choice output-tags {
         case output-tag {
           leaf output {
             type string;
           }
         }
         case actual-tag {
           anyxml global-pcp-statistics-information;
         }
         case multichassis-tag {
           anyxml multi-routing-engine-results;
         }
       }
     }
   }
   rpc get-traffic-load-balance-statistics {
     description "Traffic load balance statistics";
     junos:command "show services traffic-load-balance statistics";
     input {
       leaf verbose {
         junos:cli-feature "nokeyword";
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
     output {
       choice output-tags {
         case output-tag {
           leaf output {
             type string;
           }
         }
         case actual-tag {
           anyxml service-traffic-load-balance-statistics;
         }
         case multichassis-tag {
           anyxml multi-routing-engine-results;
         }
       }
     }
   }
   rpc get-flb-statistics {
     description "FLB  statistics";
     junos:command "show services traffic-load-balance flb-statistics";
     input {
       leaf all {
         description "All flb instances";
         type empty;
       }
     }
     output {
       choice output-tags {
         case output-tag {
           leaf output {
             type string;
           }
         }
         case actual-tag {
           anyxml flb-statistics;
         }
         case multichassis-tag {
           anyxml multi-routing-engine-results;
         }
       }
     }
   }
   rpc traffic-load-balance-commit-status {
     description "Display commit status";
     junos:command "show services traffic-load-balance commit-status";
     output {
       choice output-tags {
         case actual-tag {
           container tdir-commit-status {
             uses tdir-commit-status-block;
           }
         }
         case multichassis-tag {
           container multi-routing-engine-results {
             list multi-routing-engine-item {
               leaf re-name {
                 type string;
               }
               choice output-tags {
                 case actual-tag {
                   container tdir-commit-status {
                     uses tdir-commit-status-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ift-global-information-block {
     container ift-global {
       leaf device-id {
         type uint32;
         description
           "Unique device identifier";
       }
       leaf meta-data-stack-length {
         type uint32;
         description
           "Maximum length of the meta-data";
       }
       leaf hop-limit {
         type uint32;
         description
           "Maximum hop limit";
       }
       leaf flow-type {
         type string;
         description
           "Traffic flow type";
       }
       leaf mode {
         type string;
         description
           "IFA mode type - live or probe";
       }
       leaf no-ipv6-address-match {
         type uint32;
         description
           "IPV6 address match allowed or not";
       }
       leaf clock-source {
         type string;
         description
           "Clock source for timestamping";
       }
     }
   }
   grouping ift-profile-information-block {
     list ift-profile {
       leaf profile-name {
         type string;
         description
           "Profile name";
       }
       leaf sample-rate {
         type uint32;
         description
           "Ratio of packets to be sampled (1 out of N)";
       }
       container collector-info {
         leaf source-address {
           type string;
           description
             "Source address";
         }
         leaf destination-address {
           type string;
           description
             "Destination address";
         }
         leaf destination-port {
           type int32;
           description
             "Destination port";
         }
         leaf maximum-clip-length {
           type int32;
           description
             "Clip length of data packet";
         }
         leaf mtu {
           type int32;
           description
             "MTU of export packets";
         }
       }
     }
   }
   grouping ift-stats-information-block {
     container ift-stats {
       leaf init-packets {
         type uint64;
         description
           "IFA initator statistics";
       }
       leaf transit-packets {
         type uint64;
         description
           "IFA transit statistics";
       }
       leaf terminate-rx-packets {
         type uint64;
         description
           "IFA termination rx statistics";
       }
       leaf terminate-tx-packets {
         type uint64;
         description
           "IFA termination tx statistics";
       }
       leaf terminate-tx-records {
         type uint64;
         description
           "IFA termination tx records";
       }
     }
   }
   grouping fips-pic-status-information-block {
     list fips-pic-status {
       leaf fpc-slot {
         type int32;
         description
           "FPC slot";
       }
       leaf pic-slot {
         type int32;
         description
           "PIC slot";
       }
       leaf serial-number {
         type string;
         description
           "PIC serial number";
       }
       leaf authorization-status {
         type string;
         description
           "PIC authorization status";
       }
     }
   }
   grouping lrf-statistics-summary-block {
     list lrf-statistics {
       description
         "LRF statistics";
       leaf interface-name {
         type string;
         description
           "Name of the adaptive services interface";
       }
       leaf flow-packets {
         type int32;
         description
           "Flow packets";
       }
       leaf flow-bytes {
         type int32;
         description
           "Flow bytes";
       }
       leaf active-flows {
         type int32;
         description
           "Active flows";
       }
       leaf total-flows {
         type int32;
         description
           "Total flows";
       }
     }
   }
   grouping lrf-collector-statistics-summary-block {
     list lrf-collector-statistics {
       description
         "LRF collector statistics";
       leaf interface-name {
         type string;
         description
           "Name of the adaptive services interface";
       }
       leaf tmpl-reg {
         type int32;
         description
           "Templates registered";
       }
       leaf tmpl-reg-failures {
         type int32;
         description
           "Template registration failures";
       }
       leaf tmpl-active {
         type int32;
         description
           "Templates active";
       }
       leaf sessions-received {
         type int32;
         description
           "Sessions received";
       }
       leaf sessions-ignored {
         type int32;
         description
           "Sessions ignored";
       }
       leaf records-logged {
         type int32;
         description
           "Records logged";
       }
       leaf rec-export {
         type int32;
         description
           "Records exported";
       }
       leaf rec-export-failures {
         type int32;
         description
           "Record export failures";
       }
       leaf rec-export-volume {
         type int32;
         description
           "Records exported for volume";
       }
       leaf rec-export-time {
         type int32;
         description
           "Records exported for time";
       }
       leaf rec-export-session-close {
         type int32;
         description
           "Records exported for session close";
       }
     }
   }
   grouping lrf-rule-statistics-summary-block {
     list lrf-rule-statistics {
       description
         "LRF rule statistics";
       leaf interface-name {
         type string;
         description
           "Name of the adaptive services interface";
       }
       leaf rule-name {
         type string;
         description
           "Rule name";
       }
       leaf rule-tmpl-name {
         type string;
         description
           "Template name";
       }
       leaf rule-tmpl-reg {
         type int32;
         description
           "Templates registered";
       }
       leaf rule-tmpl-reg-failures {
         type int32;
         description
           "Template registration failures";
       }
       leaf rule-coll-name {
         type string;
         description
           "Collector name";
       }
       leaf rule-sessions-received {
         type int32;
         description
           "Sessions received";
       }
       leaf rule-sessions-ignored {
         type int32;
         description
           "Sessions ignored";
       }
       leaf rule-sessions-logged {
         type int32;
         description
           "Sessions logged";
       }
       leaf rule-rec-export {
         type int32;
         description
           "Records exported";
       }
       leaf rule-rec-export-failures {
         type int32;
         description
           "Record export failures";
       }
       leaf rule-rec-export-volume {
         type int32;
         description
           "Records exported for volume";
       }
       leaf rule-rec-export-time {
         type int32;
         description
           "Records exported for time";
       }
       leaf rule-rec-export-session-close {
         type int32;
         description
           "Records exported for session close";
       }
     }
   }
   grouping lrf-template-block {
     leaf-list export-field {
       type string;
     }
     leaf-list export-field-id {
       type int32;
     }
     leaf-list export-field-len {
       type int32;
     }
     leaf-list export-field-vendor {
       type string;
     }
   }
   grouping analytics-agent-information-block {
     list analytics-service-agent-information {
       leaf analytics-service-agent-name {
         type string;
         description
           "Service agent ID";
       }
       leaf analytics-service-agent-output-plugin-count {
         type int32;
         description
           "Number of output plugins configured";
       }
       leaf analytics-service-agent-input-plugin-count {
         type int32;
         description
           "Number of input plugins configured";
       }
       leaf analytics-service-agent-process-id {
         type int32;
         description
           "Service agent process id(PID)";
       }
       leaf analytics-service-agent-input-plugins {
         type string;
         description
           "Service agent input plugin list";
       }
       leaf analytics-service-agent-output-plugins {
         type string;
         description
           "Service agent output plugin list";
       }
     }
     container analytics-controller-information {
       leaf analytics-controller-process-id {
         type int32;
         description
           "Analytics agent process id(PID)";
       }
       leaf analytics-controller-conf-file {
         type string;
         description
           "Analytics agent configuration file";
       }
       leaf analytics-controller-log-file {
         type string;
         description
           "Analytics agent log file";
       }
       leaf analytics-controller-service-agent-count {
         type int32;
         description
           "Number of service agents";
       }
     }
   }
   grouping services-analytics-dialout-statistics-block {
     list session {
       key "streaming-server export-profile";
       leaf streaming-server {
         type string;
       }
       leaf export-profile {
         type string;
       }
       leaf source-address {
         type string;
       }
       leaf destination-address {
         type string;
       }
       leaf dialout-type {
         type string;
       }
       leaf session-type {
         type string;
       }
       leaf packets-sent {
         type int32;
       }
       leaf session-duration {
         type string;
       }
       leaf session-begin-time {
         type string;
       }
     }
   }
   grouping probe-results-block {
     list probe-results-terse {
       leaf test-name {
         type string;
         description
           "Name of test";
       }
       leaf destination-interface {
         type string;
         description
           "Name of output interface for probes";
       }
       leaf target-address {
         type string;
         description
           "Target address of test";
       }
       leaf last-status {
         type string;
         description
           "Status";
       }
       leaf last-status-changed {
         type string;
         description
           "Last time when status updated";
       }
       leaf twl-local-link {
         type string;
         description
           "Name of local link for TWAMP-Light probes";
       }
       leaf last-probe-status {
         type string;
         description
           "Probe status";
       }
     }
     list probe-test-results {
       leaf owner {
         type string;
         description
           "Test owner name";
       }
       leaf test-name {
         type string;
         description
           "Name of test";
       }
       leaf target-address {
         type string;
         description
           "Target address of test";
       }
       leaf target-url {
         type string;
         description
           "Target URL of test";
       }
       leaf target-fqdn {
         type string;
         description
           "Target FQDN of test";
       }
       leaf source-address {
         type string;
         description
           "Source address of test";
       }
       leaf probe-type {
         type string;
         description
           "Name of the probe";
       }
       leaf icmp-id {
         type uint32;
         description
           "Icmp id for icmp-ping probes";
       }
       leaf test-size {
         type uint32;
         description
           "Number of probes in test";
       }
       leaf server-status {
         type string;
         description
           "TWAMP server is Connected or Not";
       }
       leaf twamp-client-retries {
         type uint32;
         description
           "Retries to connect TWAMP server at every test-interval";
       }
       leaf server-address {
         type jt:ipaddr;
         description
           "Server address";
       }
       leaf server-port {
         type uint32;
         description
           "Server port";
       }
       leaf client-address {
         type jt:ipaddr;
         description
           "Client address";
       }
       leaf client-port {
         type uint32;
         description
           "Client port";
       }
       leaf reflector-address {
         type jt:ipaddr;
         description
           "Reflector address";
       }
       leaf reflector-port {
         type uint32;
         description
           "Reflector port";
       }
       leaf sender-address {
         type jt:ipaddr;
         description
           "Sender address";
       }
       leaf sender-port {
         type uint32;
         description
           "Sender port";
       }
       leaf routing-instance-name {
         type string;
         description
           "Routing Instance Name";
       }
       leaf destination-interface {
         type string;
         description
           "Name of output interface for probes";
       }
       leaf twl-local-link {
         type string;
         description
           "Name of local link for TWAMP-Light probes";
       }
       leaf http-status {
         type uint32;
         description
           "HTTP Status Code";
       }
       leaf loss-thresh-total {
         type uint32;
         description
           "Maximum number of all lost probes";
       }
       leaf loss-thresh-succ {
         type uint32;
         description
           "Maximum number of successive lost probes";
       }
       leaf delay-thresh {
         type uint32;
         description
           "Maximum delay threshold";
       }
       leaf jitter-thresh {
         type uint32;
         description
           "Maximum jitter threshold";
       }
       leaf stddev-thresh {
         type uint32;
         description
           "Maximum standard deviation threshold";
       }
       leaf egress-thresh {
         type uint32;
         description
           "Maximum egress delay threshold";
       }
       leaf egress-jitter-thresh {
         type uint32;
         description
           "Maximum egress jitter threshold";
       }
       leaf egress-stddev-thresh {
         type uint32;
         description
           "Maximum egress standard deviation threshold";
       }
       leaf ingress-thresh {
         type uint32;
         description
           "Maximum ingress delay threshold";
       }
       leaf ingress-jitter-thresh {
         type uint32;
         description
           "Maximum ingress jitter threshold";
       }
       leaf ingress-stddev-thresh {
         type uint32;
         description
           "Maximum ingress standard deviation threshold";
       }
       container probe-single-results {
         leaf probe-sent-time {
           type string;
           description
             "Time at which probe was sent";
         }
         leaf probe-status {
           type string;
           description
             "Operation response status from probes";
         }
         leaf probe-time {
           type string;
           description
             "Time at which probe response was received or timed out";
         }
         leaf hardware-timestamp-status {
           type string;
           description
             "Use of hardware timestamps in probes";
         }
         leaf http-status {
           type uint32;
           description
             "HTTP Status Code";
         }
         leaf rtt {
           type uint32;
           description
             "Round trip time of probes";
         }
         leaf ingress {
           type uint32;
           description
             "Ingress trip time of probes";
         }
         leaf egress {
           type uint32;
           description
             "Egress trip time of probes";
         }
         leaf egress-jitter {
           type int32;
           description
             "Egress jitter of probes";
         }
         leaf ingress-jitter {
           type int32;
           description
             "Ingress jitter of probes";
         }
         leaf round-trip-jitter {
           type int32;
           description
             "Round trip jitter of probes";
         }
         leaf egress-interarrival-jitter {
           type int32;
           description
             "Egress interarrival jitter of probes";
         }
         leaf ingress-interarrival-jitter {
           type int32;
           description
             "Ingress interarrival jitter of probes";
         }
         leaf round-trip-interarrival-jitter {
           type int32;
           description
             "Round trip interarrival jitter of probes";
         }
         leaf owner {
           type string;
           description
             "Test owner name";
         }
         leaf test-name {
           type string;
           description
             "Name of test";
         }
       }
       container probe-test-current-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-last-test-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-moving-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-global-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-hwts-err-stats {
         leaf invalid-client-recv-ts-cntr {
           type uint32;
           description
             "Client recv timestamp less than Client send timestamp";
         }
         leaf invalid-client-nots-cntr {
           type uint32;
           description
             "Client timestamps (T1, T4) are marked as deadbeef";
         }
         leaf invalid-server-send-ts-cntr {
           type uint32;
           description
             "Server send timestamp less than Server recv timestamp";
         }
         leaf invalid-server-spent-time-cntr {
           type uint32;
           description
             "Server side spent time greater than RTT";
         }
         leaf pkt-rcvd-after-timeout-cntr {
           type uint32;
           description
             "RTT is greater than probe-interval";
         }
       }
     }
   }
   grouping history-results-block {
     list history-test-results {
       leaf owner {
         type string;
         description
           "Test owner name";
       }
       leaf test-name {
         type string;
         description
           "Name of test";
       }
       leaf probe-type {
         type string;
         description
           "Name of the probe";
       }
       leaf icmp-id {
         type uint32;
         description
           "Icmp id for icmp-ping probes";
       }
       leaf target-address {
         type string;
         description
           "Target address of test";
       }
       leaf target-url {
         type string;
         description
           "Target URL of test";
       }
       leaf target-fqdn {
         type string;
         description
           "Target FQDN of test";
       }
       leaf source-address {
         type string;
         description
           "Source address of test";
       }
       leaf destination-interface {
         type string;
         description
           "Name of output interface for probes";
       }
       leaf twl-local-link {
         type string;
         description
           "Name of local link for TWAMP-Light probes";
       }
       leaf loss-thresh-total {
         type uint32;
         description
           "Maximum number of all lost probes";
       }
       leaf loss-thresh-succ {
         type uint32;
         description
           "Maximum number of successive lost probes";
       }
       leaf delay-thresh {
         type uint32;
         description
           "Maximum delay threshold";
       }
       leaf jitter-thresh {
         type uint32;
         description
           "Maximum jitter threshold";
       }
       leaf stddev-thresh {
         type uint32;
         description
           "Maximum standard deviation threshold";
       }
       leaf egress-thresh {
         type uint32;
         description
           "Maximum egress delay threshold";
       }
       leaf egress-jitter-thresh {
         type uint32;
         description
           "Maximum egress jitter threshold";
       }
       leaf ingress-thresh {
         type uint32;
         description
           "Maximum ingress delay threshold";
       }
       leaf ingress-jitter-thresh {
         type uint32;
         description
           "Maximum ingress jitter threshold";
       }
       container probe-single-results {
         leaf probe-sent-time {
           type string;
           description
             "Time at which probe was sent";
         }
         leaf probe-status {
           type string;
           description
             "Operation response status from probes";
         }
         leaf probe-time {
           type string;
           description
             "Time at which probe response was received or timed out";
         }
         leaf hardware-timestamp-status {
           type string;
           description
             "Use of hardware timestamps in probes";
         }
         leaf http-status {
           type uint32;
           description
             "HTTP Status Code";
         }
         leaf rtt {
           type uint32;
           description
             "Round trip time of probes";
         }
         leaf ingress {
           type uint32;
           description
             "Ingress trip time of probes";
         }
         leaf egress {
           type uint32;
           description
             "Egress trip time of probes";
         }
         leaf egress-jitter {
           type int32;
           description
             "Egress jitter of probes";
         }
         leaf ingress-jitter {
           type int32;
           description
             "Ingress jitter of probes";
         }
         leaf round-trip-jitter {
           type int32;
           description
             "Round trip jitter of probes";
         }
         leaf egress-interarrival-jitter {
           type int32;
           description
             "Egress interarrival jitter of probes";
         }
         leaf ingress-interarrival-jitter {
           type int32;
           description
             "Ingress interarrival jitter of probes";
         }
         leaf round-trip-interarrival-jitter {
           type int32;
           description
             "Round trip interarrival jitter of probes";
         }
         leaf owner {
           type string;
           description
             "Test owner name";
         }
         leaf test-name {
           type string;
           description
             "Name of test";
         }
       }
       container probe-test-current-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
     }
   }
   grouping active-servers-block {
     list configured-servers {
       leaf protocol {
         type string;
         description
           "Protocol";
       }
       leaf port {
         type uint32;
         description
           "Port";
       }
       leaf destination-interface {
         type string;
         description
           "Name of output interface for probes";
       }
     }
   }
   grouping tdir-commit-status-block {
     leaf tdir-config-status {
       type string;
       description
         "Prints config status of previous commit";
     }
   }
 }
