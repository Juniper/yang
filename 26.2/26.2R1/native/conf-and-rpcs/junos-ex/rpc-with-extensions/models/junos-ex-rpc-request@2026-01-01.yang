/*
 * Copyright (c) 2026 Juniper Networks, Inc.
 * All rights reserved.
 */
 module junos-ex-rpc-request {
   namespace "http://yang.juniper.net/junos-ex/rpc/request";

   prefix request;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for request command(s)";

   revision 2026-01-01 {
     description "Junos: 26.2R1.7";
   }

   rpc resize-configuraion-database {
     description "Resize the configuration database";
     junos:command "request system configuration database resize";
     input {
       uses command-forwarding;
       leaf force {
         description "Resize the configuration database even if modified";
         type empty;
       }
     }
     output {
       choice output-tags {
         case output-tag {
           leaf output {
             type string;
           }
         }
         case multichassis-tag {
           anyxml multi-routing-engine-results;
         }
       }
     }
   }
   rpc request-save-rescue-configuration {
     description "Save committed configuration as rescue configuration";
     junos:command "request system configuration rescue save";
     output {
       choice output-tags {
         case actual-tag {
           container rescue-management-results {
             uses rescue-management-results-block;
           }
         }
         case multichassis-tag {
           container multi-routing-engine-results {
             list multi-routing-engine-item {
               leaf re-name {
                 type string;
               }
               choice output-tags {
                 case actual-tag {
                   container rescue-management-results {
                     uses rescue-management-results-block;
                   }
                 }
               }
             }
           }
         }
       }
     }
   }
   rpc request-delete-rescue-configuration {
     description "Delete the rescue configuration";
     junos:command "request system configuration rescue delete";
     output {
       choice output-tags {
         case actual-tag {
           container rescue-management-results {
             uses rescue-management-results-block;
           }
         }
         case multichassis-tag {
           container multi-routing-engine-results {
             list multi-routing-engine-item {
               leaf re-name {
                 type string;
               }
               choice output-tags {
                 case actual-tag {
                   container rescue-management-results {
                     uses rescue-management-results-block;
                   }
                 }
               }
             }
           }
         }
       }
     }
   }
   rpc request-commit-server-cleanup {
     description "Commit queue clean up operations";
     junos:command "request system commit server queue cleanup";
     input {
       choice queue-selector {
         case id {
           leaf id {
             description "Clean up queue id";
             type union {
               type uint32;
               type string {
                 pattern "<.*>|$.*";
               }
             }
           }
         }
         case job-status {
           leaf job-status {
             description "Clean up all entries with specified status";
             type enumeration {
               enum "error" {
                 description "Remove jobs that had errors";
               }
               enum "pending" {
                 description "Remove jobs that are pending";
               }
               enum "success" {
                 description "Remove jobs that succeeded";
               }
             }
           }
         }
       }
     }
     output {
       choice output-tags {
         case actual-tag {
           container commit-server-delete-results {
             uses commit-server-delete-results-block;
           }
         }
         case multichassis-tag {
           container multi-routing-engine-results {
             list multi-routing-engine-item {
               leaf re-name {
                 type string;
               }
               choice output-tags {
                 case actual-tag {
                   container commit-server-delete-results {
                     uses commit-server-delete-results-block;
                   }
                 }
               }
             }
           }
         }
       }
     }
   }
   rpc request-commit-server-pause {
     description "Pause the commit server";
     junos:command "request system commit server pause";
     output {
       choice output-tags {
         case actual-tag {
           container commit-server-operation {
             uses commit-server-operation-block;
           }
         }
         case multichassis-tag {
           container multi-routing-engine-results {
             list multi-routing-engine-item {
               leaf re-name {
                 type string;
               }
               choice output-tags {
                 case actual-tag {
                   container commit-server-operation {
                     uses commit-server-operation-block;
                   }
                 }
               }
             }
           }
         }
       }
     }
   }
   rpc request-commit-server-start {
     description "Start the commit server";
     junos:command "request system commit server start";
     output {
       choice output-tags {
         case actual-tag {
           container commit-server-operation {
             uses commit-server-operation-block;
           }
         }
         case multichassis-tag {
           container multi-routing-engine-results {
             list multi-routing-engine-item {
               leaf re-name {
                 type string;
               }
               choice output-tags {
                 case actual-tag {
                   container commit-server-operation {
                     uses commit-server-operation-block;
                   }
                 }
               }
             }
           }
         }
       }
     }
   }
   rpc request-delta-exporter-initialize {
     description "Initialize delta exporter database";
     junos:command "request system commit delta-exporter initialize";
     output {
       choice output-tags {
         case output-tag {
           leaf output {
             type string;
           }
         }
         case multichassis-tag {
           anyxml multi-routing-engine-results;
         }
       }
     }
   }
   rpc request-yang-add {
     description "Add YANG module(s) and action/translation script(s)";
     junos:command "request system yang add";
     input {
       leaf package {
         description "Unique ID for future op - delete/update";
         type string;
         mandatory true;
       }
       leaf-list module {
         ordered-by user;
         description "YANG module(s) path";
         type jt:filename;
       }
       leaf-list action-script {
         ordered-by user;
         description "Action script path";
         type jt:filename;
       }
       leaf-list translation-script {
         ordered-by user;
         description "Translation script path";
         type jt:filename;
       }
       leaf-list deviation-module {
         ordered-by user;
         description "Deviation module path";
         type jt:filename;
       }
       leaf proxy-xml {
         description "XML proxy YANG module(s)";
         type empty;
       }
       leaf snmp {
         description "Add custom MIB in YANG format";
         type empty;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output-tags {
         case output-tag {
           leaf output {
             type string;
           }
         }
         case multichassis-tag {
           anyxml multi-routing-engine-results;
         }
       }
     }
   }
   rpc request-yang-delete {
     description "Remove YANG package";
     junos:command "request system yang delete";
     input {
       leaf package {
         description "ID to be removed";
         junos:cli-feature "nokeyword";
         type string;
         mandatory true;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output-tags {
         case output-tag {
           leaf output {
             type string;
           }
         }
         case multichassis-tag {
           anyxml multi-routing-engine-results;
         }
       }
     }
   }
   rpc request-yang-enable {
     description "Enable YANG package to JUNOS translation";
     junos:command "request system yang enable";
     input {
       leaf package {
         description "ID";
         junos:cli-feature "nokeyword";
         type string;
         mandatory true;
       }
     }
     output {
       choice output-tags {
         case output-tag {
           leaf output {
             type string;
           }
         }
         case multichassis-tag {
           anyxml multi-routing-engine-results;
         }
       }
     }
   }
   rpc request-yang-disable {
     description "Disable YANG package to JUNOS translation";
     junos:command "request system yang disable";
     input {
       leaf package {
         description "ID";
         junos:cli-feature "nokeyword";
         type string;
         mandatory true;
       }
     }
     output {
       choice output-tags {
         case output-tag {
           leaf output {
             type string;
           }
         }
         case multichassis-tag {
           anyxml multi-routing-engine-results;
         }
       }
     }
   }
   rpc request-yang-validate {
     description "Validate YANG module(s) and action/translation script(s)";
     junos:command "request system yang validate";
     input {
       leaf-list module {
         ordered-by user;
         description "Name of the YANG module to be validated";
         type jt:filename;
       }
       leaf-list translation-script {
         ordered-by user;
         description "Name of the translation-script to be validated";
         type jt:filename;
       }
       leaf-list action-script {
         ordered-by user;
         description "Name of the action-script to be validated";
         type jt:filename;
       }
       leaf proxy-xml {
         description "XML proxy YANG module";
         type empty;
       }
       leaf snmp {
         description "Validate custom MIB in YANG format";
         type empty;
       }
     }
     output {
       choice output-tags {
         case output-tag {
           leaf output {
             type string;
           }
         }
         case multichassis-tag {
           anyxml multi-routing-engine-results;
         }
       }
     }
   }
   rpc request-yang-update {
     description "Update YANG module(s) and action/translation script(s)";
     junos:command "request system yang update";
     input {
       leaf package {
         description "ID";
         junos:cli-feature "nokeyword";
         type string;
         mandatory true;
       }
       leaf-list module {
         ordered-by user;
         description "YANG module(s) path";
         type jt:filename;
       }
       leaf-list translation-script {
         ordered-by user;
         description "Translation script path";
         type jt:filename;
       }
       leaf-list deviation-module {
         ordered-by user;
         description "Deviation module path";
         type jt:filename;
       }
       leaf-list action-script {
         ordered-by user;
         description "Action script path";
         type jt:filename;
       }
       leaf proxy-xml {
         description "XML proxy YANG module(s)";
         type empty;
       }
       leaf snmp {
         description "Update custom MIBs in YANG format";
         type empty;
       }
     }
     output {
       choice output-tags {
         case output-tag {
           leaf output {
             type string;
           }
         }
         case multichassis-tag {
           anyxml multi-routing-engine-results;
         }
       }
     }
   }
   rpc request-logout-user {
     description "Forcibly end user's CLI login session";
     junos:command "request system logout";
     input {
       uses command-forwarding;
       leaf pid {
         description "Management process ID for user";
         type union {
           type uint32;
           type string {
             pattern "<.*>|$.*";
           }
         }
       }
       leaf all {
         description "Logout all sessions owned by user";
         type empty;
       }
       leaf user {
         description "Name of user";
         type string {
           junos:posix-pattern "^[[:alnum:]_]{1,}[.]{0,1}[[:alnum:]_-]{0,}[.]{0,1}[[:alnum:]_-]{0,}$";
           junos:pattern-message "Must contain characters (alphanumerics, underscores or hyphens) beginning with an alphanumeric or an underscore character.";
         }
       }
       leaf terminal {
         description "Terminal user is logged in to";
         type string {
           junos:posix-pattern "^[a-z/][0-9a-z/-]*$";
           junos:pattern-message "Must start with a letter followed by alphanumeric character";
         }
       }
     }
     output {
       choice output-tags {
         case actual-tag {
           container logout-user {
             uses logout-user-block;
           }
         }
         case multichassis-tag {
           container multi-routing-engine-results {
             list multi-routing-engine-item {
               leaf re-name {
                 type string;
               }
               choice output-tags {
                 case actual-tag {
                   container logout-user {
                     uses logout-user-block;
                   }
                 }
               }
             }
           }
         }
       }
     }
   }
   rpc request-json-configuration-conversion {
     description "Convert the given JSON configuration file as per Junos";
     junos:command "request system convert-json-configuration";
     input {
       leaf filename {
         description "Path to the input JSON configuration file";
         junos:cli-feature "nokeyword";
         type jt:filename;
         mandatory true;
       }
       leaf output-filename {
         description "Path to the output file";
         type string {
           junos:posix-pattern "![/ %]";
           junos:pattern-message "Must not contain \'/\', % or a space";
         }
         mandatory true;
       }
       leaf origin-schema {
         description "Specify the Yang schema origin";
         default "juniper";
         type string;
       }
     }
     output {
       choice output-tags {
         case output-tag {
           leaf output {
             type string;
           }
         }
         case multichassis-tag {
           anyxml multi-routing-engine-results;
         }
       }
     }
   }
   rpc generate-genstate-json-schema {
     description "Generate the Genstate JSON schema";
     junos:command "request system schema genstate-json generate";
     output {
       choice output-tags {
         case actual-tag {
           container genstate-json-schema-result {
             uses genstate-json-schema-result-block;
           }
         }
         case multichassis-tag {
           container multi-routing-engine-results {
             list multi-routing-engine-item {
               leaf re-name {
                 type string;
               }
               choice output-tags {
                 case actual-tag {
                   container genstate-json-schema-result {
                     uses genstate-json-schema-result-block;
                   }
                 }
               }
             }
           }
         }
       }
     }
   }
   rpc reload-event-scripts {
     description "Reload all existing event-scripts";
     junos:command "request system scripts event-scripts reload";
     output {
       choice output-tags {
         case output-tag {
           leaf output {
             type string;
           }
         }
         case actual-tag {
           anyxml event-scripts-reload;
         }
         case multichassis-tag {
           anyxml multi-routing-engine-results;
         }
       }
     }
   }
   rpc request-scripts-package-add {
     description "Add or upgrade jais package";
     junos:command "request system scripts add";
     input {
       leaf no-copy {
         description "Don't save copy of jais package file";
         type empty;
       }
       leaf unlink {
         description "Remove the package after successful installation";
         type empty;
       }
       leaf package-name {
         description "URL or pathname of package";
         junos:cli-feature "nokeyword";
         type jt:filename;
         mandatory true;
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case master {
           leaf master {
             description "Run command on master";
             type empty;
           }
         }
         case backup {
           leaf backup {
             description "Run command on backup";
             type empty;
           }
         }
       }
     }
     output {
       choice output-tags {
         case output-tag {
           leaf output {
             type string;
           }
         }
         case multichassis-tag {
           anyxml multi-routing-engine-results;
         }
       }
     }
   }
   rpc request-scripts-package-delete {
     description "Remove jais package";
     junos:command "request system scripts delete";
     input {
       uses command-forwarding;
     }
     output {
       choice output-tags {
         case output-tag {
           leaf output {
             type string;
           }
         }
         case multichassis-tag {
           anyxml multi-routing-engine-results;
         }
       }
     }
   }
   rpc request-scripts-package-rollback {
     description "Attempt to roll back to last jais package";
     junos:command "request system scripts rollback";
     input {
       uses command-forwarding;
     }
     output {
       choice output-tags {
         case output-tag {
           leaf output {
             type string;
           }
         }
         case multichassis-tag {
           anyxml multi-routing-engine-results;
         }
       }
     }
   }
   rpc request-script-refresh-from {
     description "Refresh script from a given base URL";
     junos:command "request system scripts refresh-from";
     input {
       leaf type {
         junos:cli-feature "nokeyword";
         type enumeration {
           enum "commit" {
             description "Refresh commit script from a given base URL";
           }
           enum "op" {
             description "Refresh op script from a given base URL";
           }
           enum "event" {
             description "Refresh event script from a given base URL";
           }
           enum "snmp" {
             description "Refresh snmp script from a given base URL";
           }
           enum "extension-service" {
             description "Refresh extension-services app from a given base URL";
           }
         }
         mandatory true;
       }
       leaf file {
         description "Local script file name";
         type string {
           junos:posix-pattern "!/";
           junos:pattern-message "File name cannot contain a \'/\'";
         }
         mandatory true;
       }
       leaf url {
         description "URL from where the content will be retrieved";
         type string;
         mandatory true;
       }
       leaf routing-instance {
         description "Specify the routing-instance name";
         type string;
       }
       leaf cert-file {
         description "Specify the ca certificate file name";
         type string;
       }
       leaf sync {
         description "Refresh script and synchronize with other RE";
         type empty;
       }
     }
     output {
       choice output-tags {
         case output-tag {
           leaf output {
             type string;
           }
         }
         case multichassis-tag {
           anyxml multi-routing-engine-results;
         }
       }
     }
   }
   rpc request-scripts-synchronize {
     description "Push the scripts to other RE";
     junos:command "request system scripts synchronize";
     input {
       leaf type {
         junos:cli-feature "nokeyword";
         type enumeration {
           enum "commit" {
             description "Push commit script to other RE";
           }
           enum "op" {
             description "Push op script to other RE";
           }
           enum "event" {
             description "Push event script to other RE";
           }
           enum "snmp" {
             description "Push snmp script to other RE";
           }
           enum "jet" {
             description "Push jet app to other RE";
           }
           enum "lib" {
             description "Push lib script to other RE";
           }
           enum "all" {
             description "Push all the scripts to other RE";
           }
         }
         mandatory true;
       }
       leaf file {
         description "Local script file name";
         type string;
       }
       leaf newer-than {
         description "Push script to other RE if newer than this time (YYYY-MM-DD.HH:MM:SS)";
         type jt:time;
       }
     }
     output {
       choice output-tags {
         case output-tag {
           leaf output {
             type string;
           }
         }
         case multichassis-tag {
           anyxml multi-routing-engine-results;
         }
       }
     }
   }
   rpc request-package-add {
     description "Add extension or upgrade package";
     junos:command "request system software add";
     input {
       leaf force {
         description "Force addition of package (ignore warnings)";
         type empty;
       }
       leaf reboot {
         description "Reboot system after adding package";
         type empty;
       }
       choice firmware-option {
         case update-firmware {
           leaf update-firmware {
             description "Synchronize device to firmware versions in the package";
             type empty;
           }
         }
       }
       leaf force-host {
         description "Force addition of host os package (ignore version check)";
         type empty;
       }
       leaf on-primary {
         description "Install image on primary partition while booted on secondary partition";
         type empty;
       }
       leaf no-auto-reboot {
         description "Do not reboot system automatically after adding package";
         type empty;
       }
       leaf delay-restart {
         description "Don't restart processes";
         type empty;
       }
       leaf no-copy {
         description "Don't save copies of package files";
         type empty;
       }
       choice validate_choice {
         case no-validate {
           leaf no-validate {
             description "Don't check compatibility with current configuration";
             type empty;
           }
         }
         case validate {
           leaf validate {
             description "Check compatibility with current configuration";
             type empty;
           }
         }
         case validate-on-host {
           leaf validate-on-host {
             description "Remote host or user@host for configuration validation";
             type string;
           }
         }
         case validate-on-routing-engine {
           leaf validate-on-routing-engine {
             description "Routing engine for configuration validation";
             type string;
           }
         }
       }
       leaf best-effort-load {
         description "Load succeeds if at least one statement is valid";
         type empty;
       }
       leaf unlink {
         description "Remove the package after successful installation";
         type empty;
       }
       choice re-choice {
         case re0 {
           leaf re0 {
             description "Install package on RE0";
             type empty;
           }
         }
         case re1 {
           leaf re1 {
             description "Install package on RE1";
             type empty;
           }
         }
         case both-routing-engines {
           leaf both-routing-engines {
             description "Simultaneous upgrade on both the RE's";
             type empty;
           }
         }
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case service-node {
         }
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
       leaf routing-instance {
         description "Specify the routing-instance name";
         type string;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
         case version {
           leaf version {
             description "Version of satellite package";
             type string;
           }
         }
       }
     }
     output {
       choice output-tags {
         case output-tag {
           leaf output {
             type string;
           }
         }
         case multichassis-tag {
           anyxml multi-routing-engine-results;
         }
       }
     }
   }
   rpc request-package-latest-status {
     description "Status of package installation";
     junos:command "request system software status";
     output {
       choice output-tags {
         case actual-tag {
           container package-status {
             uses package-status-block;
           }
         }
         case multichassis-tag {
           container multi-routing-engine-results {
             list multi-routing-engine-item {
               leaf re-name {
                 type string;
               }
               choice output-tags {
                 case actual-tag {
                   container package-status {
                     uses package-status-block;
                   }
                 }
               }
             }
           }
         }
       }
     }
   }
   rpc abort-in-service-upgrade {
     description "Abort in-service software upgrade";
     junos:command "request system software abort in-service-upgrade";
     output {
       choice output-tags {
         case output-tag {
           leaf output {
             type string;
           }
         }
         case multichassis-tag {
           anyxml multi-routing-engine-results;
         }
       }
     }
   }
   rpc request-package-in-service-upgrade {
     description "In-service software upgrade";
     junos:command "request system software in-service-upgrade";
     input {
       leaf reboot {
         description "Reboot system after adding package";
         type empty;
       }
       choice package-options {
         case set {
         }
         case package-name {
           leaf package-name {
             description "URL or pathname of package";
             junos:cli-feature "nokeyword";
             type jt:filename;
           }
         }
       }
       leaf no-old-master-upgrade {
         description "Don't upgrade the old master after switchover";
         type empty;
       }
       leaf no-copy {
         description "Don't save copies of package files";
         type empty;
       }
       leaf unlink {
         description "Remove the package after successful installation";
         type empty;
       }
       leaf no-validate {
         description "Don't check compatibility with current configuration";
         type empty;
       }
       choice issu_internal {
       }
     }
     output {
       choice output-tags {
         case output-tag {
           leaf output {
             type string;
           }
         }
         case multichassis-tag {
           anyxml multi-routing-engine-results;
         }
       }
     }
   }
   rpc request-package-nonstop-upgrade {
     description "Nonstop software upgrade";
     junos:command "request system software nonstop-upgrade";
     input {
       choice firmware-option {
         case update-firmware {
           leaf update-firmware {
             description "Synchronize device to firmware versions in the package";
             type empty;
           }
         }
       }
       leaf force-host {
         description "Force addition of host os package (ignore version check)";
         type empty;
       }
       leaf no-auto-recovery {
         description "Will not recover in case of NSSU failure";
         type empty;
       }
       leaf reboot {
         description "Reboot system after adding package";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf no-old-master-upgrade {
         description "Don't upgrade the old master after switchover";
         type empty;
       }
       leaf no-copy {
         description "Don't save copies of package files";
         status deprecated;
         type empty;
       }
       leaf unlink {
         description "Remove the package after successful installation";
         status deprecated;
         type empty;
       }
     }
     output {
       choice output-tags {
         case output-tag {
           leaf output {
             type string;
           }
         }
         case multichassis-tag {
           anyxml multi-routing-engine-results;
         }
       }
     }
   }
   rpc request-package-delete {
     description "Remove extension or upgrade package";
     junos:command "request system software delete";
     input {
       leaf archived {
         description "Removing of all archived software versions except current and rollback";
         type empty;
       }
       leaf force {
         description "Force removal of package (ignore warnings)";
         type empty;
       }
       choice package-options {
         case set {
         }
         case package-name {
           leaf package-name {
             description "Name of package";
             junos:cli-feature "nokeyword";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
       choice re-choice {
         case re0 {
           leaf re0 {
             description "Delete package on RE0";
             type empty;
           }
         }
         case re1 {
           leaf re1 {
             description "Delete package on RE1";
             type empty;
           }
         }
       }
       choice chassis {
         case scc {
           leaf scc {
             description "Delete package on SCC";
             type empty;
           }
         }
         case lcc {
           leaf lcc {
             description "Delete package on an LCC";
             type union {
               type string {
                 pattern "<.*>|$.*";
               }
               type uint32 {
                 range "0 .. 3";
               }
             }
           }
         }
         case sfc {
           leaf sfc {
             description "Delete package on SFC";
             type empty;
           }
         }
         case member {
           leaf member {
             description "Delete package on VC Member";
             type union {
               type string {
                 pattern "<.*>|$.*";
               }
               type uint32;
             }
           }
         }
         case dont-forward {
           leaf dont-forward {
             type empty;
           }
         }
       }
     }
     output {
       choice output-tags {
         case output-tag {
           leaf output {
             type string;
           }
         }
         case multichassis-tag {
           anyxml multi-routing-engine-results;
         }
       }
     }
   }
   rpc request-package-rollback {
     description "Attempt to roll back to previous set of packages";
     junos:command "request system software rollback";
     input {
       uses command-forwarding;
       choice satellite-arg {
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
       leaf reboot {
         description "Reboot system after rollback";
         type empty;
       }
     }
     output {
       choice output-tags {
         case output-tag {
           leaf output {
             type string;
           }
         }
         case multichassis-tag {
           anyxml multi-routing-engine-results;
         }
       }
     }
   }
   rpc request-package-validate {
     description "Verify package compatibility with current configuration";
     junos:command "request system software validate";
     input {
       choice package-options {
         case set {
         }
         case package-name {
           leaf package-name {
             description "URL or pathname of package";
             junos:cli-feature "nokeyword";
             type jt:filename;
           }
         }
       }
       choice chassis {
         case scc {
           leaf scc {
             description "Validate package on SCC";
             type empty;
           }
         }
         case lcc {
           leaf lcc {
             description "Validate package on an LCC";
             type union {
               type string {
                 pattern "<.*>|$.*";
               }
               type uint32;
             }
           }
         }
         case sfc {
           leaf sfc {
             description "Validate package on SFC";
             type empty;
           }
         }
         case member {
           leaf member {
             description "Validate package on member";
             type union {
               type string {
                 pattern "<.*>|$.*";
               }
               type uint32;
             }
           }
         }
         case dont-forward {
           leaf dont-forward {
             type empty;
           }
         }
       }
     }
     output {
       choice output-tags {
         case output-tag {
           leaf output {
             type string;
           }
         }
         case multichassis-tag {
           anyxml multi-routing-engine-results;
         }
       }
     }
   }
   rpc check-in-service-upgrade {
     description "Check in-service software upgrade";
     junos:command "request system software validate in-service-upgrade";
     input {
       choice package-options {
         case set {
         }
         case package-name {
           leaf package-name {
             description "URL or pathname of package";
             junos:cli-feature "nokeyword";
             type jt:filename;
           }
         }
       }
     }
     output {
       choice output-tags {
         case output-tag {
           leaf output {
             type string;
           }
         }
         case multichassis-tag {
           anyxml multi-routing-engine-results;
         }
       }
     }
   }
   rpc request-license-add {
     description "Add license keys from file, local or from server";
     junos:command "request system license add";
     input {
       leaf filename {
         description "Filename (URL, local, remote, or floppy)";
         junos:cli-feature "nokeyword";
         type string;
       }
       leaf key-data {
         description "License key data";
         type string;
       }
     }
     output {
       choice output-tags {
         case actual-tag {
           container add-license-results {
             uses add-license-results-block;
           }
         }
         case multichassis-tag {
           container multi-routing-engine-results {
             list multi-routing-engine-item {
               leaf re-name {
                 type string;
               }
               choice output-tags {
                 case actual-tag {
                   container add-license-results {
                     uses add-license-results-block;
                   }
                 }
               }
             }
           }
         }
       }
     }
   }
   rpc request-license-delete {
     description "Delete license keys";
     junos:command "request system license delete";
     input {
       choice delete-choice {
         case all {
           leaf all {
             description "Delete all license keys";
             type empty;
           }
         }
         case license-identifier {
           leaf license-identifier {
             description "Identifier of installed license key";
             junos:cli-feature "nokeyword";
             type string;
           }
         }
         case license-identifier-list {
           leaf-list license-identifier-list {
             ordered-by user;
             description "Identifier of installed license key";
             type string;
           }
         }
       }
     }
     output {
       choice output-tags {
         case output-tag {
           leaf output {
             type string;
           }
         }
         case multichassis-tag {
           anyxml multi-routing-engine-results;
         }
       }
     }
   }
   rpc request-license-save {
     description "Save license keys to file, local or to server";
     junos:command "request system license save";
     input {
       leaf filename {
         description "Filename (URL, local, remote, or floppy)";
         junos:cli-feature "nokeyword";
         type string;
         mandatory true;
       }
     }
     output {
       choice output-tags {
         case output-tag {
           leaf output {
             type string;
           }
         }
         case multichassis-tag {
           anyxml multi-routing-engine-results;
         }
       }
     }
   }
   rpc request-license-update {
     description "Start autoupdate license keys from LMS servers";
     junos:command "request system license update";
     input {
       leaf trial {
         description "Start autoupdate trial license keys from LMS servers";
         status deprecated;
         type empty;
       }
     }
     output {
       choice output-tags {
         case actual-tag {
           container inform {
             uses inform-block;
           }
         }
         case multichassis-tag {
           container multi-routing-engine-results {
             list multi-routing-engine-item {
               leaf re-name {
                 type string;
               }
               choice output-tags {
                 case actual-tag {
                   container inform {
                     uses inform-block;
                   }
                 }
               }
             }
           }
         }
       }
     }
   }
   rpc license-revoke-licenses {
     description "Revoke licenses in the Authorization key";
     status deprecated;
     junos:command "request system license revoke-licenses";
     input {
       leaf filename {
         description "Filename (URL, local, remote, or floppy)";
         junos:cli-feature "nokeyword";
         type string;
         mandatory true;
       }
     }
     output {
       choice output-tags {
         case output-tag {
           leaf output {
             type string;
           }
         }
         case multichassis-tag {
           anyxml multi-routing-engine-results;
         }
       }
     }
   }
   rpc fips-selftest {
     description "Execute FIPS known answer tests (KATs)";
     junos:command "request system fips self-test";
     output {
       choice output-tags {
         case output-tag {
           leaf output {
             type string;
           }
         }
         case multichassis-tag {
           anyxml multi-routing-engine-results;
         }
       }
     }
   }
   rpc request-system-erase {
     description "Secure erase SATA drives";
     junos:command "request system erase";
     output {
       choice output-tags {
         case output-tag {
           leaf output {
             type string;
           }
         }
         case actual-tag {
           anyxml system-erase;
         }
         case multichassis-tag {
           anyxml multi-routing-engine-results;
         }
       }
     }
   }
   rpc request-personality-file-generate {
     description "Generate the personality-file tarball for the device";
     junos:command "request system personality-file generate";
     input {
       leaf personality-file-create {
         description "Url containing the remote server alongwith the name of the tarball";
         type string;
         mandatory true;
       }
     }
     output {
       choice output-tags {
         case output-tag {
           leaf output {
             type string;
           }
         }
         case multichassis-tag {
           anyxml multi-routing-engine-results;
         }
       }
     }
   }
   rpc request-personality-file-retrieve {
     description "Retrieve the personality-file tarball of the device";
     junos:command "request system personality-file retrieve";
     input {
       leaf personality-file-retrieve {
         description "Url containing the remote server alongwith the name of the tarball";
         type string;
         mandatory true;
       }
       leaf retrieve-location {
         description "Path on the local device where the personality-file will be retrieved";
         type string;
         mandatory true;
       }
     }
     output {
       choice output-tags {
         case output-tag {
           leaf output {
             type string;
           }
         }
         case multichassis-tag {
           anyxml multi-routing-engine-results;
         }
       }
     }
   }
   rpc request-system-storage-cleanup {
     description "Clean up temporary files and rotate logs";
     junos:command "request system storage cleanup";
     input {
       uses command-forwarding;
       leaf dry-run {
         description "Only list the cleanup candidates, do not remove them";
         type empty;
       }
       leaf no-confirm {
         description "Do not ask for confirmation";
         type empty;
       }
     }
     output {
       choice output-tags {
         case actual-tag {
           container system-storage-cleanup-information {
             uses system-storage-cleanup-information-block;
           }
         }
         case multichassis-tag {
           container multi-routing-engine-results {
             list multi-routing-engine-item {
               leaf re-name {
                 type string;
               }
               choice output-tags {
                 case actual-tag {
                   container system-storage-cleanup-information {
                     uses system-storage-cleanup-information-block;
                   }
                 }
               }
             }
           }
         }
       }
     }
   }
   rpc request-system-storage-expand-user {
     description "Manage size of user disk";
     junos:command "request system storage user-disk";
     input {
       leaf operation {
         description "Expand user disk or revert to default";
         junos:cli-feature "nokeyword";
         type enumeration {
           enum "expand" {
             description "Expand user disk to maximum available size";
           }
           enum "restore" {
             description "Restore user disk to default setting";
           }
         }
         mandatory true;
       }
     }
     output {
       choice output-tags {
         case output-tag {
           leaf output {
             type string;
           }
         }
         case multichassis-tag {
           anyxml multi-routing-engine-results;
         }
       }
     }
   }
   rpc request-boot-console {
     description "Switch boot-console port";
     junos:command "request system boot-console";
     input {
       uses command-forwarding;
       leaf port {
         description "Choice of port";
         junos:cli-feature "nokeyword";
         type enumeration {
           enum "console" {
             description "Set Console port as boot console";
           }
           enum "auxiliary" {
             description "Set Auxiliary port as boot console";
           }
         }
         mandatory true;
       }
     }
     output {
       choice output-tags {
         case output-tag {
           leaf output {
             type string;
           }
         }
         case multichassis-tag {
           anyxml multi-routing-engine-results;
         }
       }
     }
   }
   rpc request-reboot {
     description "Reboot the system";
     junos:command "request system reboot";
     input {
       uses command-forwarding;
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
         case at {
           leaf at {
             description "Time at which to perform the operation in hh::mm 24 hrs format";
             default "now";
             type string;
           }
         }
         case in {
           leaf in {
             description "Number of minutes to delay before operation";
             default "now";
             type string;
           }
         }
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output-tags {
         case actual-tag {
           container request-reboot-results {
             uses request-reboot-results-block;
           }
         }
         case multichassis-tag {
           container multi-routing-engine-results {
             list multi-routing-engine-item {
               leaf re-name {
                 type string;
               }
               choice output-tags {
                 case actual-tag {
                   container request-reboot-results {
                     uses request-reboot-results-block;
                   }
                 }
               }
             }
           }
         }
       }
     }
   }
   rpc request-reboot-in-service {
     description "Reboot with minimal traffic disruption";
     junos:command "request system reboot in-service";
     output {
       choice output-tags {
         case output-tag {
           leaf output {
             type string;
           }
         }
         case multichassis-tag {
           anyxml multi-routing-engine-results;
         }
       }
     }
   }
   rpc request-halt {
     description "Halt the system";
     junos:command "request system halt";
     input {
       uses command-forwarding;
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
         case at {
           leaf at {
             description "Time at which to perform the operation in hh::mm 24 hrs format";
             default "now";
             type string;
           }
         }
         case in {
           leaf in {
             description "Number of minutes to delay before operation";
             default "now";
             type string;
           }
         }
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output-tags {
         case output-tag {
           leaf output {
             type string;
           }
         }
         case multichassis-tag {
           anyxml multi-routing-engine-results;
         }
       }
     }
   }
   rpc request-power-off {
     description "Power off the software on RE";
     junos:command "request system power-off";
     input {
       uses command-forwarding;
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
         case at {
           leaf at {
             description "Time at which to perform the operation in hh::mm 24 hrs format";
             default "now";
             type string;
           }
         }
         case in {
           leaf in {
             description "Number of minutes to delay before operation";
             default "now";
             type string;
           }
         }
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output-tags {
         case output-tag {
           leaf output {
             type string;
           }
         }
         case multichassis-tag {
           anyxml multi-routing-engine-results;
         }
       }
     }
   }
   rpc request-process-terminate {
     description "Terminate the process";
     junos:command "request system process terminate";
     input {
       leaf process-id {
         description "Process ID";
         junos:cli-feature "nokeyword";
         type union {
           type string {
             pattern "<.*>|$.*";
           }
           type uint32 {
             range "1 .. 99999";
           }
         }
         mandatory true;
       }
     }
     output {
       choice output-tags {
         case output-tag {
           leaf output {
             type string;
           }
         }
         case multichassis-tag {
           anyxml multi-routing-engine-results;
         }
       }
     }
   }
   rpc request-system-zeroize {
     description "Erase all data, including configuration and log files";
     junos:command "request system zeroize";
     input {
       leaf media {
         description "Overwrite media";
         type empty;
       }
       leaf local {
         description "Zeroize just this Routing Engine";
         type empty;
       }
     }
     output {
       choice output-tags {
         case actual-tag {
           leaf system-zeroize-status {
             type string;
             description
               "Status of zeroize operation";
           }
         }
         case multichassis-tag {
           container multi-routing-engine-results {
             list multi-routing-engine-item {
               leaf re-name {
                 type string;
               }
               choice output-tags {
                 case actual-tag {
                   leaf system-zeroize-status {
                     type string;
                     description
                       "Status of zeroize operation";
                   }
                 }
               }
             }
           }
         }
       }
     }
   }
   rpc request-system-zeroize-vc {
     description "Virtual-chassis zeroize options";
     junos:command "request system zeroize virtual-chassis";
     input {
       uses command-forwarding;
       leaf media {
         description "Overwrite media";
         type empty;
       }
     }
     output {
       choice output-tags {
         case actual-tag {
           leaf system-zeroize-status {
             type string;
             description
               "Status of zeroize operation";
           }
         }
         case multichassis-tag {
           container multi-routing-engine-results {
             list multi-routing-engine-item {
               leaf re-name {
                 type string;
               }
               choice output-tags {
                 case actual-tag {
                   leaf system-zeroize-status {
                     type string;
                     description
                       "Status of zeroize operation";
                   }
                 }
               }
             }
           }
         }
       }
     }
   }
   rpc request-snapshot {
     description "Create a normal Junos or a recovery snapshot";
     junos:command "request system snapshot";
     input {
       uses command-forwarding;
       leaf snapshot-name {
         description "Snapshot name";
         type string;
       }
       leaf configuration {
         junos:cli-feature "nokeyword";
         default "configuration";
         type enumeration {
           enum "configuration" {
             description "Store device configuration in snapshot";
           }
           enum "no-configuration" {
             description "Do not store device configuration in snapshot";
           }
         }
       }
       leaf force {
         description "Force snapshot operation";
         type empty;
       }
       leaf recovery {
         description "Create a recovery snapshot";
         type empty;
       }
       leaf delete {
         description "Delete an existing snapshot";
         type string;
       }
       leaf load {
         description "Load a given snapshot and activate it upon reboot";
         type string;
       }
       leaf partition {
         description "Partition the media";
         type empty;
       }
       leaf slice {
         description "Write snapshot to specified partition";
         status deprecated;
         type enumeration {
           enum "alternate" {
             description "Write snapshot to alternate partition";
             status deprecated;
           }
         }
       }
       leaf media {
         description "Media to snapshot to";
         default "compact-flash";
         type enumeration {
           enum "removable-compact-flash" {
             description "Write snapshot to removable compact flash";
           }
           enum "compact-flash" {
             description "Write snapshot to compact flash";
           }
           enum "usb" {
             description "Write snapshot to device connected to USB port";
           }
           enum "usb0" {
             description "Write snapshot to device connected to USB0 port";
           }
           enum "usb1" {
             description "Write snapshot to device connected to USB1 port";
           }
           enum "hard-disk" {
             description "Write snapshot to hard disk";
           }
           enum "internal" {
             description "Write snapshot to internal flash";
           }
           enum "external" {
             description "Write snapshot to external storage device";
           }
         }
       }
     }
     output {
       choice output-tags {
         case actual-tag {
           container snapshot-information {
             uses snapshot-information-block;
           }
         }
         case multichassis-tag {
           container multi-routing-engine-results {
             list multi-routing-engine-item {
               leaf re-name {
                 type string;
               }
               choice output-tags {
                 case actual-tag {
                   container snapshot-information {
                     uses snapshot-information-block;
                   }
                 }
               }
             }
           }
         }
       }
     }
   }
   rpc request-system-firmware-reload-fpc {
     description "Reload FPC ROM monitor";
     junos:command "request system firmware reload fpc";
     input {
       leaf slot {
         description "FPC slot number";
         type union {
           type string {
             pattern "<.*>|$.*";
           }
           type uint32;
         }
         mandatory true;
       }
       choice which-arg {
         case wanio-fpga {
         }
         case i2cs-fpga {
         }
         case boot-cpld {
         }
       }
     }
     output {
       choice output-tags {
         case actual-tag {
           container system-firmware-information {
             uses system-firmware-information-block;
           }
         }
         case multichassis-tag {
           container multi-routing-engine-results {
             list multi-routing-engine-item {
               leaf re-name {
                 type string;
               }
               choice output-tags {
                 case actual-tag {
                   container system-firmware-information {
                     uses system-firmware-information-block;
                   }
                 }
               }
             }
           }
         }
       }
     }
   }
   rpc request-system-firmware-upgrade-jnpr-optics-fw {
     description "Upgrade optics firmware";
     junos:command "request system firmware optics update";
     input {
       leaf part-number {
         description "Enter juniper or vendor optic part number";
         type string;
       }
       leaf fpc-slot {
         description "Slot number of FPC";
         type union {
           type string {
             pattern "<.*>|$.*";
           }
           type uint32;
         }
       }
       leaf pic-slot {
         description "PIC slot number";
         type union {
           type string {
             pattern "<.*>|$.*";
           }
           type uint32;
         }
       }
       leaf port {
         description "Enter Port number";
         type union {
           type string {
             pattern "<.*>|$.*";
           }
           type uint32;
         }
       }
       leaf firmware-path {
         description "Enter firmware path";
         type string;
       }
       leaf password {
         description "Password to unlock firmware download";
         type union {
           type string {
             pattern "<.*>|$.*";
           }
           type uint32 {
             range "0 .. 2147483647";
           }
         }
       }
     }
     output {
       choice output-tags {
         case output-tag {
           leaf output {
             type string;
           }
         }
         case multichassis-tag {
           anyxml multi-routing-engine-results;
         }
       }
     }
   }
   rpc request-system-firmware-optics-switch {
     description "Firmware switch optics";
     junos:command "request system firmware optics switch";
     input {
       leaf fpc-slot {
         description "Slot number of FPC";
         type union {
           type string {
             pattern "<.*>|$.*";
           }
           type uint32;
         }
         mandatory true;
       }
       leaf pic-slot {
         description "Slot number of FPC";
         type union {
           type string {
             pattern "<.*>|$.*";
           }
           type uint32;
         }
         mandatory true;
       }
       leaf port {
         description "Slot number of FPC";
         type union {
           type string {
             pattern "<.*>|$.*";
           }
           type uint32;
         }
         mandatory true;
       }
       leaf password {
         description "Password to unlock firmware download";
         type union {
           type string {
             pattern "<.*>|$.*";
           }
           type uint32 {
             range "0 .. 2147483647";
           }
         }
       }
     }
     output {
       choice output-tags {
         case output-tag {
           leaf output {
             type string;
           }
         }
         case multichassis-tag {
           anyxml multi-routing-engine-results;
         }
       }
     }
   }
   rpc request-jfw-cpld-upgrade {
     description "Upgrade CPLD firmware";
     junos:command "request system firmware upgrade jfirmware cpld";
     input {
       leaf cpld-type {
         description "CPLD type: RE, MAIN, FAN";
         type string;
       }
     }
     output {
       choice output-tags {
         case output-tag {
           leaf output {
             type string;
           }
         }
         case multichassis-tag {
           anyxml multi-routing-engine-results;
         }
       }
     }
   }
   rpc request-jfw-cpld-mainboard-upgrade {
     description "Upgrade mainboard CPLD firmware";
     junos:command "request system firmware upgrade jfirmware cpld main";
     output {
       choice output-tags {
         case output-tag {
           leaf output {
             type string;
           }
         }
         case actual-tag {
           anyxml system-jfw-cpld-mainboard-upgrade-information;
         }
         case multichassis-tag {
           anyxml multi-routing-engine-results;
         }
       }
     }
   }
   rpc request-jfw-main-board-upgrade-status {
     description "Show MAIN board upgrade status";
     junos:command "request system firmware upgrade jfirmware cpld main progress";
     output {
       choice output-tags {
         case output-tag {
           leaf output {
             type string;
           }
         }
         case actual-tag {
           anyxml system-jfw-main-board-upgrade-information-status;
         }
         case multichassis-tag {
           anyxml multi-routing-engine-results;
         }
       }
     }
   }
   rpc request-jfw-cpld-fanboard-upgrade {
     description "Upgrade fanboard CPLD firmware";
     junos:command "request system firmware upgrade jfirmware cpld fan";
     input {
       uses command-forwarding;
     }
     output {
       choice output-tags {
         case output-tag {
           leaf output {
             type string;
           }
         }
         case actual-tag {
           anyxml system-jfw-cpld-fanboard-upgrade-information;
         }
         case multichassis-tag {
           anyxml multi-routing-engine-results;
         }
       }
     }
   }
   rpc request-jfw-cpld-fanboard-upgrade-status {
     description "Show fanboard CPLD upgrade status";
     junos:command "request system firmware upgrade jfirmware cpld fan progress";
     input {
       uses command-forwarding;
     }
     output {
       choice output-tags {
         case output-tag {
           leaf output {
             type string;
           }
         }
         case actual-tag {
           anyxml system-jfw-cpld-fanboard-upgrade-information-status;
         }
         case multichassis-tag {
           anyxml multi-routing-engine-results;
         }
       }
     }
   }
   rpc request-jfw-cpld-sys-upgrade {
     description "Upgrade Sys CPLD firmware";
     junos:command "request system firmware upgrade jfirmware cpld sys";
     input {
       uses command-forwarding;
     }
     output {
       choice output-tags {
         case output-tag {
           leaf output {
             type string;
           }
         }
         case actual-tag {
           anyxml system-jfw-cpld-sys-upgrade-information;
         }
         case multichassis-tag {
           anyxml multi-routing-engine-results;
         }
       }
     }
   }
   rpc request-jfw-sys-cpld-upgrade-status {
     description "Show Sys cpld upgrade status";
     junos:command "request system firmware upgrade jfirmware cpld sys progress";
     input {
       uses command-forwarding;
     }
     output {
       choice output-tags {
         case output-tag {
           leaf output {
             type string;
           }
         }
         case actual-tag {
           anyxml system-jfw-sys-cpld-upgrade-information-status;
         }
         case multichassis-tag {
           anyxml multi-routing-engine-results;
         }
       }
     }
   }
   rpc request-jfw-cpld-cpuboard-upgrade {
     description "Upgrade CPU board CPLD firmware";
     junos:command "request system firmware upgrade jfirmware cpld cpu";
     input {
       uses command-forwarding;
     }
     output {
       choice output-tags {
         case output-tag {
           leaf output {
             type string;
           }
         }
         case actual-tag {
           anyxml system-jfw-cpld-cpuboard-upgrade-information;
         }
         case multichassis-tag {
           anyxml multi-routing-engine-results;
         }
       }
     }
   }
   rpc request-jfw-cpu-cpld-upgrade-status {
     description "Show CPU cpld upgrade status";
     junos:command "request system firmware upgrade jfirmware cpld cpu progress";
     input {
       uses command-forwarding;
     }
     output {
       choice output-tags {
         case output-tag {
           leaf output {
             type string;
           }
         }
         case actual-tag {
           anyxml system-jfw-cpu-cpld-upgrade-information-status;
         }
         case multichassis-tag {
           anyxml multi-routing-engine-results;
         }
       }
     }
   }
   rpc request-jfw-cpld-port-upgrade {
     description "Upgrade port CPLD firmware";
     junos:command "request system firmware upgrade jfirmware cpld port";
     input {
       uses command-forwarding;
     }
     output {
       choice output-tags {
         case output-tag {
           leaf output {
             type string;
           }
         }
         case actual-tag {
           anyxml system-jfw-cpld-port-upgrade-information;
         }
         case multichassis-tag {
           anyxml multi-routing-engine-results;
         }
       }
     }
   }
   rpc request-jfw-port-cpld-upgrade-status {
     description "Show port cpld upgrade status";
     junos:command "request system firmware upgrade jfirmware cpld port progress";
     input {
       uses command-forwarding;
     }
     output {
       choice output-tags {
         case output-tag {
           leaf output {
             type string;
           }
         }
         case actual-tag {
           anyxml system-jfw-port-cpld-upgrade-information-status;
         }
         case multichassis-tag {
           anyxml multi-routing-engine-results;
         }
       }
     }
   }
   rpc request-jfw-mmc-upgrade {
     description "Upgrade MMC firmware";
     junos:command "request system firmware upgrade jfirmware mmc";
     input {
       uses command-forwarding;
     }
     output {
       choice output-tags {
         case output-tag {
           leaf output {
             type string;
           }
         }
         case actual-tag {
           anyxml system-jfw-mmc-upgrade-information;
         }
         case multichassis-tag {
           anyxml multi-routing-engine-results;
         }
       }
     }
   }
   rpc request-jfw-mmc-upgrade-status {
     description "Show MMC upgrade status";
     junos:command "request system firmware upgrade jfirmware mmc progress";
     input {
       uses command-forwarding;
     }
     output {
       choice output-tags {
         case output-tag {
           leaf output {
             type string;
           }
         }
         case actual-tag {
           anyxml system-jfw-mmc-upgrade-information-status;
         }
         case multichassis-tag {
           anyxml multi-routing-engine-results;
         }
       }
     }
   }
   rpc request-jfw-nvme-upgrade {
     description "Upgrade NVME SSD firmware";
     junos:command "request system firmware upgrade jfirmware nvme";
     input {
       uses command-forwarding;
     }
     output {
       choice output-tags {
         case output-tag {
           leaf output {
             type string;
           }
         }
         case multichassis-tag {
           anyxml multi-routing-engine-results;
         }
       }
     }
   }
   rpc request-jfw-nvme-upgrade-status {
     description "Show NVME upgrade status";
     junos:command "request system firmware upgrade jfirmware nvme progress";
     input {
       uses command-forwarding;
     }
     output {
       choice output-tags {
         case output-tag {
           leaf output {
             type string;
           }
         }
         case multichassis-tag {
           anyxml multi-routing-engine-results;
         }
       }
     }
   }
   rpc request-jfw-eusb-upgrade {
     description "Upgrade eusb firmware";
     junos:command "request system firmware upgrade jfirmware eusb";
     output {
       choice output-tags {
         case output-tag {
           leaf output {
             type string;
           }
         }
         case actual-tag {
           anyxml system-jfw-eusb-upgrade-information;
         }
         case multichassis-tag {
           anyxml multi-routing-engine-results;
         }
       }
     }
   }
   rpc request-jfw-eusb-upgrade-status {
     description "Show eusb upgrade status";
     junos:command "request system firmware upgrade jfirmware eusb progress";
     output {
       choice output-tags {
         case output-tag {
           leaf output {
             type string;
           }
         }
         case actual-tag {
           anyxml system-jfw-eusb-upgrade-information-status;
         }
         case multichassis-tag {
           anyxml multi-routing-engine-results;
         }
       }
     }
   }
   rpc request-jfw-uboot-upgrade {
     description "Upgrade uboot binary";
     junos:command "request system firmware upgrade jfirmware uboot";
     input {
       uses command-forwarding;
     }
     output {
       choice output-tags {
         case output-tag {
           leaf output {
             type string;
           }
         }
         case actual-tag {
           anyxml system-jfw-uboot-upgrade-information;
         }
         case multichassis-tag {
           anyxml multi-routing-engine-results;
         }
       }
     }
   }
   rpc request-jfw-uboot-upgrade-status {
     description "Show uboot upgrade status";
     junos:command "request system firmware upgrade jfirmware uboot progress";
     input {
       uses command-forwarding;
     }
     output {
       choice output-tags {
         case output-tag {
           leaf output {
             type string;
           }
         }
         case actual-tag {
           anyxml system-jfw-uboot-upgrade-information-status;
         }
         case multichassis-tag {
           anyxml multi-routing-engine-results;
         }
       }
     }
   }
   rpc request-jfw-nic-i350-upgrade {
     description "Upgrade Builtin i350 NIC firmware";
     junos:command "request system firmware upgrade jfirmware nic i350";
     output {
       choice output-tags {
         case output-tag {
           leaf output {
             type string;
           }
         }
         case multichassis-tag {
           anyxml multi-routing-engine-results;
         }
       }
     }
   }
   rpc request-jfirmware-nic-i210-upgrade {
     description "Upgrade Builtin i210 NIC firmware";
     junos:command "request system firmware upgrade jfirmware nic i210";
     output {
       choice output-tags {
         case output-tag {
           leaf output {
             type string;
           }
         }
         case multichassis-tag {
           anyxml multi-routing-engine-results;
         }
       }
     }
   }
   rpc request-jfw-nic-x552-upgrade {
     description "Upgrade Builtin x552 NIC firmware";
     junos:command "request system firmware upgrade jfirmware nic x552";
     output {
       choice output-tags {
         case output-tag {
           leaf output {
             type string;
           }
         }
         case actual-tag {
           anyxml system-jfw-nic-x552-upgrade-information;
         }
         case multichassis-tag {
           anyxml multi-routing-engine-results;
         }
       }
     }
   }
   rpc request-jfw-nic-x722-upgrade {
     description "Upgrade Builtin x722 NIC firmware";
     junos:command "request system firmware upgrade jfirmware nic x722";
     output {
       choice output-tags {
         case output-tag {
           leaf output {
             type string;
           }
         }
         case actual-tag {
           anyxml system-jfw-nic-x722-upgrade-information;
         }
         case multichassis-tag {
           anyxml multi-routing-engine-results;
         }
       }
     }
   }
   rpc request-jfw-nic-x722-upgrade-status {
     description "Show NIC upgrade status";
     junos:command "request system firmware upgrade jfirmware nic x722 progress";
     output {
       choice output-tags {
         case output-tag {
           leaf output {
             type string;
           }
         }
         case actual-tag {
           anyxml system-jfw-nic-x722-upgrade-information-status;
         }
         case multichassis-tag {
           anyxml multi-routing-engine-results;
         }
       }
     }
   }
   rpc request-jfw-nic-x553-upgrade {
     description "Upgrade Builtin x553 NIC firmware";
     junos:command "request system firmware upgrade jfirmware nic x553";
     output {
       choice output-tags {
         case output-tag {
           leaf output {
             type string;
           }
         }
         case actual-tag {
           anyxml system-jfw-nic-x553-upgrade-information;
         }
         case multichassis-tag {
           anyxml multi-routing-engine-results;
         }
       }
     }
   }
   rpc request-jfw-nic-i82599-1-upgrade {
     description "Upgrade Builtin i82599_1 NIC firmware";
     junos:command "request system firmware upgrade jfirmware nic i82599-1";
     output {
       choice output-tags {
         case output-tag {
           leaf output {
             type string;
           }
         }
         case actual-tag {
           anyxml system-jfw-nic-i82599-1-upgrade-information;
         }
         case multichassis-tag {
           anyxml multi-routing-engine-results;
         }
       }
     }
   }
   rpc request-jfw-nic-i82599-2-upgrade {
     description "Upgrade Builtin i82599_2 NIC firmware";
     junos:command "request system firmware upgrade jfirmware nic i82599-2";
     output {
       choice output-tags {
         case output-tag {
           leaf output {
             type string;
           }
         }
         case actual-tag {
           anyxml system-jfw-nic-i82599-2-upgrade-information;
         }
         case multichassis-tag {
           anyxml multi-routing-engine-results;
         }
       }
     }
   }
   rpc request-jfw-em-i350-copper-upgrade {
     description "Upgrade Expansion Module i350 NIC Copper firmware";
     junos:command "request system firmware upgrade jfirmware em i350 copper";
     output {
       choice output-tags {
         case output-tag {
           leaf output {
             type string;
           }
         }
         case actual-tag {
           anyxml system-jfw-em-i350-copper-upgrade-information;
         }
         case multichassis-tag {
           anyxml multi-routing-engine-results;
         }
       }
     }
   }
   rpc request-jfw-em-i350-sfp-upgrade {
     description "Upgrade Expansion Module i350 NIC SFP firmware";
     junos:command "request system firmware upgrade jfirmware em i350 sfp";
     output {
       choice output-tags {
         case output-tag {
           leaf output {
             type string;
           }
         }
         case actual-tag {
           anyxml system-jfw-em-i350-sfp-upgrade-information;
         }
         case multichassis-tag {
           anyxml multi-routing-engine-results;
         }
       }
     }
   }
   rpc request-jfw-bios-upgrade {
     description "Upgrade BIOS firmware";
     junos:command "request system firmware upgrade jfirmware bios";
     input {
       uses command-forwarding;
       leaf disk {
         description "1, 2";
         type string;
       }
     }
     output {
       choice output-tags {
         case output-tag {
           leaf output {
             type string;
           }
         }
         case multichassis-tag {
           anyxml multi-routing-engine-results;
         }
       }
     }
   }
   rpc request-jfw-bios-upgrade-status {
     description "Show BIOS upgrade status";
     junos:command "request system firmware upgrade jfirmware bios progress";
     input {
       uses command-forwarding;
     }
     output {
       choice output-tags {
         case output-tag {
           leaf output {
             type string;
           }
         }
         case actual-tag {
           anyxml system-jfw-bios-upgrade-information-status;
         }
         case multichassis-tag {
           anyxml multi-routing-engine-results;
         }
       }
     }
   }
   rpc request-jfw-psu-upgrade {
     description "Upgrade psu firmware";
     junos:command "request system firmware upgrade jfirmware psu";
     input {
       uses command-forwarding;
       leaf slot {
         description "PEM slot number";
         type union {
           type string {
             pattern "<.*>|$.*";
           }
           type uint32;
         }
       }
     }
     output {
       choice output-tags {
         case output-tag {
           leaf output {
             type string;
           }
         }
         case multichassis-tag {
           anyxml multi-routing-engine-results;
         }
       }
     }
   }
   rpc request-jfw-psu-upgrade-status {
     description "Show PSU upgrade status";
     junos:command "request system firmware upgrade jfirmware psu progress";
     input {
       uses command-forwarding;
     }
     output {
       choice output-tags {
         case output-tag {
           leaf output {
             type string;
           }
         }
         case actual-tag {
           anyxml system-jfw-psu-upgrade-information-status;
         }
         case multichassis-tag {
           anyxml multi-routing-engine-results;
         }
       }
     }
   }
   rpc request-jfirmware-hv-psu-upgrade {
     description "Upgrade HV PSU firmware";
     junos:command "request system firmware upgrade jfirmware hv-psu";
     output {
       choice output-tags {
         case output-tag {
           leaf output {
             type string;
           }
         }
         case multichassis-tag {
           anyxml multi-routing-engine-results;
         }
       }
     }
   }
   rpc request-jfirmware-hv-psu-upgrade-status {
     description "Show HV PSU upgrade status";
     junos:command "request system firmware upgrade jfirmware hv-psu progress";
     output {
       choice output-tags {
         case output-tag {
           leaf output {
             type string;
           }
         }
         case multichassis-tag {
           anyxml multi-routing-engine-results;
         }
       }
     }
   }
   rpc request-jfw-ssd-upgrade {
     description "Upgrade SSD firmware";
     junos:command "request system firmware upgrade jfirmware ssd";
     input {
       leaf disk {
         description "1, 2";
         type string;
       }
     }
     output {
       choice output-tags {
         case output-tag {
           leaf output {
             type string;
           }
         }
         case multichassis-tag {
           anyxml multi-routing-engine-results;
         }
       }
     }
   }
   rpc get-jfw-tpm-upgrade {
     description "Upgrade TPM firmware";
     junos:command "request system firmware upgrade jfirmware tpm";
     output {
       choice output-tags {
         case output-tag {
           leaf output {
             type string;
           }
         }
         case multichassis-tag {
           anyxml multi-routing-engine-results;
         }
       }
     }
   }
   rpc request-jfw-poe-upgrade {
     description "Upgrade POE firmware";
     junos:command "request system firmware upgrade jfirmware poe";
     input {
       uses command-forwarding;
       leaf fpc-slot {
         description "FPC slot";
         type string;
         mandatory true;
       }
       leaf poe-firmware-type {
         description "POE_FIRMWARE_TYPE";
         junos:cli-feature "nokeyword";
         type enumeration {
           enum "poe-at-firmware" {
             description "IEEE 802.3at PoE Firmware Support";
           }
           enum "poe-bt-firmware" {
             description "IEEE 802.3bt PoE Firmware Support";
           }
         }
       }
     }
     output {
       choice output-tags {
         case output-tag {
           leaf output {
             type string;
           }
         }
         case multichassis-tag {
           anyxml multi-routing-engine-results;
         }
       }
     }
   }
   rpc request-jfw-bcm-pcie-upgrade {
     description "Upgrade BCM PCIe firmware";
     junos:command "request system firmware upgrade jfirmware bcmpcie";
     output {
       choice output-tags {
         case output-tag {
           leaf output {
             type string;
           }
         }
         case multichassis-tag {
           anyxml multi-routing-engine-results;
         }
       }
     }
   }
   rpc request-jfirmware-pmic-upgrade {
     description "Upgrade PMIC firmware";
     junos:command "request system firmware upgrade jfirmware pmic";
     output {
       choice output-tags {
         case output-tag {
           leaf output {
             type string;
           }
         }
         case multichassis-tag {
           anyxml multi-routing-engine-results;
         }
       }
     }
   }
   rpc request-jfw-pmic-fpga-upgrade-status {
     description "Show PMIC Upgrade status";
     junos:command "request system firmware upgrade jfirmware pmic progress";
     output {
       choice output-tags {
         case output-tag {
           leaf output {
             type string;
           }
         }
         case multichassis-tag {
           anyxml multi-routing-engine-results;
         }
       }
     }
   }
   rpc request-jfw-re-fpga-upgrade {
     description "Upgrade RE FPGA";
     junos:command "request system firmware upgrade jfirmware fpga re";
     input {
       uses command-forwarding;
       leaf file {
         description "Jfirmware package file";
         type string;
       }
     }
     output {
       choice output-tags {
         case output-tag {
           leaf output {
             type string;
           }
         }
         case actual-tag {
           anyxml system-jfw-re-fpga-upgrade-information;
         }
         case multichassis-tag {
           anyxml multi-routing-engine-results;
         }
       }
     }
   }
   rpc request-jfw-re-fpga-upgrade-status {
     description "Show RE FPGA Upgrade status";
     junos:command "request system firmware upgrade jfirmware fpga re progress";
     input {
       uses command-forwarding;
     }
     output {
       choice output-tags {
         case output-tag {
           leaf output {
             type string;
           }
         }
         case actual-tag {
           anyxml system-jfw-re-fpga-upgrade-information-status;
         }
         case multichassis-tag {
           anyxml multi-routing-engine-results;
         }
       }
     }
   }
   rpc request-jfw-tmc-fpga-upgrade {
     description "Upgrade Mainboard TMC FPGA";
     junos:command "request system firmware upgrade jfirmware fpga tmc";
     output {
       choice output-tags {
         case output-tag {
           leaf output {
             type string;
           }
         }
         case actual-tag {
           anyxml system-jfw-tmc-fpga-upgrade-information;
         }
         case multichassis-tag {
           anyxml multi-routing-engine-results;
         }
       }
     }
   }
   rpc request-jfw-tmc-fpga-upgrade-status {
     description "Show TMC Upgrade status";
     junos:command "request system firmware upgrade jfirmware fpga tmc progress";
     output {
       choice output-tags {
         case output-tag {
           leaf output {
             type string;
           }
         }
         case actual-tag {
           anyxml system-jfw-tmc-fpga-upgrade-information-status;
         }
         case multichassis-tag {
           anyxml multi-routing-engine-results;
         }
       }
     }
   }
   rpc request-jfw-main-fpga-upgrade {
     description "Upgrade Mainboard FPGA";
     junos:command "request system firmware upgrade jfirmware fpga main-board";
     input {
       uses command-forwarding;
     }
     output {
       choice output-tags {
         case output-tag {
           leaf output {
             type string;
           }
         }
         case actual-tag {
           anyxml system-jfw-main-fpga-upgrade-information;
         }
         case multichassis-tag {
           anyxml multi-routing-engine-results;
         }
       }
     }
   }
   rpc request-jfw-power-cpld-upgrade {
     description "Upgrade Power CPLD";
     junos:command "request system firmware upgrade jfirmware fpga powercpld";
     output {
       choice output-tags {
         case output-tag {
           leaf output {
             type string;
           }
         }
         case actual-tag {
           anyxml system-jfw-power-cpld-upgrade-information;
         }
         case multichassis-tag {
           anyxml multi-routing-engine-results;
         }
       }
     }
   }
   rpc request-jfw-powercpld-upgrade-status {
     description "Show Powercpld Upgrade status";
     junos:command "request system firmware upgrade jfirmware fpga powercpld progress";
     output {
       choice output-tags {
         case output-tag {
           leaf output {
             type string;
           }
         }
         case actual-tag {
           anyxml system-jfw-powercpld-upgrade-information-status;
         }
         case multichassis-tag {
           anyxml multi-routing-engine-results;
         }
       }
     }
   }
   rpc request-jfirmware-fanboard-fpga-upgrade {
     description "Upgrade Fanboard FPGA";
     junos:command "request system firmware upgrade jfirmware fpga fan";
     output {
       choice output-tags {
         case output-tag {
           leaf output {
             type string;
           }
         }
         case multichassis-tag {
           anyxml multi-routing-engine-results;
         }
       }
     }
   }
   rpc request-jfirmware-fanboard-fpga-upgrade-status {
     description "Show Fanboard FPGA Upgrade status";
     junos:command "request system firmware upgrade jfirmware fpga fan progress";
     output {
       choice output-tags {
         case output-tag {
           leaf output {
             type string;
           }
         }
         case multichassis-tag {
           anyxml multi-routing-engine-results;
         }
       }
     }
   }
   rpc request-jfw-optics-sfp-upgrade {
     description "Upgrade Optics FPGA/CPLD";
     junos:command "request system firmware upgrade jfirmware fpga sfp";
     output {
       choice output-tags {
         case output-tag {
           leaf output {
             type string;
           }
         }
         case actual-tag {
           anyxml system-jfw-optics-sfp-upgrade-information;
         }
         case multichassis-tag {
           anyxml multi-routing-engine-results;
         }
       }
     }
   }
   rpc request-jfw-optics-sfp-upgrade-status {
     description "Show SFP Upgrade status";
     junos:command "request system firmware upgrade jfirmware fpga sfp progress";
     output {
       choice output-tags {
         case output-tag {
           leaf output {
             type string;
           }
         }
         case actual-tag {
           anyxml system-jfw-optics-sfp-upgrade-information-status;
         }
         case multichassis-tag {
           anyxml multi-routing-engine-results;
         }
       }
     }
   }
   rpc request-jfw-optics-qsfp-upgrade {
     description "Upgrade Optics FPGA/CPLD";
     junos:command "request system firmware upgrade jfirmware fpga qsfp";
     output {
       choice output-tags {
         case output-tag {
           leaf output {
             type string;
           }
         }
         case actual-tag {
           anyxml system-jfw-optics-qsfp-upgrade-information;
         }
         case multichassis-tag {
           anyxml multi-routing-engine-results;
         }
       }
     }
   }
   rpc request-jfw-optics-qsfp-upgrade-status {
     description "Show QSFP Upgrade status";
     junos:command "request system firmware upgrade jfirmware fpga qsfp progress";
     output {
       choice output-tags {
         case output-tag {
           leaf output {
             type string;
           }
         }
         case actual-tag {
           anyxml system-jfw-optics-qsfp-upgrade-information-status;
         }
         case multichassis-tag {
           anyxml multi-routing-engine-results;
         }
       }
     }
   }
   rpc request-jfw-bmc-upgrade {
     description "Upgrade BMC firmware";
     junos:command "request system firmware upgrade jfirmware bmc";
     input {
       leaf file {
         description "Jfirmware package file";
         type string;
       }
     }
     output {
       choice output-tags {
         case output-tag {
           leaf output {
             type string;
           }
         }
         case multichassis-tag {
           anyxml multi-routing-engine-results;
         }
       }
     }
   }
   rpc request-jfw-bmc-upgrade-status {
     description "Show BMC Upgrade status";
     junos:command "request system firmware upgrade jfirmware bmc progress";
     output {
       choice output-tags {
         case output-tag {
           leaf output {
             type string;
           }
         }
         case multichassis-tag {
           anyxml multi-routing-engine-results;
         }
       }
     }
   }
   rpc request-jfw-allfw-upgrade {
     description "Upgrade all firmwares applicable in Jfirmware package";
     junos:command "request system firmware upgrade jfirmware allfw";
     input {
       uses command-forwarding;
     }
     output {
       choice output-tags {
         case output-tag {
           leaf output {
             type string;
           }
         }
         case multichassis-tag {
           anyxml multi-routing-engine-results;
         }
       }
     }
   }
   rpc request-jfw-allfw-upgrade-status {
     description "Show all firmware upgrade status";
     junos:command "request system firmware upgrade jfirmware allfw progress";
     input {
       uses command-forwarding;
     }
     output {
       choice output-tags {
         case output-tag {
           leaf output {
             type string;
           }
         }
         case actual-tag {
           anyxml system-jfw-allfw-upgrade-information-status;
         }
         case multichassis-tag {
           anyxml multi-routing-engine-results;
         }
       }
     }
   }
   rpc request-scb-fpga-upgrade {
     description "Upgrade SCB FPGA ";
     junos:command "request system firmware upgrade fpga scb";
     input {
       leaf file {
         description "FPGA file name";
         type string;
       }
     }
     output {
       choice output-tags {
         case output-tag {
           leaf output {
             type string;
           }
         }
         case actual-tag {
           anyxml system-fpga-upgrade-information;
         }
         case multichassis-tag {
           anyxml multi-routing-engine-results;
         }
       }
     }
   }
   rpc request-fpc-fpga-upgrade {
     description "Upgrade Line Card FPGAs";
     junos:command "request system firmware upgrade fpga fpc";
     input {
       uses command-forwarding;
       leaf slot {
         description "FPC slot number";
         type union {
           type string {
             pattern "<.*>|$.*";
           }
           type uint32;
         }
       }
       leaf file {
         description "FPGA file name";
         type string;
       }
     }
     output {
       choice output-tags {
         case output-tag {
           leaf output {
             type string;
           }
         }
         case actual-tag {
           anyxml system-fpga-upgrade-information;
         }
         case multichassis-tag {
           anyxml multi-routing-engine-results;
         }
       }
     }
   }
   rpc request-system-download-clear {
     description "Clear records of completed and aborted downloads";
     junos:command "request system download clear";
     output {
       choice output-tags {
         case actual-tag {
           container download-information {
             uses download-information-block;
           }
         }
         case multichassis-tag {
           container multi-routing-engine-results {
             list multi-routing-engine-item {
               leaf re-name {
                 type string;
               }
               choice output-tags {
                 case actual-tag {
                   container download-information {
                     uses download-information-block;
                   }
                 }
               }
             }
           }
         }
       }
     }
   }
   rpc request-system-download-start {
     description "Start a new download";
     junos:command "request system download start";
     input {
       leaf url {
         description "URL of file";
         junos:cli-feature "nokeyword";
         type string;
         mandatory true;
       }
       leaf max-rate {
         description "Maximum bandwidth for the download";
         type string {
           junos:posix-pattern "^[1-9][0-9]{0,8}([kKmM])?$";
           junos:pattern-message "Up to 9 digits with optional k or m suffix";
         }
       }
       leaf save-as {
         description "Rename file when saving to local file system";
         type string;
       }
       leaf login {
         description "Login credentials (username:password)";
         type string;
       }
       leaf identity-file {
         description "Identity file for sftp pubic key authentication";
         type string;
       }
       leaf passphrase {
         description "Passphrase used to protect identity key pair";
         type string;
       }
       leaf delay {
         description "Delay the start of the download";
         units "hours";
         type union {
           type string {
             pattern "<.*>|$.*";
           }
           type int32 {
             range "1 .. 48";
           }
         }
       }
     }
     output {
       choice output-tags {
         case actual-tag {
           container download-information {
             uses download-information-block;
           }
         }
         case multichassis-tag {
           container multi-routing-engine-results {
             list multi-routing-engine-item {
               leaf re-name {
                 type string;
               }
               choice output-tags {
                 case actual-tag {
                   container download-information {
                     uses download-information-block;
                   }
                 }
               }
             }
           }
         }
       }
     }
   }
   rpc request-system-download-pause {
     description "Pause an active download";
     junos:command "request system download pause";
     input {
       leaf download-id {
         description "ID of the download to be paused";
         junos:cli-feature "nokeyword";
         type union {
           type uint16;
           type string {
             pattern "<.*>|$.*";
           }
         }
         mandatory true;
       }
     }
     output {
       choice output-tags {
         case actual-tag {
           container download-information {
             uses download-information-block;
           }
         }
         case multichassis-tag {
           container multi-routing-engine-results {
             list multi-routing-engine-item {
               leaf re-name {
                 type string;
               }
               choice output-tags {
                 case actual-tag {
                   container download-information {
                     uses download-information-block;
                   }
                 }
               }
             }
           }
         }
       }
     }
   }
   rpc request-system-download-resume {
     description "Resume a paused download";
     junos:command "request system download resume";
     input {
       leaf download-id {
         description "ID of the download to be resumed";
         junos:cli-feature "nokeyword";
         type union {
           type uint16;
           type string {
             pattern "<.*>|$.*";
           }
         }
         mandatory true;
       }
       leaf max-rate {
         description "Maximum bandwidth for the download";
         type string;
       }
     }
     output {
       choice output-tags {
         case actual-tag {
           container download-information {
             uses download-information-block;
           }
         }
         case multichassis-tag {
           container multi-routing-engine-results {
             list multi-routing-engine-item {
               leaf re-name {
                 type string;
               }
               choice output-tags {
                 case actual-tag {
                   container download-information {
                     uses download-information-block;
                   }
                 }
               }
             }
           }
         }
       }
     }
   }
   rpc request-system-download-abort {
     description "Abort a download and delete the local file";
     junos:command "request system download abort";
     input {
       leaf download-id {
         description "ID of the download to be aborted";
         junos:cli-feature "nokeyword";
         type union {
           type uint16;
           type string {
             pattern "<.*>|$.*";
           }
         }
         mandatory true;
       }
     }
     output {
       choice output-tags {
         case actual-tag {
           container download-information {
             uses download-information-block;
           }
         }
         case multichassis-tag {
           container multi-routing-engine-results {
             list multi-routing-engine-item {
               leaf re-name {
                 type string;
               }
               choice output-tags {
                 case actual-tag {
                   container download-information {
                     uses download-information-block;
                   }
                 }
               }
             }
           }
         }
       }
     }
   }
   rpc request-system-routing-pitrace {
     description "Routing protocol daemon";
     junos:command "request system pixel-tracing routing";
     output {
       choice output-tags {
         case output-tag {
           leaf output {
             type string;
           }
         }
         case multichassis-tag {
           anyxml multi-routing-engine-results;
         }
       }
     }
   }
   rpc request-system-routing-pitrace-flush {
     description "Flush pitrace";
     junos:command "request system pixel-tracing routing flush";
     output {
       choice output-tags {
         case output-tag {
           leaf output {
             type string;
           }
         }
         case multichassis-tag {
           anyxml multi-routing-engine-results;
         }
       }
     }
   }
   rpc request-system-routing-pitrace-enable {
     description "Enable pitrace";
     junos:command "request system pixel-tracing routing enable";
     output {
       choice output-tags {
         case output-tag {
           leaf output {
             type string;
           }
         }
         case multichassis-tag {
           anyxml multi-routing-engine-results;
         }
       }
     }
   }
   rpc request-system-routing-pitrace-disable {
     description "Disable pitrace";
     junos:command "request system pixel-tracing routing disable";
     output {
       choice output-tags {
         case output-tag {
           leaf output {
             type string;
           }
         }
         case multichassis-tag {
           anyxml multi-routing-engine-results;
         }
       }
     }
   }
   rpc get-ethernet-switching-status-evpn-vlan {
     description "Show vlans status";
     junos:command "request system evpn forwarding vlans";
     input {
       leaf no-confirm {
         description "Do not ask for confirmation";
         type empty;
       }
       leaf instance {
         description "Routing instance";
         type string;
       }
       leaf vlan {
         description "VLAN name";
         type string;
       }
       leaf verbosity {
         junos:cli-feature "nokeyword";
         type enumeration {
           enum "detail" {
             description "Display detailed output";
           }
           enum "format" {
             description "Display formated output";
           }
         }
       }
       leaf module {
         description "Module name";
         type enumeration {
           enum "mac-table" {
             description "MAC module";
           }
           enum "mac-ip-table" {
             description "MAC IP module";
           }
         }
       }
     }
     output {
       choice output-tags {
         case actual-tag {
           container system-evpn {
             uses system-evpn-block;
           }
         }
         case multichassis-tag {
           container multi-routing-engine-results {
             list multi-routing-engine-item {
               leaf re-name {
                 type string;
               }
               choice output-tags {
                 case actual-tag {
                   container system-evpn {
                     uses system-evpn-block;
                   }
                 }
               }
             }
           }
         }
       }
     }
   }
   rpc get-ethernet-switching-status-hash-vlan {
     description "Show vlans status";
     junos:command "request system evpn hash-values vlans";
     input {
       leaf no-confirm {
         description "Do not ask for confirmation";
         type empty;
       }
       leaf instance {
         description "Routing instance";
         type string;
       }
       leaf vlan {
         description "VLAN name";
         type string;
       }
     }
     output {
       choice output-tags {
         case actual-tag {
           container system-evpn {
             uses system-evpn-block;
           }
         }
         case multichassis-tag {
           container multi-routing-engine-results {
             list multi-routing-engine-item {
               leaf re-name {
                 type string;
               }
               choice output-tags {
                 case actual-tag {
                   container system-evpn {
                     uses system-evpn-block;
                   }
                 }
               }
             }
           }
         }
       }
     }
   }
   rpc generate-pki-key-pair {
     description "Generate RSA, DSA or ECDSA private and public key pair";
     junos:command "request security pki generate-key-pair";
     input {
       uses command-forwarding;
       choice daemon-select {
         case logical-system {
         }
       }
       choice id-type {
         case certificate-id {
           leaf certificate-id {
             description "Certificate identifier";
             type string {
               length "1 .. 32";
               junos:posix-pattern "![/ %.]";
               junos:pattern-message "Must not contain \'/\', %, \'.\' or a space";
             }
           }
         }
         case acme-key-id {
           leaf acme-key-id {
             description "Acme account key identifier";
             type string {
               length "1 .. 32";
               junos:posix-pattern "![/ %.]";
               junos:pattern-message "Must not contain \'/\', %, \'.\' or a space";
             }
           }
         }
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption";
           }
           enum "dsa" {
             description "DSA encryption";
           }
           enum "ecdsa" {
             description "ECDSA encryption";
           }
         }
       }
     }
     output {
       choice output-tags {
         case actual-tag {
           container cert-key-pair {
             uses cert-key-pair-block;
           }
         }
         case multichassis-tag {
           container multi-routing-engine-results {
             list multi-routing-engine-item {
               leaf re-name {
                 type string;
               }
               choice output-tags {
                 case actual-tag {
                   container cert-key-pair {
                     uses cert-key-pair-block;
                   }
                 }
               }
             }
           }
         }
       }
     }
   }
   rpc generate-pki-certificate-request {
     description "Generate the certificate request in PKCS-10 format";
     junos:command "request security pki generate-certificate-request";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
       }
       leaf email {
         description "Email address";
         type string;
       }
     }
     output {
       choice output-tags {
         case output-tag {
           leaf output {
             type string;
           }
         }
         case multichassis-tag {
           anyxml multi-routing-engine-results;
         }
       }
     }
   }
   rpc load-pki-ca-certificate {
     description "Load the certificate onto the routing platform";
     junos:command "request security pki ca-certificate load";
     input {
       uses command-forwarding;
       leaf ca-profile {
         description "Certificate authority profile";
         type string {
           length "1 .. 32";
           junos:posix-pattern "![/%. ]";
           junos:pattern-message "Must not contain \'/\', %, \'.\' or a space";
         }
         mandatory true;
       }
       choice daemon-select {
         case logical-system {
         }
       }
       leaf filename {
         description "File pathname containing certificate to load";
         type string;
         mandatory true;
       }
     }
     output {
       choice output-tags {
         case actual-tag {
           container cert-ca-load-status {
             uses cert-ca-load-status-block;
           }
         }
         case multichassis-tag {
           container multi-routing-engine-results {
             list multi-routing-engine-item {
               leaf re-name {
                 type string;
               }
               choice output-tags {
                 case actual-tag {
                   container cert-ca-load-status {
                     uses cert-ca-load-status-block;
                   }
                 }
               }
             }
           }
         }
       }
     }
   }
   rpc request-security-pki-ca-profile-group {
     description "Perform operations on group of Certificate-authority(CA) certificates";
     junos:command "request security pki ca-certificate ca-profile-group";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case actual-tag {
           anyxml ca-profile-group;
         }
         case multichassis-tag {
           anyxml multi-routing-engine-results;
         }
       }
     }
   }
   rpc request-default-trusted-ca-certs {
     description "Perform actions on default trusted ca certificates";
     junos:command "request security pki ca-certificate ca-profile-group default-trusted-ca-certs";
     input {
       uses command-forwarding;
     }
     output {
       choice output-tags {
         case output-tag {
           leaf output {
             type string;
           }
         }
         case multichassis-tag {
           anyxml multi-routing-engine-results;
         }
       }
     }
   }
   rpc request-default-trusted-ca-certs-download {
     description "Download default trusted CA certs from a CDN server";
     junos:command "request security pki ca-certificate ca-profile-group default-trusted-ca-certs download";
     input {
       uses command-forwarding;
     }
     output {
       choice output-tags {
         case actual-tag {
           container default-trusted-ca-certs-download {
             uses default-trusted-ca-certs-download-block;
           }
         }
         case multichassis-tag {
           container multi-routing-engine-results {
             list multi-routing-engine-item {
               leaf re-name {
                 type string;
               }
               choice output-tags {
                 case actual-tag {
                   container default-trusted-ca-certs-download {
                     uses default-trusted-ca-certs-download-block;
                   }
                 }
               }
             }
           }
         }
       }
     }
   }
   rpc request-default-trusted-ca-certs-download-cs {
     description "Check connectivity to CDN server to download default trusted CA certs";
     junos:command "request security pki ca-certificate ca-profile-group default-trusted-ca-certs download check-server";
     input {
       uses command-forwarding;
     }
     output {
       choice output-tags {
         case actual-tag {
           container default-trusted-ca-certs-download-cs {
             uses default-trusted-ca-certs-download-cs-block;
           }
         }
         case multichassis-tag {
           container multi-routing-engine-results {
             list multi-routing-engine-item {
               leaf re-name {
                 type string;
               }
               choice output-tags {
                 case actual-tag {
                   container default-trusted-ca-certs-download-cs {
                     uses default-trusted-ca-certs-download-cs-block;
                   }
                 }
               }
             }
           }
         }
       }
     }
   }
   rpc request-default-trusted-ca-certs-download-status {
     description "Check current status of default trusted CA certs downloaded from CDN server";
     junos:command "request security pki ca-certificate ca-profile-group default-trusted-ca-certs download status";
     input {
       uses command-forwarding;
     }
     output {
       choice output-tags {
         case actual-tag {
           container default-trusted-ca-certs-download-status {
             uses default-trusted-ca-certs-download-status-block;
           }
         }
         case multichassis-tag {
           container multi-routing-engine-results {
             list multi-routing-engine-item {
               leaf re-name {
                 type string;
               }
               choice output-tags {
                 case actual-tag {
                   container default-trusted-ca-certs-download-status {
                     uses default-trusted-ca-certs-download-status-block;
                   }
                 }
               }
             }
           }
         }
       }
     }
   }
   rpc request-security-pki-ca-profile-group-load {
     description "Load the certificate group onto the routing platform";
     junos:command "request security pki ca-certificate ca-profile-group load";
     input {
       uses command-forwarding;
       choice daemon-select {
         case logical-system {
         }
       }
       leaf ca-group-name {
         description "CA group identifier";
         type string {
           length "1 .. 24";
           junos:posix-pattern "![/ %]";
           junos:pattern-message "Must not contain \'/\', % or a space";
         }
         mandatory true;
       }
       leaf filename {
         description "File pathname containing certificate to load";
         type string;
         mandatory true;
       }
     }
     output {
       choice output-tags {
         case output-tag {
           leaf output {
             type string;
           }
         }
         case actual-tag {
           anyxml ca-profile-group-load;
         }
         case multichassis-tag {
           anyxml multi-routing-engine-results;
         }
       }
     }
   }
   rpc verify-pki-ca-certificate {
     description "Verify the certificate";
     junos:command "request security pki ca-certificate verify";
     input {
       uses command-forwarding;
       choice daemon-select {
         case logical-system {
         }
       }
       leaf ca-profile {
         description "Certificate authority profile";
         type string {
           length "1 .. 32";
           junos:posix-pattern "![/%. ]";
           junos:pattern-message "Must not contain \'/\', %, \'.\' or a space";
         }
         mandatory true;
       }
     }
     output {
       choice output-tags {
         case output-tag {
           leaf output {
             type string;
           }
         }
         case multichassis-tag {
           anyxml multi-routing-engine-results;
         }
       }
     }
   }
   rpc request-security-local-certificate-enroll {
     description "Enroll router certificate with CA online";
     junos:command "request security pki local-certificate enroll";
     input {
       uses command-forwarding;
       leaf certificate-id {
         description "Certificate identifier";
         status deprecated;
         type string {
           length "1 .. 32";
           junos:posix-pattern "![/%. ]";
           junos:pattern-message "Must not contain \'/\', %, \'.\' or a space";
         }
         mandatory true;
       }
       leaf ca-profile {
         description "Certificate authority profile";
         status deprecated;
         type string {
           length "1 .. 32";
           junos:posix-pattern "![/%. ]";
           junos:pattern-message "Must not contain \'/\', %, \'.\' or a space";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
       choice daemon-select {
         case logical-system {
         }
       }
       leaf domain-name {
         description "Fully qualified domain name";
         status deprecated;
         type string;
       }
       leaf email {
         description "Email address";
         status deprecated;
         type string;
       }
     }
     output {
       choice output-tags {
         case output-tag {
           leaf output {
             type string;
           }
         }
         case actual-tag {
           anyxml local-certificate-enroll;
         }
         case multichassis-tag {
           anyxml multi-routing-engine-results;
         }
       }
     }
   }
   rpc request-security-local-certificate-enroll-cmpv2 {
     description "Enroll certificate using CMPv2 protocol";
     junos:command "request security pki local-certificate enroll cmpv2";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
           junos:posix-pattern "![/%. ]";
           junos:pattern-message "Must not contain \'/\', %, \'.\' or a space";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
     output {
       choice output-tags {
         case output-tag {
           leaf output {
             type string;
           }
         }
         case actual-tag {
           anyxml local-certificate-enroll-cmpv2;
         }
         case multichassis-tag {
           anyxml multi-routing-engine-results;
         }
       }
     }
   }
   rpc request-security-local-certificate-enroll-acme {
     description "Enroll certificate using ACME protocol";
     junos:command "request security pki local-certificate enroll acme";
     input {
       uses command-forwarding;
       choice daemon-select {
         case logical-system {
         }
       }
       leaf acme-key-id {
         description "ACME account key identifier";
         type string {
           length "1 .. 32";
           junos:posix-pattern "![/%. ]";
           junos:pattern-message "Must not contain \'/\', %, \'.\' or a space";
         }
         mandatory true;
       }
       leaf certificate-id {
         description "Certificate identifier";
         type string {
           length "1 .. 32";
           junos:posix-pattern "![/%. ]";
           junos:pattern-message "Must not contain \'/\', %, \'.\' or a space";
         }
         mandatory true;
       }
       leaf letsencrypt-enrollment {
         description "Whether the enrollment server is Let's Encrypt or not";
         type enumeration {
           enum "yes" {
             description "Certificate enrollment using Let's Encrypt";
           }
           enum "no" {
             description "Certificate enrollment using other server";
           }
         }
         mandatory true;
       }
       leaf terms-of-service {
         description "Service agreement of Let's Encrypt (https://letsencrypt.org/repository)";
         type enumeration {
           enum "agree" {
             description "Agreed to terms of service";
           }
           enum "disagree" {
             description "Disagree to terms of service";
           }
         }
       }
       leaf domain-names {
         description "Fully qualified domain names for subject-alt-name separated by comma. Maximum limit is 5";
         type string {
           junos:posix-pattern "![_ ]";
           junos:pattern-message "Must not contain \'_\' or space";
         }
         mandatory true;
       }
       leaf email {
         description "Email address";
         type string;
         mandatory true;
       }
       leaf ca-profile {
         description "Certificate authority profile";
         type string {
           length "1 .. 32";
           junos:posix-pattern "![/%. ]";
           junos:pattern-message "Must not contain \'/\', %, \'.\' or a space";
         }
         mandatory true;
       }
     }
     output {
       choice output-tags {
         case output-tag {
           leaf output {
             type string;
           }
         }
         case actual-tag {
           anyxml local-certificate-enroll-acme;
         }
         case multichassis-tag {
           anyxml multi-routing-engine-results;
         }
       }
     }
   }
   rpc request-security-local-certificate-enroll-scep {
     description "Enroll end-entity certificate using SCEP protocol";
     junos:command "request security pki local-certificate enroll scep";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
         mandatory true;
       }
       leaf challenge-password {
         description "Password used by CA for enrollment and revocation";
         type string;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (default value)";
           }
           enum "sha-256" {
             description "SHA-256 digests";
           }
         }
       }
     }
     output {
       choice output-tags {
         case output-tag {
           leaf output {
             type string;
           }
         }
         case actual-tag {
           anyxml local-certificate-enroll-scep;
         }
         case multichassis-tag {
           anyxml multi-routing-engine-results;
         }
       }
     }
   }
   rpc request-security-local-certificate-re-enroll {
     description "Re-enroll router certificate with CA online";
     junos:command "request security pki local-certificate re-enroll";
     input {
       uses command-forwarding;
     }
     output {
       choice output-tags {
         case output-tag {
           leaf output {
             type string;
           }
         }
         case actual-tag {
           anyxml local-certificate-re-enroll;
         }
         case multichassis-tag {
           anyxml multi-routing-engine-results;
         }
       }
     }
   }
   rpc request-security-local-cert-re-enroll-acme {
     description "Enroll certificate using ACME protocol";
     junos:command "request security pki local-certificate re-enroll acme";
     input {
       uses command-forwarding;
       choice daemon-select {
         case logical-system {
         }
       }
       leaf acme-key-id {
         description "ACME account key identifier";
         type string {
           length "1 .. 32";
           junos:posix-pattern "![/%. ]";
           junos:pattern-message "Must not contain \'/\', %, \'.\' or a space";
         }
         mandatory true;
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
     output {
       choice output-tags {
         case output-tag {
           leaf output {
             type string;
           }
         }
         case actual-tag {
           anyxml local-cert-re-enroll-acme;
         }
         case multichassis-tag {
           anyxml multi-routing-engine-results;
         }
       }
     }
   }
   rpc request-security-local-cert-re-enroll-cmpv2 {
     description "Enroll certificate using CMPv2 protocol";
     junos:command "request security pki local-certificate re-enroll cmpv2";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
     output {
       choice output-tags {
         case output-tag {
           leaf output {
             type string;
           }
         }
         case actual-tag {
           anyxml local-cert-re-enroll-cmpv2;
         }
         case multichassis-tag {
           anyxml multi-routing-engine-results;
         }
       }
     }
   }
   rpc request-security-local-cert-re-enroll-scep {
     description "Enroll end-entity certificate using SCEP protocol";
     junos:command "request security pki local-certificate re-enroll scep";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf challenge-password {
         description "Password used by CA for enrollment and revocation";
         type string;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
     output {
       choice output-tags {
         case output-tag {
           leaf output {
             type string;
           }
         }
         case actual-tag {
           anyxml local-cert-re-enroll-scep;
         }
         case multichassis-tag {
           anyxml multi-routing-engine-results;
         }
       }
     }
   }
   rpc request-security-local-certificate-export {
     description "Export Certificate";
     junos:command "request security pki local-certificate export";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
     output {
       choice output-tags {
         case output-tag {
           leaf output {
             type string;
           }
         }
         case actual-tag {
           anyxml local-certificate-export;
         }
         case multichassis-tag {
           anyxml multi-routing-engine-results;
         }
       }
     }
   }
   rpc load-pki-local-certificate {
     description "Load the certificate onto the routing platform";
     junos:command "request security pki local-certificate load";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       choice output-tags {
         case actual-tag {
           container cert-load-status {
             uses cert-load-status-block;
           }
         }
         case multichassis-tag {
           container multi-routing-engine-results {
             list multi-routing-engine-item {
               leaf re-name {
                 type string;
               }
               choice output-tags {
                 case actual-tag {
                   container cert-load-status {
                     uses cert-load-status-block;
                   }
                 }
               }
             }
           }
         }
       }
     }
   }
   rpc verify-pki-local-certificate {
     description "Verify the certificate";
     junos:command "request security pki local-certificate verify";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
     }
     output {
       choice output-tags {
         case output-tag {
           leaf output {
             type string;
           }
         }
         case multichassis-tag {
           anyxml multi-routing-engine-results;
         }
       }
     }
   }
   rpc generate-pki-self-signed-local-certificate {
     description "Generate a self-signed certificate";
     junos:command "request security pki local-certificate generate-self-signed";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
         mandatory true;
       }
       leaf ip-address {
         description "Static IP address of the device";
         type jt:ipaddr;
       }
       leaf ipv6-address {
         description "Static IPV6 address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
     output {
       choice output-tags {
         case output-tag {
           leaf output {
             type string;
           }
         }
         case multichassis-tag {
           anyxml multi-routing-engine-results;
         }
       }
     }
   }
   rpc request-security-key-pair-export {
     description "Export Keypair in PEM format";
     junos:command "request security pki key-pair export";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier for keypair";
         type string {
           length "1 .. 32";
           junos:posix-pattern "![/%. ]";
           junos:pattern-message "Must not contain \'/\', %, \'.\' or a space";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
     output {
       choice output-tags {
         case output-tag {
           leaf output {
             type string;
           }
         }
         case actual-tag {
           anyxml key-pair-export;
         }
         case multichassis-tag {
           anyxml multi-routing-engine-results;
         }
       }
     }
   }
   rpc load-pki-crl {
     description "Load the CRL onto the routing platform";
     junos:command "request security pki crl load";
     input {
       uses command-forwarding;
       choice daemon-select {
         case logical-system {
         }
       }
       leaf ca-profile {
         description "Certificate authority profile";
         type string {
           length "1 .. 32";
           junos:posix-pattern "![/%. ]";
           junos:pattern-message "Must not contain \'/\', %, \'.\' or a space";
         }
         mandatory true;
       }
       leaf filename {
         description "Pathname of file containing CRL to load";
         type string;
         mandatory true;
       }
     }
     output {
       choice output-tags {
         case output-tag {
           leaf output {
             type string;
           }
         }
         case multichassis-tag {
           anyxml multi-routing-engine-results;
         }
       }
     }
   }
   rpc request-security-pki-file-sync {
     description "Perform PKI file-sync with MN-HA remote node";
     junos:command "request security pki sync-from-peer";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case actual-tag {
           anyxml pki-file-sync;
         }
         case multichassis-tag {
           anyxml multi-routing-engine-results;
         }
       }
     }
   }
   rpc node-local-generate-key-pair {
     description "Generate RSA, DSA or ECDSA private and public key pair";
     junos:command "request security pki node-local generate-key-pair";
     input {
       uses command-forwarding;
       choice daemon-select {
         case logical-system {
         }
       }
       leaf certificate-id {
         description "Certificate identifier";
         type string {
           length "1 .. 32";
           junos:posix-pattern "![/ %.]";
           junos:pattern-message "Must not contain \'/\', %, \'.\' or a space";
         }
         mandatory true;
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption (Key-Size: 512/1024/2048/4096 bits";
           }
           enum "dsa" {
             description "DSA encryption (Key-Size: 1024/2048/4096 bits)";
           }
           enum "ecdsa" {
             description "ECDSA encryption (Key-Size: 256/384/521 bits)";
           }
         }
       }
     }
     output {
       choice output-tags {
         case actual-tag {
           container cert-key-pair {
             uses cert-key-pair-block;
           }
         }
         case multichassis-tag {
           container multi-routing-engine-results {
             list multi-routing-engine-item {
               leaf re-name {
                 type string;
               }
               choice output-tags {
                 case actual-tag {
                   container cert-key-pair {
                     uses cert-key-pair-block;
                   }
                 }
               }
             }
           }
         }
       }
     }
   }
   rpc node-local-generate-csr {
     description "Generate the certificate request in PKCS-10 format";
     junos:command "request security pki node-local generate-certificate-request";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name for subject-alt-name";
         type string;
       }
       leaf email {
         description "Email address";
         type string;
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
     }
     output {
       choice output-tags {
         case output-tag {
           leaf output {
             type string;
           }
         }
         case actual-tag {
           anyxml node-local-gen-csr;
         }
         case multichassis-tag {
           anyxml multi-routing-engine-results;
         }
       }
     }
   }
   rpc node-local-local-certificate-enroll {
     description "Enroll router certificate with CA online";
     junos:command "request security pki node-local local-certificate enroll";
     input {
       uses command-forwarding;
       leaf certificate-id {
         description "Certificate identifier";
         status deprecated;
         type string {
           length "1 .. 32";
           junos:posix-pattern "![/%. ]";
           junos:pattern-message "Must not contain \'/\', %, \'.\' or a space";
         }
         mandatory true;
       }
       leaf domain-name {
         description "Fully qualified domain name for subject-alt-name";
         status deprecated;
         type string;
       }
       leaf email {
         description "Email address";
         status deprecated;
         type string;
       }
       leaf ca-profile {
         description "Certificate authority profile";
         status deprecated;
         type string {
           length "1 .. 32";
           junos:posix-pattern "![/%. ]";
           junos:pattern-message "Must not contain \'/\', %, \'.\' or a space";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
     }
     output {
       choice output-tags {
         case output-tag {
           leaf output {
             type string;
           }
         }
         case actual-tag {
           anyxml local-certificate-enroll;
         }
         case multichassis-tag {
           anyxml multi-routing-engine-results;
         }
       }
     }
   }
   rpc node-local-local-certificate-enroll-cmpv2 {
     description "Enroll certificate using CMPv2 protocol";
     junos:command "request security pki node-local local-certificate enroll cmpv2";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
           junos:posix-pattern "![/%. ]";
           junos:pattern-message "Must not contain \'/\', %, \'.\' or a space";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
     output {
       choice output-tags {
         case output-tag {
           leaf output {
             type string;
           }
         }
         case actual-tag {
           anyxml local-certificate-enroll-cmpv2;
         }
         case multichassis-tag {
           anyxml multi-routing-engine-results;
         }
       }
     }
   }
   rpc node-local-local-certificate-enroll-scep {
     description "Enroll end-entity certificate using SCEP protocol";
     junos:command "request security pki node-local local-certificate enroll scep";
     input {
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
         mandatory true;
       }
       leaf challenge-password {
         description "Password used by CA for enrollment and revocation";
         type string;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (default value)";
           }
           enum "sha-256" {
             description "SHA-256 digests";
           }
         }
       }
     }
     output {
       choice output-tags {
         case output-tag {
           leaf output {
             type string;
           }
         }
         case actual-tag {
           anyxml local-certificate-enroll-scep;
         }
         case multichassis-tag {
           anyxml multi-routing-engine-results;
         }
       }
     }
   }
   rpc load-node-local-local-certificate {
     description "Load the certificate onto the routing platform";
     junos:command "request security pki node-local local-certificate load";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       choice output-tags {
         case actual-tag {
           container cert-load-status {
             uses cert-load-status-block;
           }
         }
         case multichassis-tag {
           container multi-routing-engine-results {
             list multi-routing-engine-item {
               leaf re-name {
                 type string;
               }
               choice output-tags {
                 case actual-tag {
                   container cert-load-status {
                     uses cert-load-status-block;
                   }
                 }
               }
             }
           }
         }
       }
     }
   }
   rpc verify-pki-node-local-local-certificate {
     description "Verify the certificate";
     junos:command "request security pki node-local local-certificate verify";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
     }
     output {
       choice output-tags {
         case output-tag {
           leaf output {
             type string;
           }
         }
         case actual-tag {
           anyxml node-local-verify-cert;
         }
         case multichassis-tag {
           anyxml multi-routing-engine-results;
         }
       }
     }
   }
   rpc generate-node-local-self-signed-certificate {
     description "Generate a self-signed certificate";
     junos:command "request security pki node-local local-certificate generate-self-signed";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
         mandatory true;
       }
       leaf ip-address {
         description "Static IP address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
     output {
       choice output-tags {
         case output-tag {
           leaf output {
             type string;
           }
         }
         case actual-tag {
           anyxml node-local-self-signed;
         }
         case multichassis-tag {
           anyxml multi-routing-engine-results;
         }
       }
     }
   }
   rpc node-local-local-certificate-re-enroll {
     description "Re-enroll router certificate with CA online";
     junos:command "request security pki node-local local-certificate re-enroll";
     input {
       uses command-forwarding;
     }
     output {
       choice output-tags {
         case output-tag {
           leaf output {
             type string;
           }
         }
         case actual-tag {
           anyxml local-certificate-re-enroll;
         }
         case multichassis-tag {
           anyxml multi-routing-engine-results;
         }
       }
     }
   }
   rpc node-local-local-cert-re-enroll-cmpv2 {
     description "Enroll certificate using CMPv2 protocol";
     junos:command "request security pki node-local local-certificate re-enroll cmpv2";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
     output {
       choice output-tags {
         case output-tag {
           leaf output {
             type string;
           }
         }
         case actual-tag {
           anyxml local-cert-re-enroll-cmpv2;
         }
         case multichassis-tag {
           anyxml multi-routing-engine-results;
         }
       }
     }
   }
   rpc node-local-local-cert-re-enroll-scep {
     description "Enroll end-entity certificate using SCEP protocol";
     junos:command "request security pki node-local local-certificate re-enroll scep";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf challenge-password {
         description "Password used by CA for enrollment and revocation";
         type string;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
     output {
       choice output-tags {
         case output-tag {
           leaf output {
             type string;
           }
         }
         case actual-tag {
           anyxml local-cert-re-enroll-scep;
         }
         case multichassis-tag {
           anyxml multi-routing-engine-results;
         }
       }
     }
   }
   rpc node-local-local-certificate-export {
     description "Export Certificate";
     junos:command "request security pki node-local local-certificate export";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
     output {
       choice output-tags {
         case output-tag {
           leaf output {
             type string;
           }
         }
         case actual-tag {
           anyxml local-certificate-export;
         }
         case multichassis-tag {
           anyxml multi-routing-engine-results;
         }
       }
     }
   }
   rpc node-local-key-pair-export {
     description "Export Keypair in PEM format";
     junos:command "request security pki node-local key-pair export";
     input {
       uses command-forwarding;
       choice daemon-select {
         case logical-system {
         }
       }
       leaf certificate-id {
         description "Certificate identifier for keypair";
         type string {
           length "1 .. 32";
           junos:posix-pattern "![/%. ]";
           junos:pattern-message "Must not contain \'/\', %, \'.\' or a space";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
     output {
       choice output-tags {
         case output-tag {
           leaf output {
             type string;
           }
         }
         case actual-tag {
           anyxml key-pair-export;
         }
         case multichassis-tag {
           anyxml multi-routing-engine-results;
         }
       }
     }
   }
   rpc request-security-pki-ca-profile-group-status {
     description "Status of CA certs in default CA profile group";
     junos:command "request security pki ca-profile-group-status";
     input {
       uses command-forwarding;
       choice daemon-select {
         case logical-system {
         }
       }
       leaf ca-group-name {
         description "CA group identifier";
         type string {
           length "1 .. 24";
           junos:posix-pattern "![/ %]";
           junos:pattern-message "Must not contain \'/\', % or a space";
         }
         mandatory true;
       }
     }
     output {
       choice output-tags {
         case actual-tag {
           container ca-profile-group-cert-status {
             uses ca-profile-group-cert-status-block;
           }
         }
         case multichassis-tag {
           container multi-routing-engine-results {
             list multi-routing-engine-item {
               leaf re-name {
                 type string;
               }
               choice output-tags {
                 case actual-tag {
                   container ca-profile-group-cert-status {
                     uses ca-profile-group-cert-status-block;
                   }
                 }
               }
             }
           }
         }
       }
     }
   }
   rpc verify-integrity-status {
     description "Check the integrity of PKI files (in CC mode)";
     junos:command "request security pki verify-integrity-status";
     input {
       uses command-forwarding;
       choice daemon-select {
         case logical-system {
         }
       }
     }
     output {
       choice output-tags {
         case actual-tag {
           container verify-integrity-status {
             uses verify-integrity-status-block;
           }
         }
         case multichassis-tag {
           container multi-routing-engine-results {
             list multi-routing-engine-item {
               leaf re-name {
                 type string;
               }
               choice output-tags {
                 case actual-tag {
                   container verify-integrity-status {
                     uses verify-integrity-status-block;
                   }
                 }
               }
             }
           }
         }
       }
     }
   }
   rpc request-pki-debug-memory-profile {
     description "Enable or disable memory profile";
     junos:command "request security pki debug-memory-profile";
     input {
       leaf profile-state {
         junos:cli-feature "nokeyword";
         type enumeration {
           enum "enable" {
             description "Enable PKI memory profiling";
           }
           enum "disable" {
             description "Disable PKI memory profiling";
           }
           enum "dump" {
             description "Dump PKI memory profile debug info";
           }
         }
         mandatory true;
       }
     }
     output {
       choice output-tags {
         case output-tag {
           leaf output {
             type string;
           }
         }
         case multichassis-tag {
           anyxml multi-routing-engine-results;
         }
       }
     }
   }
   rpc get-enable-ike-debug {
     description "Enable ike debug";
     junos:command "request security ike debug-enable";
     input {
       uses command-forwarding;
       leaf remote {
         description "Remote ip address";
         type jt:ipaddr;
         mandatory true;
       }
     }
     output {
       choice output-tags {
         case output-tag {
           leaf output {
             type string;
           }
         }
         case multichassis-tag {
           anyxml multi-routing-engine-results;
         }
       }
     }
   }
   rpc get-disable-ike-debug {
     description "Disable ike debug";
     junos:command "request security ike debug-disable";
     input {
       uses command-forwarding;
     }
     output {
       choice output-tags {
         case output-tag {
           leaf output {
             type string;
           }
         }
         case multichassis-tag {
           anyxml multi-routing-engine-results;
         }
       }
     }
   }
   rpc get-support-information {
     description "Generate in-depth system status report";
     junos:command "request support information";
     input {
       uses command-forwarding;
       leaf level {
         junos:cli-feature "nokeyword";
         type enumeration {
           enum "brief" {
             description "Display brief output for selected commands";
           }
         }
       }
       leaf archive {
         description "Archive RSI report";
         type empty;
       }
       leaf with-logs {
         description "Archive log files along with RSI report";
         type empty;
       }
       leaf-list with-components {
         ordered-by user;
         description "Archive log files, components specific report along with generic RSI report";
         type string;
       }
       container with-options {
         leaf component-name {
           description "Archive log files, component specific report along with generic RSI report";
           junos:cli-feature "nokeyword";
           type string;
         }
       }
       container options {
         leaf name {
           junos:cli-feature "nokeyword";
           type string;
         }
         leaf value {
           junos:cli-feature "nokeyword";
           type string;
         }
       }
     }
     output {
       choice output-tags {
         case actual-tag {
           leaf output {
             type string;
           }
         }
         case multichassis-tag {
           container multi-routing-engine-results {
             list multi-routing-engine-item {
               leaf re-name {
                 type string;
               }
               choice output-tags {
                 case actual-tag {
                   leaf output {
                     type string;
                   }
                 }
               }
             }
           }
         }
       }
     }
   }
   rpc revert-redundancy-interface-to-primary {
     description "Revert redundancy interface to its primary";
     junos:command "request interface revert";
     input {
       leaf interface-name {
         description "Name of interface";
         junos:cli-feature "nokeyword";
         type union {
           type jt:interface-wildcard;
           type string {
             pattern "<.*>|$.*";
           }
         }
         mandatory true;
       }
     }
     output {
       choice output-tags {
         case output-tag {
           leaf output {
             type string;
           }
         }
         case multichassis-tag {
           anyxml multi-routing-engine-results;
         }
       }
     }
   }
   rpc switch-redundancy-interface-to-secondary {
     description "Switch redundancy interface over to its secondary";
     junos:command "request interface switchover";
     input {
       leaf interface-name {
         description "Name of interface";
         junos:cli-feature "nokeyword";
         type union {
           type jt:interface-wildcard;
           type string {
             pattern "<.*>|$.*";
           }
         }
         mandatory true;
       }
     }
     output {
       choice output-tags {
         case output-tag {
           leaf output {
             type string;
           }
         }
         case multichassis-tag {
           anyxml multi-routing-engine-results;
         }
       }
     }
   }
   rpc request-interface-link-degade-recover {
     description "Perform manual link recovery";
     junos:command "request interface link-degrade-recover";
     input {
       leaf interface-name {
         description "Name of interface";
         junos:cli-feature "nokeyword";
         type union {
           type jt:interface-device;
           type string {
             pattern "<.*>|$.*";
           }
         }
         mandatory true;
       }
     }
     output {
       choice output-tags {
         case output-tag {
           leaf output {
             type string;
           }
         }
         case multichassis-tag {
           anyxml multi-routing-engine-results;
         }
       }
     }
   }
   rpc request-interface-optics-reset {
     description "Perform manual optics-reset";
     junos:command "request interface optics-reset";
     input {
       leaf transceiver-name {
         description "Transceiver name";
         junos:cli-feature "nokeyword";
         type string {
           junos:posix-pattern "^(xcvr|et)-[0-9]+/[0-9]+/[0-9]+$|et-[0-9]+/[0-9]+/[0-9]+:[0-9]+$";
           junos:pattern-message "Only transceiver name supported (xcvr-<fpc slot>/<pic slot>/<port number>)";
         }
         mandatory true;
       }
     }
     output {
       choice output-tags {
         case output-tag {
           leaf output {
             type string;
           }
         }
         case multichassis-tag {
           anyxml multi-routing-engine-results;
         }
       }
     }
   }
   rpc request-bounce-interface {
     description "Bounce the port";
     junos:command "request interface bounce";
     input {
       leaf interface-name {
         description "Name of the interface";
         junos:cli-feature "nokeyword";
         type string;
         mandatory true;
       }
       leaf interval {
         description "Interval (in secs) between DOWN and UP";
         type union {
           type string {
             pattern "<.*>|$.*";
           }
           type uint32 {
             range "1 .. 30";
           }
         }
       }
     }
     output {
       choice output-tags {
         case actual-tag {
           container bounce-interface {
             uses bounce-interface-block;
           }
         }
         case multichassis-tag {
           container multi-routing-engine-results {
             list multi-routing-engine-item {
               leaf re-name {
                 type string;
               }
               choice output-tags {
                 case actual-tag {
                   container bounce-interface {
                     uses bounce-interface-block;
                   }
                 }
               }
             }
           }
         }
       }
     }
   }
   rpc extension-service-start {
     description "Start JET application";
     junos:command "request extension-service start";
     input {
       leaf invoke-debugger {
         description "Invoke extension-service in debugger mode";
         type enumeration {
           enum "cli" {
             description "Invoke debugger in cli";
           }
         }
       }
       leaf application-name {
         description "Application name";
         junos:cli-feature "nokeyword";
         type jt:filename;
         mandatory true;
       }
     }
     output {
       choice output-tags {
         case output-tag {
           leaf output {
             type string;
           }
         }
         case multichassis-tag {
           anyxml multi-routing-engine-results;
         }
       }
     }
   }
   rpc extension-service-stop {
     description "Stop JET application";
     junos:command "request extension-service stop";
     input {
       leaf application-name {
         description "Application name";
         junos:cli-feature "nokeyword";
         type jt:filename;
         mandatory true;
       }
     }
     output {
       choice output-tags {
         case output-tag {
           leaf output {
             type string;
           }
         }
         case multichassis-tag {
           anyxml multi-routing-engine-results;
         }
       }
     }
   }
   rpc extension-service-restart {
     description "Restart JET application";
     junos:command "request extension-service restart";
     input {
       leaf application-name {
         description "Application name";
         junos:cli-feature "nokeyword";
         type jt:filename;
         mandatory true;
       }
     }
     output {
       choice output-tags {
         case output-tag {
           leaf output {
             type string;
           }
         }
         case multichassis-tag {
           anyxml multi-routing-engine-results;
         }
       }
     }
   }
   rpc extension-service-daemonize-restart {
     description "Restart daemonize JET application";
     junos:command "request extension-service restart-daemonize-app";
     input {
       leaf application-name {
         description "Application name";
         junos:cli-feature "nokeyword";
         type jt:filename;
         mandatory true;
       }
     }
     output {
       choice output-tags {
         case actual-tag {
           container extension-service-daemonize-restart-status {
             uses extension-service-daemonize-restart-status-block;
           }
         }
         case multichassis-tag {
           container multi-routing-engine-results {
             list multi-routing-engine-item {
               leaf re-name {
                 type string;
               }
               choice output-tags {
                 case actual-tag {
                   container extension-service-daemonize-restart-status {
                     uses extension-service-daemonize-restart-status-block;
                   }
                 }
               }
             }
           }
         }
       }
     }
   }
   rpc mgd-jnu-role {
     description "JNU Role";
     junos:command "request jnu role";
     input {
       uses command-forwarding;
       leaf jnu-role {
         junos:cli-feature "nokeyword";
         type enumeration {
           enum "controller" {
             description "Controller";
           }
           enum "satellite" {
             description "Satellite";
           }
         }
         mandatory true;
       }
       leaf delete {
         description "Delete JNU";
         type empty;
       }
     }
     output {
       choice output-tags {
         case output-tag {
           leaf output {
             type string;
           }
         }
         case multichassis-tag {
           anyxml multi-routing-engine-results;
         }
       }
     }
   }
   rpc mgd-jnu-schema-delete {
     description "Delete a JNU satellite schema";
     junos:command "request jnu schema delete";
     input {
       leaf model {
         description "Satellite model";
         type string;
         mandatory true;
       }
       leaf version {
         description "Satellite version";
         type string {
           junos:posix-pattern "^[[:digit:]][[:alnum:]_.-]+$";
           junos:pattern-message "Version should begin with a number";
         }
         mandatory true;
       }
     }
     output {
       choice output-tags {
         case output-tag {
           leaf output {
             type string;
           }
         }
         case multichassis-tag {
           anyxml multi-routing-engine-results;
         }
       }
     }
   }
   rpc mgd-jnu-schema-merge {
     description "Merge JNU schema to this controller";
     junos:command "request jnu schema merge";
     input {
       leaf satschema {
         description "Satellite Schema Path";
         type jt:filename;
         mandatory true;
       }
       leaf conschema {
         description "Controller Schema Path";
         type jt:filename;
         mandatory true;
       }
     }
     output {
       choice output-tags {
         case output-tag {
           leaf output {
             type string;
           }
         }
         case multichassis-tag {
           anyxml multi-routing-engine-results;
         }
       }
     }
   }
   rpc mgd-jnu-schema-add {
     description "Add JNU schema to this controller";
     junos:command "request jnu schema add";
     input {
       leaf model {
         description "Satellite model";
         type string;
         mandatory true;
       }
       leaf version {
         description "Satellite version";
         type string {
           junos:posix-pattern "^[[:digit:]][[:alnum:]_.-]+$";
           junos:pattern-message "Version should begin with a number";
         }
         mandatory true;
       }
       leaf filename {
         description "Satellite schema TLV package filename";
         junos:cli-feature "nokeyword";
         type jt:filename;
         mandatory true;
       }
       leaf model-id {
         description "Satellite model id";
         type union {
           type uint32;
           type string {
             pattern "<.*>|$.*";
           }
         }
       }
     }
     output {
       choice output-tags {
         case output-tag {
           leaf output {
             type string;
           }
         }
         case multichassis-tag {
           anyxml multi-routing-engine-results;
         }
       }
     }
   }
   rpc request-jnu-satellite-sync {
     description "Sync satellite with controller";
     junos:command "request jnu satellite sync";
     output {
       choice output-tags {
         case output-tag {
           leaf output {
             type string;
           }
         }
         case multichassis-tag {
           anyxml multi-routing-engine-results;
         }
       }
     }
   }
   rpc clear-jdaf-command-client-stats {
     description "Clear JDAF client side statistics";
     junos:command "request jdaf clear statistics service cmd client";
     output {
       choice output-tags {
         case actual-tag {
           container jdaf-request-no-response {
             uses jdaf-request-no-response-block;
           }
         }
         case multichassis-tag {
           container multi-routing-engine-results {
             list multi-routing-engine-item {
               leaf re-name {
                 type string;
               }
               choice output-tags {
                 case actual-tag {
                   container jdaf-request-no-response {
                     uses jdaf-request-no-response-block;
                   }
                 }
               }
             }
           }
         }
       }
     }
   }
   rpc clear-jdaf-command-server-stats {
     description "Clear JDAF server statistics";
     junos:command "request jdaf clear statistics service cmd server";
     output {
       choice output-tags {
         case output-tag {
           leaf output {
             type string;
           }
         }
         case multichassis-tag {
           anyxml multi-routing-engine-results;
         }
       }
     }
   }
   rpc clear-jdaf-config-client-stats {
     description "Clear JDAF client side statistics";
     junos:command "request jdaf clear statistics service config client";
     output {
       choice output-tags {
         case actual-tag {
           container jdaf-request-no-response {
             uses jdaf-request-no-response-block;
           }
         }
         case multichassis-tag {
           container multi-routing-engine-results {
             list multi-routing-engine-item {
               leaf re-name {
                 type string;
               }
               choice output-tags {
                 case actual-tag {
                   container jdaf-request-no-response {
                     uses jdaf-request-no-response-block;
                   }
                 }
               }
             }
           }
         }
       }
     }
   }
   rpc clear-jdaf-config-server-stats {
     description "Clear JDAF server statistics";
     junos:command "request jdaf clear statistics service config server";
     output {
       choice output-tags {
         case output-tag {
           leaf output {
             type string;
           }
         }
         case multichassis-tag {
           anyxml multi-routing-engine-results;
         }
       }
     }
   }
   rpc clear-jdaf-firewall-client-stats {
     description "Clear JDAF client side statistics";
     junos:command "request jdaf clear statistics service firewall client";
     input {
       leaf client-id {
         description "Client id";
         junos:cli-feature "nokeyword";
         default "0";
         type union {
           type uint32;
           type string {
             pattern "<.*>|$.*";
           }
         }
       }
     }
     output {
       choice output-tags {
         case actual-tag {
           container jdaf-request-no-response {
             uses jdaf-request-no-response-block;
           }
         }
         case multichassis-tag {
           container multi-routing-engine-results {
             list multi-routing-engine-item {
               leaf re-name {
                 type string;
               }
               choice output-tags {
                 case actual-tag {
                   container jdaf-request-no-response {
                     uses jdaf-request-no-response-block;
                   }
                 }
               }
             }
           }
         }
       }
     }
   }
   rpc clear-jdaf-firewall-server-stats {
     description "Clear JDAF server statistics";
     junos:command "request jdaf clear statistics service firewall server";
     output {
       choice output-tags {
         case output-tag {
           leaf output {
             type string;
           }
         }
         case multichassis-tag {
           anyxml multi-routing-engine-results;
         }
       }
     }
   }
   rpc clear-jdaf-interface-client-stats {
     description "Clear JDAF client side statistics";
     junos:command "request jdaf clear statistics service interface client";
     input {
       leaf client-id {
         description "Client id";
         junos:cli-feature "nokeyword";
         default "0";
         type union {
           type uint32;
           type string {
             pattern "<.*>|$.*";
           }
         }
       }
     }
     output {
       choice output-tags {
         case actual-tag {
           container jdaf-request-no-response {
             uses jdaf-request-no-response-block;
           }
         }
         case multichassis-tag {
           container multi-routing-engine-results {
             list multi-routing-engine-item {
               leaf re-name {
                 type string;
               }
               choice output-tags {
                 case actual-tag {
                   container jdaf-request-no-response {
                     uses jdaf-request-no-response-block;
                   }
                 }
               }
             }
           }
         }
       }
     }
   }
   rpc clear-jdaf-interface-server-stats {
     description "Clear JDAF server statistics";
     junos:command "request jdaf clear statistics service interface server";
     output {
       choice output-tags {
         case output-tag {
           leaf output {
             type string;
           }
         }
         case multichassis-tag {
           anyxml multi-routing-engine-results;
         }
       }
     }
   }
   rpc clear-jdaf-route-client-stats {
     description "Clear JDAF client side statistics";
     junos:command "request jdaf clear statistics service route client";
     input {
       leaf client-id {
         description "Client id";
         junos:cli-feature "nokeyword";
         default "0";
         type union {
           type uint32;
           type string {
             pattern "<.*>|$.*";
           }
         }
       }
     }
     output {
       choice output-tags {
         case actual-tag {
           container jdaf-request-no-response {
             uses jdaf-request-no-response-block;
           }
         }
         case multichassis-tag {
           container multi-routing-engine-results {
             list multi-routing-engine-item {
               leaf re-name {
                 type string;
               }
               choice output-tags {
                 case actual-tag {
                   container jdaf-request-no-response {
                     uses jdaf-request-no-response-block;
                   }
                 }
               }
             }
           }
         }
       }
     }
   }
   rpc clear-jdaf-route-server-stats {
     description "Clear JDAF server statistics";
     junos:command "request jdaf clear statistics service route server";
     output {
       choice output-tags {
         case output-tag {
           leaf output {
             type string;
           }
         }
         case multichassis-tag {
           anyxml multi-routing-engine-results;
         }
       }
     }
   }
   rpc request-dhcp-server-reconfigure-information {
     description "Perform DHCP server reconfigure operation";
     junos:command "request dhcp server reconfigure";
     input {
       choice reconfigure-choice {
         case address {
           leaf address {
             description "IP address or MAC address or Session Id of DHCP client binding";
             junos:cli-feature "nokeyword";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-server-reconfigure-interface {
     description "Name of interface";
     junos:command "request dhcp server reconfigure interface";
     input {
       leaf interface-name {
         description "Name of interface";
         junos:cli-feature "nokeyword";
         type string;
         mandatory true;
       }
     }
     output {
       choice output-tags {
         case output-tag {
           leaf output {
             type string;
           }
         }
         case multichassis-tag {
           anyxml multi-routing-engine-results;
         }
       }
     }
   }
   rpc request-dhcp-server-regenerate-persistent-file {
     description "Triggers the flat file backup operation";
     junos:command "request dhcp server regenerate-persistent-storage";
     output {
       choice output-tags {
         case output-tag {
           leaf output {
             type string;
           }
         }
         case multichassis-tag {
           anyxml multi-routing-engine-results;
         }
       }
     }
   }
   rpc request-dhcp-server-restore-client-from-file {
     description "Triggers the flat file restore operation";
     junos:command "request dhcp server restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-client-renew-information {
     description "Request DHCP client renew";
     junos:command "request dhcp client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-leasequery {
     description "Perform DHCP relay leasequery operation";
     junos:command "request dhcp relay leasequery";
     input {
       leaf address {
         description "Query by IPv4 address or mac-address or Client-ID";
         junos:cli-feature "nokeyword";
         type string;
         mandatory true;
       }
       leaf gateway-address {
         description "Giaddr of leasequery packet";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-bulk-leasequery {
     description "Perform DHCP relay bulk leasequery operation";
     junos:command "request dhcp relay bulk-leasequery";
     input {
       leaf address {
         description "Query by IPv4 address or mac-address or Client-ID";
         junos:cli-feature "nokeyword";
         type string;
       }
       choice query-server {
         case server-address {
           leaf server-address {
             description "Send leasequery to server address";
             type string;
           }
         }
         case server-group {
           leaf server-group {
             description "Send leasequery to servers in server-group";
             type string;
           }
         }
       }
       leaf all-configured-ip {
         description "Query by all-configure-ip-addresss";
         type empty;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-bulk-leasequery-relay-id {
     description "Query by relay-id";
     junos:command "request dhcp relay bulk-leasequery relay-id";
     input {
       leaf relay-id {
         description "Query by relay-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-bulk-leasequery-remote-id {
     description "Query by remote-id";
     junos:command "request dhcp relay bulk-leasequery remote-id";
     input {
       leaf remote-id {
         description "Query by remote-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-active-leasequery {
     description "Request DHCP active-leasequery operations";
     junos:command "request dhcp relay active-leasequery";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-alq-peer {
     description "Active-leasequery peer";
     junos:command "request dhcp relay active-leasequery restart peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-relay-alq-interface {
     description "Active-leasequery interface";
     junos:command "request dhcp relay active-leasequery restart interface";
     input {
       leaf interface-name {
         description "Active-leasequery interface name";
         junos:cli-feature "nokeyword";
         type string;
         mandatory true;
       }
     }
     output {
       choice output-tags {
         case output-tag {
           leaf output {
             type string;
           }
         }
         case multichassis-tag {
           anyxml multi-routing-engine-results;
         }
       }
     }
   }
   rpc request-dhcp-relay-regenerate-persistent-file {
     description "Triggers the flat file backup operation";
     junos:command "request dhcp relay regenerate-persistent-storage";
     output {
       choice output-tags {
         case output-tag {
           leaf output {
             type string;
           }
         }
         case multichassis-tag {
           anyxml multi-routing-engine-results;
         }
       }
     }
   }
   rpc request-dhcp-relay-restore-client-from-file {
     description "Triggers the flat file restore operation";
     junos:command "request dhcp relay restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcp-regenerate-persistent-file {
     description "Triggers the flat file backup operation";
     junos:command "request dhcp regenerate-persistent-storage";
     output {
       choice output-tags {
         case output-tag {
           leaf output {
             type string;
           }
         }
         case multichassis-tag {
           anyxml multi-routing-engine-results;
         }
       }
     }
   }
   rpc request-dhcp-restore-client-from-file {
     description "Triggers the flat file restore operation";
     junos:command "request dhcp restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-client-renew-information {
     description "Request DHCP client renew";
     junos:command "request dhcpv6 client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-server-reconfigure-information {
     description "Perform DHCPv6 server reconfigure operation";
     junos:command "request dhcpv6 server reconfigure";
     input {
       choice reconfigure-choice {
         case address {
           leaf address {
             description "IPv6 Prefix, session-id or CID of DHCPv6 client binding";
             junos:cli-feature "nokeyword";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-server-reconfigure-interface {
     description "Name of interface";
     junos:command "request dhcpv6 server reconfigure interface";
     input {
       leaf interface-name {
         description "Name of interface";
         junos:cli-feature "nokeyword";
         type string;
         mandatory true;
       }
     }
     output {
       choice output-tags {
         case output-tag {
           leaf output {
             type string;
           }
         }
         case multichassis-tag {
           anyxml multi-routing-engine-results;
         }
       }
     }
   }
   rpc request-dhcpv6-server-regenerate-persistent-file {
     description "Triggers the flat file backup operation";
     junos:command "request dhcpv6 server regenerate-persistent-storage";
     output {
       choice output-tags {
         case output-tag {
           leaf output {
             type string;
           }
         }
         case multichassis-tag {
           anyxml multi-routing-engine-results;
         }
       }
     }
   }
   rpc request-dhcpv6-server-restore-client-from-file {
     description "Triggers the flat file restore operation";
     junos:command "request dhcpv6 server restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-leasequery {
     description "Perform DHCPv6 relay leasequery operation";
     junos:command "request dhcpv6 relay leasequery";
     input {
       leaf address {
         description "Query by IPv6 Prefix or CID of DHCPv6 client binding";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-bulk-leasequery {
     description "Perform DHCPv6 relay bulk leasequery operation";
     junos:command "request dhcpv6 relay bulk-leasequery";
     input {
       leaf address {
         description "Query by IPv6 Prefix or CID of DHCPv6 client binding";
         junos:cli-feature "nokeyword";
         type string;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-bulk-leasequery-relay-id {
     description "Query by relay-id";
     junos:command "request dhcpv6 relay bulk-leasequery relay-id";
     input {
       leaf relay-id {
         description "Query by relay-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-bulk-leasequery-link-addr {
     description "Query by link-address";
     junos:command "request dhcpv6 relay bulk-leasequery link-addr";
     input {
       leaf link-addr {
         description "Query by link-address";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-bulk-leasequery-remote-id {
     description "Query by remote-id";
     junos:command "request dhcpv6 relay bulk-leasequery remote-id";
     input {
       leaf remote-id {
         description "Query by remote-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-regenerate-persistent-file {
     description "Triggers the flat file backup operation";
     junos:command "request dhcpv6 relay regenerate-persistent-storage";
     output {
       choice output-tags {
         case output-tag {
           leaf output {
             type string;
           }
         }
         case multichassis-tag {
           anyxml multi-routing-engine-results;
         }
       }
     }
   }
   rpc request-dhcpv6-relay-restore-client-from-file {
     description "Triggers the flat file restore operation";
     junos:command "request dhcpv6 relay restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-active-leasequery {
     description "Request DHCP active-leasequery operations";
     junos:command "request dhcpv6 relay active-leasequery";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-alq-peer {
     description "Active-leasequery peer";
     junos:command "request dhcpv6 relay active-leasequery restart peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-dhcpv6-relay-alq-interface {
     description "Active-leasequery interface";
     junos:command "request dhcpv6 relay active-leasequery restart interface";
     input {
       leaf interface-name {
         description "Active-leasequery interface name";
         junos:cli-feature "nokeyword";
         type string;
         mandatory true;
       }
     }
     output {
       choice output-tags {
         case output-tag {
           leaf output {
             type string;
           }
         }
         case multichassis-tag {
           anyxml multi-routing-engine-results;
         }
       }
     }
   }
   rpc request-as-ra-guard-forward-interface {
     description "Name of interface";
     junos:command "request access-security router-advertisement-guard-forward interface";
     input {
       leaf interface-name {
         description "Name of interface";
         junos:cli-feature "nokeyword";
         type union {
           type jt:interface-name;
           type string {
             pattern "<.*>|$.*";
           }
         }
         mandatory true;
       }
     }
     output {
       choice output-tags {
         case output-tag {
           leaf output {
             type string;
           }
         }
         case multichassis-tag {
           anyxml multi-routing-engine-results;
         }
       }
     }
   }
   rpc request-as-ra-guard-block-interface {
     description "Name of interface";
     junos:command "request access-security router-advertisement-guard-block interface";
     input {
       leaf interface-name {
         description "Name of interface";
         junos:cli-feature "nokeyword";
         type union {
           type jt:interface-name;
           type string {
             pattern "<.*>|$.*";
           }
         }
         mandatory true;
       }
     }
     output {
       choice output-tags {
         case output-tag {
           leaf output {
             type string;
           }
         }
         case multichassis-tag {
           anyxml multi-routing-engine-results;
         }
       }
     }
   }
   rpc request-as-ra-guard-learn-interface {
     description "RA Guard Learn on an Interface";
     junos:command "request access-security router-advertisement-guard-learn interface";
     input {
       leaf interface {
         description "RA Guard Learn on an interface";
         junos:cli-feature "nokeyword";
         type union {
           type jt:interface-name;
           type string {
             pattern "<.*>|$.*";
           }
         }
         mandatory true;
       }
       leaf duration {
         description "Time window for RA Guard learn";
         units "seconds";
         type union {
           type string {
             pattern "<.*>|$.*";
           }
           type uint32 {
             range "1 .. 3600";
           }
         }
         mandatory true;
       }
     }
     output {
       choice output-tags {
         case output-tag {
           leaf output {
             type string;
           }
         }
         case multichassis-tag {
           anyxml multi-routing-engine-results;
         }
       }
     }
   }
   rpc twamp-test-start {
     description "Start TWAMP test sessions";
     junos:command "request services rpm twamp start client";
     input {
       leaf control-connection {
         description "Name of the control connection";
         junos:cli-feature "nokeyword";
         default "all";
         type string;
       }
     }
     output {
       choice output-tags {
         case output-tag {
           leaf output {
             type string;
           }
         }
         case multichassis-tag {
           anyxml multi-routing-engine-results;
         }
       }
     }
   }
   rpc twamp-test-stop {
     description "Stop TWAMP test sessions";
     junos:command "request services rpm twamp stop client";
     input {
       leaf control-connection {
         description "Name of the control connection";
         junos:cli-feature "nokeyword";
         default "all";
         type string;
       }
     }
     output {
       choice output-tags {
         case output-tag {
           leaf output {
             type string;
           }
         }
         case multichassis-tag {
           anyxml multi-routing-engine-results;
         }
       }
     }
   }
   rpc request-netconf-trace {
     description "NETCONF tracing";
     junos:command "request services netconf trace";
     input {
       leaf on-demand {
         description "Control on-demand tracing";
         junos:cli-feature "nokeyword";
         type enumeration {
           enum "start" {
             description "Start NETCONF tracing";
           }
           enum "stop" {
             description "Stop NETCONF tracing";
           }
         }
         mandatory true;
       }
     }
     output {
       choice output-tags {
         case output-tag {
           leaf output {
             type string;
           }
         }
         case multichassis-tag {
           anyxml multi-routing-engine-results;
         }
       }
     }
   }
   rpc request-flb-maintenance-down {
     description "Request for destination to go in maintenance-down mode";
     junos:command "request services traffic-load-balance flb-destination maintenance-down";
     input {
       leaf destination {
         description "Destination VSRX";
         type string;
       }
     }
     output {
       choice output-tags {
         case actual-tag {
           container tdir-flb-maintenance-down-status {
             uses tdir-flb-maintenance-down-status-block;
           }
         }
         case multichassis-tag {
           container multi-routing-engine-results {
             list multi-routing-engine-item {
               leaf re-name {
                 type string;
               }
               choice output-tags {
                 case actual-tag {
                   container tdir-flb-maintenance-down-status {
                     uses tdir-flb-maintenance-down-status-block;
                   }
                 }
               }
             }
           }
         }
       }
     }
   }
   rpc request-traffic-loadbalance-real-service-rejoin {
     description "Rejoin for load-balance request";
     junos:command "request services traffic-load-balance real-service rejoin";
     input {
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
     output {
       choice output-tags {
         case output-tag {
           leaf output {
             type string;
           }
         }
         case multichassis-tag {
           anyxml multi-routing-engine-results;
         }
       }
     }
   }
   rpc request-lacp-link-protection-switchover {
     description "Request LACP link protection switchover";
     junos:command "request lacp link-switchover";
     input {
       leaf interface-name {
         description "Name of AE interface";
         junos:cli-feature "nokeyword";
         type union {
           type jt:interface-wildcard;
           type string {
             pattern "<.*>|$.*";
           }
         }
         mandatory true;
       }
     }
     output {
       choice output-tags {
         case actual-tag {
           container lacp-link-switchover {
             uses lacp-link-switchover-block;
           }
         }
         case multichassis-tag {
           container multi-routing-engine-results {
             list multi-routing-engine-item {
               leaf re-name {
                 type string;
               }
               choice output-tags {
                 case actual-tag {
                   container lacp-link-switchover {
                     uses lacp-link-switchover-block;
                   }
                 }
               }
             }
           }
         }
       }
     }
   }
   rpc request-message {
     description "Send text message to other users";
     junos:command "request message";
     input {
       leaf user {
         description "Name of user (account@terminal) to receive message";
         type string;
         mandatory true;
       }
       leaf terminal {
         description "Device name of target terminal (/dev/ttyXX)";
         type string;
       }
       leaf message {
         description "Text of message";
         type string;
       }
     }
     output {
       choice output-tags {
         case output-tag {
           leaf output {
             type string;
           }
         }
         case multichassis-tag {
           anyxml multi-routing-engine-results;
         }
       }
     }
   }
   rpc request-message-all {
     description "Send message to all logged-in users";
     junos:command "request message all";
     input {
       leaf message {
         description "Text of message";
         type string;
       }
     }
     output {
       choice output-tags {
         case output-tag {
           leaf output {
             type string;
           }
         }
         case multichassis-tag {
           anyxml multi-routing-engine-results;
         }
       }
     }
   }
   rpc request-vmhost-poweroff {
     description "Power off the software on RE";
     junos:command "request vmhost power-off";
     input {
       leaf other-routing-engine {
         description "Power off other Routing Engine";
         type empty;
       }
     }
     output {
       choice output-tags {
         case output-tag {
           leaf output {
             type string;
           }
         }
         case multichassis-tag {
           anyxml multi-routing-engine-results;
         }
       }
     }
   }
   rpc request-vmhost-halt {
     description "Halt the software on RE";
     junos:command "request vmhost halt";
     input {
       uses command-forwarding;
     }
     output {
       choice output-tags {
         case output-tag {
           leaf output {
             type string;
           }
         }
         case multichassis-tag {
           anyxml multi-routing-engine-results;
         }
       }
     }
   }
   rpc request-vmhost-power-on-other-re {
     description "Power on the system";
     junos:command "request vmhost power-on";
     input {
       leaf other-routing-engine {
         description "Power on other Routing Engine";
         type empty;
         mandatory true;
       }
     }
     output {
       choice output-tags {
         case output-tag {
           leaf output {
             type string;
           }
         }
         case multichassis-tag {
           anyxml multi-routing-engine-results;
         }
       }
     }
   }
   rpc request-vmhost-power-cycle {
     description "Power cycle the vmhost";
     junos:command "request vmhost power-cycle";
     input {
       uses command-forwarding;
     }
     output {
       choice output-tags {
         case output-tag {
           leaf output {
             type string;
           }
         }
         case multichassis-tag {
           anyxml multi-routing-engine-results;
         }
       }
     }
   }
   rpc request-vmhost-power-cycle-cb {
     description "Power Cycle Chassis";
     junos:command "request vmhost power-cycle-cb";
     output {
       choice output-tags {
         case output-tag {
           leaf output {
             type string;
           }
         }
         case multichassis-tag {
           anyxml multi-routing-engine-results;
         }
       }
     }
   }
   rpc request-vmhost-power-cycle-re {
     description "Power Cycle RE";
     junos:command "request vmhost power-cycle-re";
     output {
       choice output-tags {
         case output-tag {
           leaf output {
             type string;
           }
         }
         case multichassis-tag {
           anyxml multi-routing-engine-results;
         }
       }
     }
   }
   rpc request-vmhost-reboot {
     description "Reboot RE vmhost";
     junos:command "request vmhost reboot";
     input {
       uses command-forwarding;
       leaf media {
         junos:cli-feature "nokeyword";
         type enumeration {
           enum "disk1" {
             description "Boot off disk1(primary) device";
           }
           enum "disk2" {
             description "Boot off disk2(backup) device";
           }
           enum "network" {
             description "Network boot via PXE";
           }
           enum "usb" {
             description "Boot off USB device";
           }
         }
       }
       leaf partition {
         junos:cli-feature "nokeyword";
         type enumeration {
           enum "primary" {
             description "Boot from primary partition";
           }
           enum "alternate" {
             description "Boot from alternate partition";
           }
         }
       }
       leaf in {
         description "Number of minutes to delay before reboot operation";
         type union {
           type string {
             pattern "<.*>|$.*";
           }
           type uint32 {
             range "0 .. 100";
           }
         }
       }
     }
     output {
       choice output-tags {
         case output-tag {
           leaf output {
             type string;
           }
         }
         case multichassis-tag {
           anyxml multi-routing-engine-results;
         }
       }
     }
   }
   rpc request-vmhost-file-cleanup {
     description "RE vmhost cleanup /var/tmp, /var/crash and /var/log";
     junos:command "request vmhost cleanup";
     input {
       uses command-forwarding;
     }
     output {
       choice output-tags {
         case output-tag {
           leaf output {
             type string;
           }
         }
         case multichassis-tag {
           anyxml multi-routing-engine-results;
         }
       }
     }
   }
   rpc request-vmhost-file-cleanup-dry-run {
     description "Only list the cleanup candidates, do not remove them";
     junos:command "request vmhost cleanup dry-run";
     output {
       choice output-tags {
         case output-tag {
           leaf output {
             type string;
           }
         }
         case multichassis-tag {
           anyxml multi-routing-engine-results;
         }
       }
     }
   }
   rpc request-vmhost-file-copy {
     description "Copy file from vmhost to vjunos";
     junos:command "request vmhost file-copy";
     input {
       leaf node-path {
         description "Copy files related to";
         junos:cli-feature "nokeyword";
         type enumeration {
           enum "crash" {
             description "Files in /var/crash";
           }
           enum "log" {
             description "Files in /var/log";
           }
         }
         mandatory true;
       }
       leaf from-jnode {
         description "Host file name";
         type string {
           junos:posix-pattern "^[a-zA-Z0-9/+._-]+$";
           junos:pattern-message "Invalid file name: unsafe characters detected";
         }
         mandatory true;
       }
       leaf to-vjunos {
         description "Junos file name";
         type string;
         mandatory true;
       }
     }
     output {
       choice output-tags {
         case output-tag {
           leaf output {
             type string;
           }
         }
         case multichassis-tag {
           anyxml multi-routing-engine-results;
         }
       }
     }
   }
   rpc request-copy-vjunos-to-jnode {
     description "Copy file from vjunos to vmhost";
     junos:command "request vmhost copy vjunos-to-jnode";
     input {
       leaf from-vjunos {
         description "Junos file name";
         type string;
         mandatory true;
       }
       leaf to-jnode {
         description "Host file name";
         type string;
         mandatory true;
       }
     }
     output {
       choice output-tags {
         case output-tag {
           leaf output {
             type string;
           }
         }
         case multichassis-tag {
           anyxml multi-routing-engine-results;
         }
       }
     }
   }
   rpc request-copy-jnode-to-vjunos {
     description "Copy file from vmhost to vjunos";
     junos:command "request vmhost copy jnode-to-vjunos";
     input {
       leaf from-jnode {
         description "Host file name";
         type string {
           junos:posix-pattern "^[a-zA-Z0-9/+._-]+$";
           junos:pattern-message "Invalid file name: unsafe characters detected";
         }
         mandatory true;
       }
       leaf to-vjunos {
         description "Junos file name";
         type string;
         mandatory true;
       }
     }
     output {
       choice output-tags {
         case output-tag {
           leaf output {
             type string;
           }
         }
         case multichassis-tag {
           anyxml multi-routing-engine-results;
         }
       }
     }
   }
   rpc request-vmhost-package-add {
     description "Add extension or upgrade package";
     junos:command "request vmhost software add";
     input {
       leaf i40-driver {
         description "Upgrade only the i40 driver";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf reboot {
         description "Reboot RE vmhost after adding package";
         type empty;
       }
       leaf in {
         description "Number of minutes to delay before reboot operation";
         type union {
           type string {
             pattern "<.*>|$.*";
           }
           type uint32 {
             range "0 .. 100";
           }
         }
       }
       choice re-choice {
         case re0 {
           leaf re0 {
             description "Install package on RE0";
             type empty;
           }
         }
         case re1 {
           leaf re1 {
             description "Install package on RE1";
             type empty;
           }
         }
       }
       choice validate_choice {
         case no-validate {
           leaf no-validate {
             description "Don't check compatibility with current configuration";
             type empty;
           }
         }
       }
       choice chassis {
         case dont-forward {
           leaf dont-forward {
             type empty;
           }
         }
       }
       leaf upgrade-to-model {
         description "Name of the model to upgrade to";
         type string;
       }
       leaf unlink {
         description "Remove the package after successful installation";
         type empty;
       }
     }
     output {
       choice output-tags {
         case output-tag {
           leaf output {
             type string;
           }
         }
         case multichassis-tag {
           anyxml multi-routing-engine-results;
         }
       }
     }
   }
   rpc request-vmhost-package-delete {
     description "Remove extension or upgrade package";
     junos:command "request vmhost software delete";
     input {
       leaf force {
         description "Force removal of package (ignore warnings)";
         type empty;
       }
       choice package-options {
         case set {
         }
         case package-name {
           leaf package-name {
             description "Name of package";
             junos:cli-feature "nokeyword";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
     }
     output {
       choice output-tags {
         case output-tag {
           leaf output {
             type string;
           }
         }
         case multichassis-tag {
           anyxml multi-routing-engine-results;
         }
       }
     }
   }
   rpc abort-vmhost-in-service-upgrade {
     description "Abort in-service software upgrade";
     junos:command "request vmhost software abort in-service-upgrade";
     output {
       choice output-tags {
         case output-tag {
           leaf output {
             type string;
           }
         }
         case multichassis-tag {
           anyxml multi-routing-engine-results;
         }
       }
     }
   }
   rpc request-vmhost-package-in-service-upgrade {
     description "In-service software upgrade";
     junos:command "request vmhost software in-service-upgrade";
     input {
       leaf package-name {
         description "URL or pathname of package";
         junos:cli-feature "nokeyword";
         type jt:filename;
         mandatory true;
       }
       leaf no-old-master-upgrade {
         description "Don't upgrade the old master after switchover";
         type empty;
       }
       leaf reboot {
         description "Reboot RE vmhost after adding package";
         type empty;
       }
     }
     output {
       choice output-tags {
         case output-tag {
           leaf output {
             type string;
           }
         }
         case multichassis-tag {
           anyxml multi-routing-engine-results;
         }
       }
     }
   }
   rpc request-vmhost-nonstop-upgrade {
     description "Nonstop software upgrade";
     junos:command "request vmhost software nonstop-upgrade";
     input {
       leaf force-host {
         description "Force addition of host os package (ignore version check)";
         type empty;
       }
       leaf no-auto-recovery {
         description "Will not recover in case of NSSU failure";
         type empty;
       }
       leaf reboot {
         description "Reboot system after adding package";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf no-old-master-upgrade {
         description "Don't upgrade the old master after switchover";
         type empty;
       }
       leaf no-copy {
         description "Don't save copies of package files";
         status deprecated;
         type empty;
       }
       leaf unlink {
         description "Remove the package after successful installation";
         status deprecated;
         type empty;
       }
     }
     output {
       choice output-tags {
         case output-tag {
           leaf output {
             type string;
           }
         }
         case multichassis-tag {
           anyxml multi-routing-engine-results;
         }
       }
     }
   }
   rpc request-vmhost-package-validate {
     description "Verify package compatibility with current configuration";
     junos:command "request vmhost software validate";
     input {
       choice package-options {
         case package-name {
           leaf package-name {
             description "URL or pathname of package";
             junos:cli-feature "nokeyword";
             type jt:filename;
           }
         }
       }
       choice chassis {
         case member {
           leaf member {
             description "Validate package on member";
             type union {
               type string {
                 pattern "<.*>|$.*";
               }
               type uint32;
             }
           }
         }
         case dont-forward {
           leaf dont-forward {
             type empty;
           }
         }
       }
     }
     output {
       choice output-tags {
         case output-tag {
           leaf output {
             type string;
           }
         }
         case multichassis-tag {
           anyxml multi-routing-engine-results;
         }
       }
     }
   }
   rpc request-vmhost-package-rollback {
     description "Attempt to roll back to previous set of packages";
     junos:command "request vmhost software rollback";
     input {
       uses command-forwarding;
       leaf reboot {
         description "Reboot system after rollback";
         type empty;
       }
     }
     output {
       choice output-tags {
         case output-tag {
           leaf output {
             type string;
           }
         }
         case actual-tag {
           anyxml rollback-information;
         }
         case multichassis-tag {
           anyxml multi-routing-engine-results;
         }
       }
     }
   }
   rpc request-vmhost-jdm-package-add {
     description "Install fresh JDM package or upgrade package";
     junos:command "request vmhost jdm add";
     input {
       leaf package-name {
         description "JDM package name";
         junos:cli-feature "nokeyword";
         type jt:filename;
         mandatory true;
       }
       leaf force {
         description "Force package add";
         type empty;
       }
     }
     output {
       choice output-tags {
         case output-tag {
           leaf output {
             type string;
           }
         }
         case multichassis-tag {
           anyxml multi-routing-engine-results;
         }
       }
     }
   }
   rpc request-vmhost-jdm-package-delete {
     description "Remove currently installed JDM package";
     junos:command "request vmhost jdm delete";
     output {
       choice output-tags {
         case output-tag {
           leaf output {
             type string;
           }
         }
         case multichassis-tag {
           anyxml multi-routing-engine-results;
         }
       }
     }
   }
   rpc request-package-vmhost-jdm-start {
     description "Start the JDM";
     junos:command "request vmhost jdm start";
     output {
       choice output-tags {
         case output-tag {
           leaf output {
             type string;
           }
         }
         case multichassis-tag {
           anyxml multi-routing-engine-results;
         }
       }
     }
   }
   rpc request-package-vmhost-jdm-stop {
     description "Stop the JDM";
     junos:command "request vmhost jdm stop";
     output {
       choice output-tags {
         case output-tag {
           leaf output {
             type string;
           }
         }
         case multichassis-tag {
           anyxml multi-routing-engine-results;
         }
       }
     }
   }
   rpc request-vmhost-jdm-login {
     description "Login to JDM";
     junos:command "request vmhost jdm login";
     output {
       choice output-tags {
         case output-tag {
           leaf output {
             type string;
           }
         }
         case multichassis-tag {
           anyxml multi-routing-engine-results;
         }
       }
     }
   }
   rpc request-vmhost-snapshot {
     description "Create a vmhost recovery snapshot";
     junos:command "request vmhost snapshot";
     input {
       uses command-forwarding;
       leaf no-confirm {
         description "Do not ask for confirmation";
         type empty;
       }
     }
     output {
       choice output-tags {
         case output-tag {
           leaf output {
             type string;
           }
         }
         case actual-tag {
           anyxml vmhost-snapshot-information;
         }
         case multichassis-tag {
           anyxml multi-routing-engine-results;
         }
       }
     }
   }
   rpc request-vmhost-snapshot-config {
     description "Sychronise Configuration between the disks";
     junos:command "request vmhost snapshot config";
     input {
       uses command-forwarding;
     }
     output {
       choice output-tags {
         case output-tag {
           leaf output {
             type string;
           }
         }
         case actual-tag {
           anyxml vmhost-snapshot-config-information;
         }
         case multichassis-tag {
           anyxml multi-routing-engine-results;
         }
       }
     }
   }
   rpc request-vmhost-snapshot-partition {
     description "Partition the target media";
     junos:command "request vmhost snapshot partition";
     input {
       uses command-forwarding;
     }
     output {
       choice output-tags {
         case output-tag {
           leaf output {
             type string;
           }
         }
         case actual-tag {
           anyxml vmhost-snapshot-partition-information;
         }
         case multichassis-tag {
           anyxml multi-routing-engine-results;
         }
       }
     }
   }
   rpc request-vmhost-snapshot-recovery {
     description "Recover the primary media from snapshot";
     junos:command "request vmhost snapshot recovery";
     input {
       uses command-forwarding;
     }
     output {
       choice output-tags {
         case output-tag {
           leaf output {
             type string;
           }
         }
         case actual-tag {
           anyxml vmhost-snapshot-recovery-information;
         }
         case multichassis-tag {
           anyxml multi-routing-engine-results;
         }
       }
     }
   }
   rpc request-vmhost-snapshot-recovery-partition {
     description "Partition the media before snapshot";
     junos:command "request vmhost snapshot recovery partition";
     input {
       uses command-forwarding;
     }
     output {
       choice output-tags {
         case output-tag {
           leaf output {
             type string;
           }
         }
         case actual-tag {
           anyxml vmhost-snapshot-recovery-partition-information;
         }
         case multichassis-tag {
           anyxml multi-routing-engine-results;
         }
       }
     }
   }
   rpc request-vmhost-zeroize {
     description "Erase all data, including configuration and log files";
     junos:command "request vmhost zeroize";
     input {
       uses command-forwarding;
     }
     output {
       choice output-tags {
         case output-tag {
           leaf output {
             type string;
           }
         }
         case actual-tag {
           anyxml vmhost-zeroize-information;
         }
         case multichassis-tag {
           anyxml multi-routing-engine-results;
         }
       }
     }
   }
   rpc request-vmhost-zeroize-erase-disk {
     description "Erase all disks";
     junos:command "request vmhost zeroize erase-disk";
     input {
       uses command-forwarding;
     }
     output {
       choice output-tags {
         case output-tag {
           leaf output {
             type string;
           }
         }
         case actual-tag {
           anyxml vmhost-zeroize-erase-disk;
         }
         case multichassis-tag {
           anyxml multi-routing-engine-results;
         }
       }
     }
   }
   rpc request-vmhost-hard-disk-test {
     description "Run smartd self tests on hard disks";
     junos:command "request vmhost hard-disk-test";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc request-vmhost-last-known-good-bios {
     description "Backup/Restore last known good bios image";
     junos:command "request vmhost last-known-good-bios";
     output {
       choice output-tags {
         case output-tag {
           leaf output {
             type string;
           }
         }
         case actual-tag {
           anyxml request-vmhost-last-known-good-bios;
         }
         case multichassis-tag {
           anyxml multi-routing-engine-results;
         }
       }
     }
   }
   rpc request-vmhost-last-known-good-bios-backup {
     description "Backup last known good bios";
     junos:command "request vmhost last-known-good-bios backup";
     input {
       leaf path {
         description "Path to take backup";
         junos:cli-feature "nokeyword";
         type string;
       }
     }
     output {
       choice output-tags {
         case output-tag {
           leaf output {
             type string;
           }
         }
         case multichassis-tag {
           anyxml multi-routing-engine-results;
         }
       }
     }
   }
   rpc request-vmhost-last-known-good-bios-restore {
     description "Restore last known good bios";
     junos:command "request vmhost last-known-good-bios restore";
     input {
       leaf path {
         description "Path which contains last known bios";
         junos:cli-feature "nokeyword";
         type string;
       }
     }
     output {
       choice output-tags {
         case output-tag {
           leaf output {
             type string;
           }
         }
         case multichassis-tag {
           anyxml multi-routing-engine-results;
         }
       }
     }
   }
   rpc request-snmp-spoof-trap {
     description "Generate artificial SNMP notification";
     junos:command "request snmp spoof-trap";
     input {
       leaf trap {
         description "The name of the trap to spoof";
         junos:cli-feature "nokeyword";
         type string;
         mandatory true;
       }
       leaf variable-bindings {
         description "The list of variables & values to include in the trap";
         type string;
       }
     }
     output {
       choice output-tags {
         case actual-tag {
           container snmp-spoof-trap-results {
             uses snmp-spoof-trap-results-block;
           }
         }
         case multichassis-tag {
           container multi-routing-engine-results {
             list multi-routing-engine-item {
               leaf re-name {
                 type string;
               }
               choice output-tags {
                 case actual-tag {
                   container snmp-spoof-trap-results {
                     uses snmp-spoof-trap-results-block;
                   }
                 }
               }
             }
           }
         }
       }
     }
   }
   rpc request-snmp-utility-mib-set {
     description "Set values in utility mib objects";
     junos:command "request snmp utility-mib set";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
       leaf object-value {
         type string;
         mandatory true;
       }
     }
     output {
       choice output-tags {
         case actual-tag {
           container snmp-utility-mib-results {
             uses snmp-utility-mib-results-block;
           }
         }
         case multichassis-tag {
           container multi-routing-engine-results {
             list multi-routing-engine-item {
               leaf re-name {
                 type string;
               }
               choice output-tags {
                 case actual-tag {
                   container snmp-utility-mib-results {
                     uses snmp-utility-mib-results-block;
                   }
                 }
               }
             }
           }
         }
       }
     }
   }
   rpc request-snmp-utility-mib-clear {
     description "Clear values in utility mib objects";
     junos:command "request snmp utility-mib clear";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
     }
     output {
       choice output-tags {
         case actual-tag {
           container snmp-utility-mib-results {
             uses snmp-utility-mib-results-block;
           }
         }
         case multichassis-tag {
           container multi-routing-engine-results {
             list multi-routing-engine-item {
               leaf re-name {
                 type string;
               }
               choice output-tags {
                 case actual-tag {
                   container snmp-utility-mib-results {
                     uses snmp-utility-mib-results-block;
                   }
                 }
               }
             }
           }
         }
       }
     }
   }
   rpc aaa-subscriber-add-service {
     description "Service activation";
     junos:command "request network-access aaa subscriber add";
     input {
       leaf session-id {
         description "Session id";
         type union {
           type string {
             pattern "<.*>|$.*";
           }
           type uint64 {
             range "1 .. 18446744073709551615";
           }
         }
         mandatory true;
       }
       leaf service-profile {
         description "Name of service-profile";
         type string;
         mandatory true;
       }
     }
     output {
       choice output-tags {
         case output-tag {
           leaf output {
             type string;
           }
         }
         case actual-tag {
           anyxml aaa-subscriber-add-service-results;
         }
         case multichassis-tag {
           anyxml multi-routing-engine-results;
         }
       }
     }
   }
   rpc aaa-subscriber-delete-service {
     description "Service deactivation";
     junos:command "request network-access aaa subscriber delete";
     input {
       leaf session-id {
         description "Session id";
         type union {
           type string {
             pattern "<.*>|$.*";
           }
           type uint64 {
             range "1 .. 18446744073709551615";
           }
         }
         mandatory true;
       }
       leaf service-profile {
         description "Name of dynamic-profile";
         type string;
         mandatory true;
       }
     }
     output {
       choice output-tags {
         case output-tag {
           leaf output {
             type string;
           }
         }
         case actual-tag {
           anyxml aaa-subscriber-delete-service-results;
         }
         case multichassis-tag {
           anyxml multi-routing-engine-results;
         }
       }
     }
   }
   rpc aaa-subscriber-modify-variable {
     description "Modify dynamic variable";
     junos:command "request network-access aaa subscriber modify";
     input {
       leaf session-id {
         description "Session id";
         type union {
           type string {
             pattern "<.*>|$.*";
           }
           type uint64 {
             range "1 .. 18446744073709551615";
           }
         }
         mandatory true;
       }
       leaf junos-cos-traffic-control-profile {
         description "Modify $junos-cos-traffic-control-profile variable";
         type string;
       }
     }
     output {
       choice output-tags {
         case output-tag {
           leaf output {
             type string;
           }
         }
         case actual-tag {
           anyxml aaa-subscriber-modify-variable-results;
         }
         case multichassis-tag {
           anyxml multi-routing-engine-results;
         }
       }
     }
   }
   rpc aaa-subscriber-set-parameters {
     description "Set AAA subscriber parameters";
     junos:command "request network-access aaa subscriber set";
     input {
       leaf session-id {
         description "Session id";
         type union {
           type string {
             pattern "<.*>|$.*";
           }
           type uint64 {
             range "1 .. 18446744073709551615";
           }
         }
         mandatory true;
       }
       leaf provisioning-state {
         description "Provisioning state";
         type enumeration {
           enum "none" {
             description "Set provisioning to none";
           }
         }
         mandatory true;
       }
     }
     output {
       choice output-tags {
         case output-tag {
           leaf output {
             type string;
           }
         }
         case actual-tag {
           anyxml aaa-subscriber-set-parameters-results;
         }
         case multichassis-tag {
           anyxml multi-routing-engine-results;
         }
       }
     }
   }
   rpc replay-pending-accounting-stops {
     description "Replay pending acct stops to radius";
     junos:command "request network-access aaa replay pending-accounting-stops";
     output {
       choice output-tags {
         case output-tag {
           leaf output {
             type string;
           }
         }
         case actual-tag {
           anyxml replay-pending-accounting-results;
         }
         case multichassis-tag {
           anyxml multi-routing-engine-results;
         }
       }
     }
   }
   rpc request-accounting-action {
     description "Accounting suspend or baseline";
     junos:command "request network-access aaa accounting";
     input {
       choice accounting_action {
         case suspend {
           leaf suspend {
             description "Suspend accounting";
             type empty;
           }
         }
         case baseline {
           leaf baseline {
             description "Baseline statistics";
             type empty;
           }
         }
         case resume {
           leaf resume {
             description "Resume accounting";
             type empty;
           }
         }
       }
     }
     output {
       choice output-tags {
         case output-tag {
           leaf output {
             type string;
           }
         }
         case multichassis-tag {
           anyxml multi-routing-engine-results;
         }
       }
     }
   }
   rpc address-assignment-domain-profile {
     description "Request domain-profile specific command options";
     junos:command "request network-access aaa address-assignment domain-profile";
     input {
       leaf ri-name {
         description "Routing instance name";
         type string;
         mandatory true;
       }
       leaf profile-name {
         description "Domain profile name";
         type string;
         mandatory true;
       }
       leaf action-type {
         junos:cli-feature "nokeyword";
         type enumeration {
           enum "enable-logins" {
             description "Enable subsequent logins";
           }
           enum "disable-logins" {
             description "Disable subsequent logins";
           }
         }
         mandatory true;
       }
     }
     output {
       choice output-tags {
         case output-tag {
           leaf output {
             type string;
           }
         }
         case multichassis-tag {
           anyxml multi-routing-engine-results;
         }
       }
     }
   }
   rpc address-assignment-subscriber-group {
     description "Request subscriber-group specific command options";
     junos:command "request network-access aaa address-assignment subscriber-group";
     input {
       leaf subscriber-group-name {
         description "Subscriber group name";
         junos:cli-feature "nokeyword";
         type string;
         mandatory true;
       }
       leaf action-type {
         junos:cli-feature "nokeyword";
         type enumeration {
           enum "enable-logins" {
             description "Enable subsequent logins";
           }
           enum "disable-logins" {
             description "Disable subsequent logins";
           }
         }
         mandatory true;
       }
     }
     output {
       choice output-tags {
         case output-tag {
           leaf output {
             type string;
           }
         }
         case multichassis-tag {
           anyxml multi-routing-engine-results;
         }
       }
     }
   }
   rpc address-assignment-drain-pool {
     description "Drain a specific dynamic pool";
     junos:command "request network-access aaa address-assignment drain pool";
     input {
       leaf pool-name {
         description "Pool name";
         junos:cli-feature "nokeyword";
         type string;
         mandatory true;
       }
     }
     output {
       choice output-tags {
         case output-tag {
           leaf output {
             type string;
           }
         }
         case multichassis-tag {
           anyxml multi-routing-engine-results;
         }
       }
     }
   }
   rpc request-auto-configuration-reconnect-pending {
     description "Request reconnect of pending out-of-band sessions";
     junos:command "request auto-configuration reconnect-pending";
     output {
       choice output-tags {
         case output-tag {
           leaf output {
             type string;
           }
         }
         case multichassis-tag {
           anyxml multi-routing-engine-results;
         }
       }
     }
   }
   rpc request-rps-download-firmware {
     description "Upgrade redundant-power-system firmware";
     junos:command "request redundant-power-system firmware upgrade";
     input {
       leaf member {
         description "Member of virtual chassis configuration";
         type union {
           type string {
             pattern "<.*>|$.*";
           }
           type int32;
         }
         mandatory true;
       }
       leaf server {
         description "TFTP server IP address";
         type jt:ipv4addr;
         mandatory true;
       }
       leaf image {
         description "Firmware image with path";
         type string;
         mandatory true;
       }
     }
     output {
       choice output-tags {
         case output-tag {
           leaf output {
             type string;
           }
         }
         case actual-tag {
           anyxml rps-firmware-download;
         }
         case multichassis-tag {
           anyxml multi-routing-engine-results;
         }
       }
     }
   }
   rpc request-rps-multi-backup {
     description "Enable RPS multi-backup";
     junos:command "request redundant-power-system multi-backup";
     input {
       leaf member {
         description "Member of virtual chassis configuration";
         type union {
           type string {
             pattern "<.*>|$.*";
           }
           type int32;
         }
         mandatory true;
       }
     }
     output {
       choice output-tags {
         case output-tag {
           leaf output {
             type string;
           }
         }
         case actual-tag {
           anyxml rps-multi-backup;
         }
         case multichassis-tag {
           anyxml multi-routing-engine-results;
         }
       }
     }
   }
   rpc request-rps-no-multi-backup {
     description "Disable RPS multi-backup";
     junos:command "request redundant-power-system no-multi-backup";
     input {
       leaf member {
         description "Member of virtual chassis configuration";
         type union {
           type string {
             pattern "<.*>|$.*";
           }
           type int32;
         }
         mandatory true;
       }
     }
     output {
       choice output-tags {
         case output-tag {
           leaf output {
             type string;
           }
         }
         case actual-tag {
           anyxml rps-no-multi-backup;
         }
         case multichassis-tag {
           anyxml multi-routing-engine-results;
         }
       }
     }
   }
   rpc request-chassis-device-recorder {
     description "Device recorder configuration";
     junos:command "request chassis device-recorder";
     input {
       uses command-forwarding;
       leaf cmd {
         junos:cli-feature "nokeyword";
         type enumeration {
           enum "enable" {
             description "Enable device recorder";
           }
           enum "disable" {
             description "Disable device recorder";
           }
         }
         mandatory true;
       }
     }
     output {
       choice output-tags {
         case output-tag {
           leaf output {
             type string;
           }
         }
         case multichassis-tag {
           anyxml multi-routing-engine-results;
         }
       }
     }
   }
   rpc request-chassis-pic {
     description "Change Physical Interface Card status";
     junos:command "request chassis pic";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf cmd {
         junos:cli-feature "nokeyword";
         type enumeration {
           enum "offline" {
             description "Take PIC offline";
           }
           enum "online" {
             description "Bring PIC online";
           }
         }
         mandatory true;
       }
     }
     output {
       choice output-tags {
         case output-tag {
           leaf output {
             type string;
           }
         }
         case multichassis-tag {
           anyxml multi-routing-engine-results;
         }
       }
     }
   }
   rpc request-chassis-fpc {
     description "Change Flexible PIC Concentrator status";
     junos:command "request chassis fpc";
     input {
       uses command-forwarding;
       leaf slot {
         description "FPC slot number";
         type union {
           type string {
             pattern "<.*>|$.*";
           }
           type uint32;
         }
         mandatory true;
       }
       leaf cmd {
         junos:cli-feature "nokeyword";
         type enumeration {
           enum "offline" {
             description "Take FPC or PFE-instance offline";
           }
           enum "online" {
             description "Bring FPC or PFE-instance online";
           }
           enum "restart" {
             description "Restart FPC or PFE-instance";
           }
         }
         mandatory true;
       }
       leaf tag {
         description "Firmware tag for online-reload";
         type union {
           type int32;
           type string {
             pattern "<.*>|$.*";
           }
         }
       }
     }
     output {
       choice output-tags {
         case actual-tag {
           container chassis-fpc-state {
             uses chassis-fpc-state-block;
           }
         }
         case multichassis-tag {
           container multi-routing-engine-results {
             list multi-routing-engine-item {
               leaf re-name {
                 type string;
               }
               choice output-tags {
                 case actual-tag {
                   container chassis-fpc-state {
                     uses chassis-fpc-state-block;
                   }
                 }
               }
             }
           }
         }
       }
     }
   }
   rpc request-chassis-fabric-plane {
     description "Change fabric plane status";
     junos:command "request chassis fabric plane";
     input {
       uses command-forwarding;
       leaf plane {
         description "Fabric plane number";
         junos:cli-feature "nokeyword";
         type union {
           type string {
             pattern "<.*>|$.*";
           }
           type uint32;
         }
         mandatory true;
       }
       leaf which-command {
         junos:cli-feature "nokeyword";
         type enumeration {
           enum "offline" {
             description "Take fabric plane offline";
           }
           enum "online" {
             description "Bring fabric plane online";
           }
         }
         mandatory true;
       }
     }
     output {
       choice output-tags {
         case actual-tag {
           container chassis-fabric-plane-state {
             uses chassis-fabric-plane-state-block;
           }
         }
         case multichassis-tag {
           container multi-routing-engine-results {
             list multi-routing-engine-item {
               leaf re-name {
                 type string;
               }
               choice output-tags {
                 case actual-tag {
                   container chassis-fabric-plane-state {
                     uses chassis-fabric-plane-state-block;
                   }
                 }
               }
             }
           }
         }
       }
     }
   }
   rpc request-chassis-sib {
     description "Change Switch Interface Board status";
     junos:command "request chassis sib";
     input {
       uses command-forwarding;
       leaf slot {
         description "SIB slot number";
         type union {
           type string {
             pattern "<.*>|$.*";
           }
           type uint32;
         }
         mandatory true;
       }
       choice cmd {
         case online-offline {
           leaf online-offline {
             junos:cli-feature "nokeyword";
             type enumeration {
               enum "offline" {
                 description "Take SIB offline";
               }
               enum "online" {
                 description "Bring SIB online";
               }
               enum "restart" {
                 description "Perform Sib restart";
               }
             }
           }
         }
         case start-receiver {
         }
         case stop-receiver {
         }
         case train-rx-tx {
           leaf train-rx-tx {
             junos:cli-feature "nokeyword";
             type enumeration {
               enum "train-link-receive" {
                 description "Train link receiver";
               }
               enum "train-link-transmit" {
                 description "Train link transmitter";
               }
             }
           }
         }
       }
     }
     output {
       choice output-tags {
         case output-tag {
           leaf output {
             type string;
           }
         }
         case multichassis-tag {
           anyxml multi-routing-engine-results;
         }
       }
     }
   }
   rpc request-chassis-frutype-replacement {
     description "Perform fru replacement start or stop";
     junos:command "request chassis fru";
     input {
       leaf frutype {
         description "Select frutype";
         junos:cli-feature "nokeyword";
         type enumeration {
           enum "sfb" {
             description "Replace SFB";
           }
         }
         mandatory true;
       }
       leaf replacement {
         description "Starts or stops the fru replacement";
         type enumeration {
           enum "start" {
             description "Start the fru replacement";
           }
           enum "stop" {
             description "Stop the fru replacement";
           }
         }
         mandatory true;
       }
     }
     output {
       choice output-tags {
         case output-tag {
           leaf output {
             type string;
           }
         }
         case multichassis-tag {
           anyxml multi-routing-engine-results;
         }
       }
     }
   }
   rpc request-chassis-routing-engine {
     description "Change Routing Engine status";
     junos:command "request chassis routing-engine";
     output {
       choice output-tags {
         case actual-tag {
           container chassis-routing-engine-state {
             uses chassis-routing-engine-state-block;
           }
         }
         case multichassis-tag {
           container multi-routing-engine-results {
             list multi-routing-engine-item {
               leaf re-name {
                 type string;
               }
               choice output-tags {
                 case actual-tag {
                   container chassis-routing-engine-state {
                     uses chassis-routing-engine-state-block;
                   }
                 }
               }
             }
           }
         }
       }
     }
   }
   rpc request-chassis-routing-engine-hard-disk-test {
     description "Run smartd self tests on hard disks";
     junos:command "request chassis routing-engine hard-disk-test";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc request-chassis-routing-engine-acquire {
     description "Attempt to become master Routing Engine";
     junos:command "request chassis routing-engine master acquire";
     input {
       uses command-forwarding;
       leaf no-confirm {
         description "Do not ask for confirmation";
         type empty;
       }
       leaf check {
         description "Check status of graceful switchover";
         type empty;
       }
     }
     output {
       choice output-tags {
         case actual-tag {
           container chassis-routing-engine-state {
             uses chassis-routing-engine-state-block;
           }
         }
         case multichassis-tag {
           container multi-routing-engine-results {
             list multi-routing-engine-item {
               leaf re-name {
                 type string;
               }
               choice output-tags {
                 case actual-tag {
                   container chassis-routing-engine-state {
                     uses chassis-routing-engine-state-block;
                   }
                 }
               }
             }
           }
         }
       }
     }
   }
   rpc request-chassis-routing-engine-release {
     description "Request that other Routing Engine become master";
     junos:command "request chassis routing-engine master release";
     input {
       uses command-forwarding;
       leaf no-confirm {
         description "Do not ask for confirmation";
         type empty;
       }
       leaf check {
         description "Check status of graceful switchover";
         type empty;
       }
     }
     output {
       choice output-tags {
         case actual-tag {
           container chassis-routing-engine-state {
             uses chassis-routing-engine-state-block;
           }
         }
         case multichassis-tag {
           container multi-routing-engine-results {
             list multi-routing-engine-item {
               leaf re-name {
                 type string;
               }
               choice output-tags {
                 case actual-tag {
                   container chassis-routing-engine-state {
                     uses chassis-routing-engine-state-block;
                   }
                 }
               }
             }
           }
         }
       }
     }
   }
   rpc request-chassis-routing-engine-switch {
     description "Toggle mastership between Routing Engines";
     junos:command "request chassis routing-engine master switch";
     input {
       uses command-forwarding;
       leaf no-confirm {
         description "Do not ask for confirmation";
         type empty;
       }
       leaf check {
         description "Check status of graceful switchover";
         type empty;
       }
     }
     output {
       choice output-tags {
         case actual-tag {
           container chassis-routing-engine-state {
             uses chassis-routing-engine-state-block;
           }
         }
         case multichassis-tag {
           container multi-routing-engine-results {
             list multi-routing-engine-item {
               leaf re-name {
                 type string;
               }
               choice output-tags {
                 case actual-tag {
                   container chassis-routing-engine-state {
                     uses chassis-routing-engine-state-block;
                   }
                 }
               }
             }
           }
         }
       }
     }
   }
   rpc request-chassis-cb {
     description "Change Control Board status";
     junos:command "request chassis cb";
     input {
       uses command-forwarding;
       leaf slot {
         description "CB slot number";
         type union {
           type string {
             pattern "<.*>|$.*";
           }
           type uint32;
         }
         mandatory true;
       }
       leaf cmd {
         junos:cli-feature "nokeyword";
         type enumeration {
           enum "offline" {
             description "Take CB offline";
           }
           enum "online" {
             description "Bring CB online";
           }
         }
         mandatory true;
       }
     }
     output {
       choice output-tags {
         case output-tag {
           leaf output {
             type string;
           }
         }
         case multichassis-tag {
           anyxml multi-routing-engine-results;
         }
       }
     }
   }
   rpc set-chassis-pic-mode-to-intraconnect {
     description "Set the mode to intraconnect";
     junos:command "request chassis pic-mode intraconnect";
     input {
       uses command-forwarding;
     }
     output {
       choice output-tags {
         case output-tag {
           leaf output {
             type string;
           }
         }
         case multichassis-tag {
           anyxml multi-routing-engine-results;
         }
       }
     }
   }
   rpc set-chassis-pic-mode-to-vc {
     description "Set the mode to virtual-chassis";
     junos:command "request chassis pic-mode virtual-chassis";
     input {
       uses command-forwarding;
     }
     output {
       choice output-tags {
         case output-tag {
           leaf output {
             type string;
           }
         }
         case multichassis-tag {
           anyxml multi-routing-engine-results;
         }
       }
     }
   }
   rpc self-mirror-enable-disable {
     description "Enable or disable port-mirroring";
     junos:command "request forwarding-options port-mirroring";
     input {
       leaf instance {
         description "Name of port-mirroring instance";
         type string;
         mandatory true;
       }
       leaf family {
         description "Family of port-mirroring instance";
         type enumeration {
           enum "inet" {
             description "IPv4 instance";
           }
           enum "inet6" {
             description "IPv6 instance";
           }
           enum "any" {
             description "Any instance";
           }
         }
       }
       choice which-cmd {
         case self-mirror-stop {
           leaf self-mirror-stop {
             description "Stop the capture";
             type empty;
           }
         }
         case self-mirror-start {
           leaf self-mirror-start {
             description "Duration in seconds";
             default "300";
             units "seconds";
             type union {
               type string {
                 pattern "<.*>|$.*";
               }
               type int32 {
                 range "45 .. 1800";
               }
             }
           }
         }
       }
     }
     output {
       choice output-tags {
         case actual-tag {
           container helper-self-mirror-enable-disable {
             uses helper-self-mirror-enable-disable-block;
           }
         }
         case multichassis-tag {
           container multi-routing-engine-results {
             list multi-routing-engine-item {
               leaf re-name {
                 type string;
               }
               choice output-tags {
                 case actual-tag {
                   container helper-self-mirror-enable-disable {
                     uses helper-self-mirror-enable-disable-block;
                   }
                 }
               }
             }
           }
         }
       }
     }
   }
   rpc request-tdr-interface-diagnostics {
     description "Enter TDR interface name";
     junos:command "request diagnostics tdr start interface";
     input {
       leaf interface-name {
         description "Interface name";
         junos:cli-feature "nokeyword";
         type string;
       }
     }
     output {
       choice output-tags {
         case output-tag {
           leaf output {
             type string;
           }
         }
         case actual-tag {
           anyxml tdr-start-interface;
         }
         case multichassis-tag {
           anyxml multi-routing-engine-results;
         }
       }
     }
   }
   rpc abort-tdr-interface-diagnostics {
     description "Enter TDR interface name";
     junos:command "request diagnostics tdr abort interface";
     input {
       leaf interface-name {
         description "Interface name";
         junos:cli-feature "nokeyword";
         type string;
       }
     }
     output {
       choice output-tags {
         case output-tag {
           leaf output {
             type string;
           }
         }
         case actual-tag {
           anyxml tdr-abort-interface;
         }
         case multichassis-tag {
           anyxml multi-routing-engine-results;
         }
       }
     }
   }
   rpc request-protection-group-erps-clear {
     description "Clears active local commands";
     junos:command "request protection-group ethernet-ring clear";
     input {
       leaf group-name {
         description "Name of protection group";
         type string {
           length "1 .. 32";
         }
       }
     }
     output {
       choice output-tags {
         case output-tag {
           leaf output {
             type string;
           }
         }
         case multichassis-tag {
           anyxml multi-routing-engine-results;
         }
       }
     }
   }
   rpc request-protection-group-erps-manual-switch {
     description "Manual switch data path to use protection path";
     junos:command "request protection-group ethernet-ring manual-switch";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output-tags {
         case output-tag {
           leaf output {
             type string;
           }
         }
         case multichassis-tag {
           anyxml multi-routing-engine-results;
         }
       }
     }
   }
   rpc request-protection-group-erps-force-switch {
     description "Force switch data path to use protection path";
     junos:command "request protection-group ethernet-ring force-switch";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output-tags {
         case output-tag {
           leaf output {
             type string;
           }
         }
         case multichassis-tag {
           anyxml multi-routing-engine-results;
         }
       }
     }
   }
   rpc request-evpn {
     junos:command "request evpn";
     input {
       leaf validate-maintenance-mode-pre-checks {
         description "Validate pre-checks for evpn maintenance mode";
         type enumeration {
           enum "erb-leaf" {
             description "EVPN ERB style of deployment for leaf node";
           }
           enum "collapsed-core" {
             description "EVPN Campus Fabric Collapsed-Core deployment for leaf node";
           }
           enum "core-distribution" {
             description "EVPN Campus Fabric Core-Distribution deployment for leaf node";
           }
           enum "ip-clos" {
             description "EVPN Campus Fabric IP-Clos deployment for leaf node";
           }
         }
       }
     }
     output {
       choice output-tags {
         case output-tag {
           leaf output {
             type string;
           }
         }
         case multichassis-tag {
           anyxml multi-routing-engine-results;
         }
       }
     }
   }
   rpc get-flight-recorder-information {
     description "Debug high cpu issues and scheduler slips";
     junos:command "request flight-recorder set high-cpu";
     input {
       leaf disable {
         description "Disable the flight recorder";
         type empty;
       }
       leaf logical-system {
         description "Enable logical systems";
         type empty;
       }
       leaf cpu-threshold {
         description "Threshold over which the collection is triggered";
         type union {
           type string {
             pattern "<.*>|$.*";
           }
           type uint32 {
             range "1 .. 400";
           }
         }
       }
       leaf polling-frequency {
         description "Frequency of polling for high cpu";
         type union {
           type string {
             pattern "<.*>|$.*";
           }
           type uint32 {
             range "5 .. 100";
           }
         }
       }
       leaf backoff-duration {
         description "Time to wait between two snapshots";
         type union {
           type string {
             pattern "<.*>|$.*";
           }
           type uint32 {
             range "10 .. 1000";
           }
         }
       }
       leaf collect-core {
         description "Whether to take a running core with every snapshot";
         type empty;
       }
       leaf num-snapshots {
         description "How many snapshots to collect before quitting";
         type union {
           type string {
             pattern "<.*>|$.*";
           }
           type uint32 {
             range "1 .. 20";
           }
         }
       }
     }
     output {
       choice output-tags {
         case actual-tag {
           container flight-recorder-information {
             uses flight-recorder-information-block;
           }
         }
         case multichassis-tag {
           container multi-routing-engine-results {
             list multi-routing-engine-item {
               leaf re-name {
                 type string;
               }
               choice output-tags {
                 case actual-tag {
                   container flight-recorder-information {
                     uses flight-recorder-information-block;
                   }
                 }
               }
             }
           }
         }
       }
     }
   }
   rpc request-l2ckt-switchover {
     description "Perform l2circuit switchover";
     junos:command "request l2circuit-switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         type jt:ipv4addr;
         mandatory true;
       }
       leaf virtual-circuit-id {
         description "Layer 2 circuit ID";
         default "all";
         type string;
       }
     }
     output {
       choice output-tags {
         case output-tag {
           leaf output {
             type string;
           }
         }
         case multichassis-tag {
           anyxml multi-routing-engine-results;
         }
       }
     }
   }
   rpc request-vpls-switchover {
     description "Perform LDP VPLS pseudowire switchover";
     junos:command "request vpls-switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of VPLS instance";
         type string;
         mandatory true;
       }
       leaf neighbor {
         description "IP address of neighbor";
         type jt:ipv4addr;
         mandatory true;
       }
       leaf vpls-id {
         description "Layer 2 circuit ID";
         default "all";
         type string;
       }
     }
     output {
       choice output-tags {
         case output-tag {
           leaf output {
             type string;
           }
         }
         case multichassis-tag {
           anyxml multi-routing-engine-results;
         }
       }
     }
   }
   rpc request-mvpn-hrs-force-revert {
     description "Request MVPN HRS Force revert";
     junos:command "request mvpn hrs-force-revert";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case output-tag {
           leaf output {
             type string;
           }
         }
         case multichassis-tag {
           anyxml multi-routing-engine-results;
         }
       }
     }
   }
   rpc request-mvpn-hrs-force-revert-instance {
     description "Per instance";
     junos:command "request mvpn hrs-force-revert instance";
     input {
       leaf instance_name {
         description "Name of instance";
         junos:cli-feature "nokeyword";
         type string;
         mandatory true;
       }
       leaf group {
         description "IP address of multicast group";
         type jt:ipprefix;
         mandatory true;
       }
       leaf source {
         description "IP address multicast source";
         type jt:ipprefix;
         mandatory true;
       }
     }
     output {
       choice output-tags {
         case output-tag {
           leaf output {
             type string;
           }
         }
         case multichassis-tag {
           anyxml multi-routing-engine-results;
         }
       }
     }
   }
   rpc pim-multicast-tunnel {
     description "Request PIM MT rebalance";
     junos:command "request pim multicast-tunnel rebalance";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output-tags {
         case output-tag {
           leaf output {
             type string;
           }
         }
         case multichassis-tag {
           anyxml multi-routing-engine-results;
         }
       }
     }
   }
   rpc request-programmable-rpd-rpc-dump-information {
     description "Request RPC dump from rpd";
     junos:command "request programmable-rpd rpc-dump";
     output {
       choice output-tags {
         case output-tag {
           leaf output {
             type string;
           }
         }
         case multichassis-tag {
           anyxml multi-routing-engine-results;
         }
       }
     }
   }
   rpc request-virtual-chassis-reactivate {
     description "Make active from inactive-split mode";
     junos:command "request virtual-chassis reactivate";
     output {
       choice output-tags {
         case output-tag {
           leaf output {
             type string;
           }
         }
         case multichassis-tag {
           anyxml multi-routing-engine-results;
         }
       }
     }
   }
   rpc request-virtual-chassis-renumber {
     description "Change member ID";
     junos:command "request virtual-chassis renumber";
     input {
       leaf member-id {
         description "Current member ID";
         type union {
           type string {
             pattern "<.*>|$.*";
           }
           type int32;
         }
         mandatory true;
       }
       leaf new-member-id {
         description "New member ID";
         type union {
           type string {
             pattern "<.*>|$.*";
           }
           type int32;
         }
         mandatory true;
       }
     }
     output {
       choice output-tags {
         case output-tag {
           leaf output {
             type string;
           }
         }
         case multichassis-tag {
           anyxml multi-routing-engine-results;
         }
       }
     }
   }
   rpc request-virtual-chassis-recycle {
     description "Recycle member ID";
     junos:command "request virtual-chassis recycle";
     input {
       leaf member-id {
         description "Member ID";
         type union {
           type string {
             pattern "<.*>|$.*";
           }
           type int32;
         }
         mandatory true;
       }
     }
     output {
       choice output-tags {
         case output-tag {
           leaf output {
             type string;
           }
         }
         case multichassis-tag {
           anyxml multi-routing-engine-results;
         }
       }
     }
   }
   rpc request-virtual-chassis-vc-port-set-interface {
     description "Member's virtual chassis interface";
     junos:command "request virtual-chassis vc-port set interface";
     input {
       uses command-forwarding;
       leaf interface-name {
         description "Name of dedicated virtual chassis interface";
         junos:cli-feature "nokeyword";
         type string;
         mandatory true;
       }
       leaf disable {
         description "Disable virtual chassis interface";
         type empty;
       }
     }
     output {
       choice output-tags {
         case output-tag {
           leaf output {
             type string;
           }
         }
         case multichassis-tag {
           anyxml multi-routing-engine-results;
         }
       }
     }
   }
   rpc request-virtual-chassis-vc-port-set-pic-slot {
     description "Member's PIC slot";
     junos:command "request virtual-chassis vc-port set pic-slot";
     input {
       uses command-forwarding;
       leaf pic-slot {
         description "PIC slot number";
         junos:cli-feature "nokeyword";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output-tags {
         case output-tag {
           leaf output {
             type string;
           }
         }
         case multichassis-tag {
           anyxml multi-routing-engine-results;
         }
       }
     }
   }
   rpc request-virtual-chassis-vc-port-set-fpc-slot {
     description "Member's FPC slot";
     junos:command "request virtual-chassis vc-port set fpc-slot";
     input {
       uses command-forwarding;
       leaf fpc-slot {
         description "FPC slot number";
         junos:cli-feature "nokeyword";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output-tags {
         case output-tag {
           leaf output {
             type string;
           }
         }
         case multichassis-tag {
           anyxml multi-routing-engine-results;
         }
       }
     }
   }
   rpc request-virtual-chassis-vc-port-delete-pic-slot {
     description "Member's PIC slot";
     junos:command "request virtual-chassis vc-port delete pic-slot";
     input {
       uses command-forwarding;
       leaf pic-slot {
         description "PIC slot number";
         junos:cli-feature "nokeyword";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output-tags {
         case output-tag {
           leaf output {
             type string;
           }
         }
         case multichassis-tag {
           anyxml multi-routing-engine-results;
         }
       }
     }
   }
   rpc request-virtual-chassis-vc-port-delete-fpc-slot {
     description "Member's FPC slot";
     junos:command "request virtual-chassis vc-port delete fpc-slot";
     input {
       uses command-forwarding;
       leaf fpc-slot {
         description "FPC slot number";
         junos:cli-feature "nokeyword";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output-tags {
         case output-tag {
           leaf output {
             type string;
           }
         }
         case multichassis-tag {
           anyxml multi-routing-engine-results;
         }
       }
     }
   }
   rpc req-virtual-chassis-mode {
     description "Set a member's mode (Warning: member's mode must be consistent)";
     junos:command "request virtual-chassis mode";
     input {
       uses command-forwarding;
       leaf mixed {
         description "Allow devices from different product families to become members";
         type empty;
       }
       leaf disable {
         description "Disable specified mode";
         type empty;
       }
       leaf network-port {
         description "Delete VC ports";
         type empty;
       }
       leaf hgoe {
         description "Virtual Chassis will operate in HGOE mode";
         type empty;
       }
       leaf homogeneous-mix-vc-mode {
         description "Virtual Chassis will operate in Homogeneous mix vc mode";
         type empty;
       }
     }
     output {
       choice output-tags {
         case output-tag {
           leaf output {
             type string;
           }
         }
         case multichassis-tag {
           anyxml multi-routing-engine-results;
         }
       }
     }
   }
   rpc set-virtual-chassis-member-id {
     description "Set virtual-chassis information";
     junos:command "request virtual-chassis member-id set";
     input {
       leaf member {
         description "Virtual-Chassis member number";
         type union {
           type string {
             pattern "<.*>|$.*";
           }
           type int32;
         }
         mandatory true;
       }
     }
     output {
       choice output-tags {
         case output-tag {
           leaf output {
             type string;
           }
         }
         case multichassis-tag {
           anyxml multi-routing-engine-results;
         }
       }
     }
   }
   rpc delete-virtual-chassis-member-id {
     description "Delete virtual-chassis information";
     junos:command "request virtual-chassis member-id delete";
     output {
       choice output-tags {
         case output-tag {
           leaf output {
             type string;
           }
         }
         case multichassis-tag {
           anyxml multi-routing-engine-results;
         }
       }
     }
   }
   rpc get-virtual-chassis-diagnostic-information {
     description "Device reachability diagnostics";
     junos:command "request virtual-chassis device-reachability";
     input {
       leaf test-name {
         description "Name of the test";
         type string {
           length "1 .. 20";
         }
         mandatory true;
       }
       leaf destination-device {
         description "Probe destination (global) device ID";
         type union {
           type uint32;
           type string {
             pattern "<.*>|$.*";
           }
         }
       }
       leaf destination-fpc {
         description "Probe destination FPC";
         type union {
           type uint32;
           type string {
             pattern "<.*>|$.*";
           }
         }
       }
       leaf destination-ip-address {
         description "IP address of destination FPC";
         type jt:ipaddr;
       }
       leaf source-fpc {
         description "Probe initiator FPC";
         type union {
           type uint32;
           type string {
             pattern "<.*>|$.*";
           }
         }
       }
       leaf source-ip-address {
         description "IP address of source FPC";
         type jt:ipaddr;
       }
       leaf probe-size {
         description "Size of one probe in bytes";
         default "56";
         type union {
           type string {
             pattern "<.*>|$.*";
           }
           type uint32 {
             range "56 .. 1500";
           }
         }
       }
       leaf probe-count {
         description "Number of probes in a test";
         default "5";
         type union {
           type string {
             pattern "<.*>|$.*";
           }
           type uint32 {
             range "1 .. 10";
           }
         }
       }
       leaf probe-pattern {
         description "Payload pattern byte in the probe (0x00-0xff)";
         default "0x00";
         type string {
           junos:posix-pattern "^0(x|X)([0-9|a-f|A-F])([0-9|a-f|A-F])$";
           junos:pattern-message "Must be hexadecimal bit pattern in (0x00..0xff)";
         }
       }
       leaf probe-interval {
         description "Duration between successive probes";
         default "1";
         units "seconds";
         type union {
           type string {
             pattern "<.*>|$.*";
           }
           type uint32 {
             range "1 .. 3";
           }
         }
       }
       leaf test-interval {
         description "Time interval to perform this test again";
         default "1";
         units "seconds";
         type union {
           type string {
             pattern "<.*>|$.*";
           }
           type uint32 {
             range "1 .. 5";
           }
         }
       }
       leaf test-count {
         description "Number of times this test to be performed";
         default "1";
         type union {
           type string {
             pattern "<.*>|$.*";
           }
           type uint32 {
             range "1 .. 3";
           }
         }
       }
     }
     output {
       choice output-tags {
         case actual-tag {
           container virtual-chassis-diagnostic-information {
             uses virtual-chassis-diagnostic-information-block;
           }
         }
         case multichassis-tag {
           container multi-routing-engine-results {
             list multi-routing-engine-item {
               leaf re-name {
                 type string;
               }
               choice output-tags {
                 case actual-tag {
                   container virtual-chassis-diagnostic-information {
                     uses virtual-chassis-diagnostic-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping rescue-management-results-block {
     list routing-engine {
       key "name";
       leaf name {
         type string;
         description
           "Syslog message tag name";
       }
       leaf success {
         type empty;
         description
           "Rescue configuration operation succeeded";
       }
       leaf commit-check-success {
         type empty;
         description
           "Configuration check succeeds";
       }
       leaf commit-success {
         type empty;
         description
           "Configuration commit is complete";
       }
       leaf commit-queued {
         type empty;
         description
           "Configuration commit is queued";
       }
       leaf commit-prepare-success {
         type empty;
         description
           "Commit cache is successfully prepared";
       }
       container satellite-commit-check-results {
         list satellite {
           key "name";
           leaf name {
             type string;
             description
               "Syslog message tag name";
           }
           leaf satellite-commit-check-success {
             type empty;
             description
               "Configuration check succeeds";
           }
         }
       }
     }
   }
   grouping commit-server-delete-results-block {
     leaf commit-server-delete-success {
       type empty;
     }
     leaf commit-server-delete-failed-match {
       type empty;
     }
   }
   grouping commit-server-operation-block {
     leaf-list message {
       type string;
       description
         "Pause message";
     }
     container pause-status {
       description
         "Commit server pause status";
       leaf pause-success {
         type empty;
         description
           "Pause success";
       }
       leaf pause-error {
         type empty;
         description
           "Pause error";
       }
       leaf pause-already {
         type empty;
         description
           "Commit server is already paused";
       }
     }
     container start-status {
       description
         "Commit server start status";
       leaf start-success {
         type empty;
         description
           "Start success";
       }
       leaf start-error {
         type empty;
         description
           "Start error";
       }
       leaf start-already {
         type empty;
         description
           "Commit server is already running";
       }
     }
   }
   grouping logout-user-block {
     leaf logout-user-message {
       type string;
     }
   }
   grouping genstate-json-schema-result-block {
     leaf schema-generated {
       type empty;
     }
   }
   grouping package-status-block {
     leaf package-status-message {
       type string;
       description
         "Show software installation status";
     }
   }
   grouping add-license-results-block {
     leaf add-success {
       type empty;
       description
         "Add completed with no errors";
     }
     leaf add-error-count {
       type int32;
       description
         "Number of errors during add license operation";
     }
     list add-individual-result {
       key "name";
       description
         "Report status of individual license add operation";
       leaf filename {
         type string;
         description
           "File name in which error exist";
       }
       leaf line-number {
         type int32;
         description
           "Line number where error exist";
       }
       leaf operation-status {
         type string;
         description
           "Defines that status of a license operation";
       }
       leaf name {
         type string;
         description
           "Identifier for this object";
       }
       leaf message {
         type string;
         description
           "Text to explain the status of an operation";
       }
     }
   }
   grouping inform-block {
     leaf source-daemon {
       type string;
     }
     leaf message {
       type string;
       description
         "Syslog message text";
     }
   }
   grouping system-storage-cleanup-information-block {
     leaf dre-repository-status {
       type string;
       description
         "DRE repository status";
     }
     container file-list {
       container file {
         description
           "Information about a cleanup candidate";
         leaf size {
           type int32;
           description
             "File size in bytes";
         }
         leaf date {
           type string;
           description
             "Modification time";
         }
         leaf file-name {
           type string;
           description
             "File name";
         }
         container file-fetch {
           leaf source-filename {
             type string;
           }
           leaf source-address {
             type string;
           }
           leaf staging-directory {
             type string;
           }
           leaf routing-instance {
             type string;
           }
           leaf cert-file {
             type string;
           }
           leaf no-check-certificate {
             type string;
           }
           leaf no-stage {
             type string;
           }
           leaf destination-filename {
             type string;
           }
         }
         container file-put {
           leaf source-filename {
             type string;
           }
           leaf destination-filename {
             type string;
           }
           leaf source-address {
             type string;
           }
           leaf routing-instance {
             type string;
           }
           leaf cleanup-source {
             type empty;
           }
           leaf filename {
             type string;
           }
           leaf encoding {
             type string;
             description
               "Encoding type: ascii or base64";
           }
           leaf permission {
             type string;
             description
               "Permission of destination file";
           }
           leaf delete-if-exist {
             type empty;
             description
               "Delete destination file if it exists";
           }
           leaf file-contents {
             type string;
             description
               "Base64 encoded contents of file";
           }
         }
         container send-file {
           leaf source-filename {
             type string;
           }
           leaf alias-filename {
             type string;
           }
           leaf display-spinner {
             type empty;
           }
           leaf source-address {
             type string;
           }
           leaf routing-instance {
             type string;
           }
         }
       }
     }
     container dre-repository-content {
       leaf dre-repository-content-header {
         type string;
         description
           "DRE repository content header";
       }
       leaf dre-repository-content-entry {
         type string;
         description
           "DRE repository content entry";
       }
       leaf dre-repository-content-footer {
         type string;
         description
           "DRE repository content footer";
       }
     }
   }
   grouping request-reboot-results-block {
     leaf request-reboot-status {
       type string;
       description
         "Reboot request status";
     }
   }
   grouping snapshot-information-block {
     leaf snapshot-medium {
       type string;
       description
         "Media type of the snapshot";
     }
     leaf creation-date {
       type string;
       description
         "Snapshot creation date";
     }
     container inform {
       leaf source-daemon {
         type string;
       }
       leaf message {
         type string;
         description
           "Syslog message text";
       }
     }
     container snapshot-copy {
       leaf source-directory {
         type string;
         description
           "Directory to backup";
       }
       leaf destination-directory {
         type string;
         description
           "Backup directory";
       }
     }
     container archived-directory-list {
       leaf directory-name {
         type string;
         description
           "Directory name";
       }
     }
     container snapshot-partitions {
       description
         "Partitions on snapshot medium";
       list partition-information {
         description
           "Partition information";
         leaf partition {
           type string;
           description
             "Partition letter";
         }
         leaf mount-point {
           type string;
           description
             "Mount point";
         }
         leaf partition-size {
           type string;
           description
             "Size of partition";
         }
         leaf snapshot-argument {
           type string;
           description
             "Argument to snapshot used to configure size";
         }
       }
     }
     container software-version {
       description
         "Version of software snapshot";
       list package {
         description
           "Package in software snapshot";
         leaf package-name {
           type string;
           description
             "Name of software package";
         }
         leaf package-version {
           type string;
           description
             "Version of software package";
         }
       }
     }
   }
   grouping system-firmware-information-block {
     list system-firmware {
       leaf firmware-name {
         type string;
         description
           "Name of this component";
       }
       leaf firmware-type {
         type string;
         description
           "Type of this component";
       }
       leaf firmware-tag {
         type int32;
         description
           "Multiple firmware per FRU delimiter";
       }
       leaf firmware-revision {
         type string;
         description
           "Firmware version for this component";
       }
       leaf firmware-revision-available {
         type string;
         description
           "Firmware version available on disk for this component";
       }
       leaf firmware-status {
         type string;
         description
           "Firmware status for this component";
       }
       container system-module {
         leaf firmware-name {
           type string;
           description
             "Name of this component";
         }
         container firmware-state {
           description
             "Firmware status per component type";
           leaf firmware-type {
             type string;
             description
               "Type of this component";
           }
           leaf firmware-status {
             type string;
             description
               "Firmware status for this component";
           }
         }
       }
       container system-sub-module-firmware-list {
         list system-sub-module-firmware {
           description
             "Firmware sub module";
           leaf firmware-name {
             type string;
             description
               "Name of this component";
           }
           leaf firmware-type {
             type string;
             description
               "Type of this component";
           }
           leaf firmware-tag {
             type int32;
             description
               "Multiple firmware per FRU delimiter";
           }
           leaf firmware-revision {
             type string;
             description
               "Firmware version for this component";
           }
           leaf firmware-revision-available {
             type string;
             description
               "Firmware version available on disk for this component";
           }
           leaf firmware-status {
             type string;
             description
               "Firmware status for this component";
           }
         }
       }
     }
   }
   grouping download-information-block {
     leaf status {
       type string;
       description
         "Status of a download request";
     }
     leaf progress {
       type string;
       description
         "Percentage of download completed";
     }
     leaf download-id {
       type string;
       description
         "ID of the download";
     }
     leaf download-url {
       type string;
       description
         "URL to download from";
     }
     leaf local-path {
       type string;
       description
         "Local path to which the file gets downloaded";
     }
     leaf max-rate {
       type string;
       description
         "Maximum rate for performing the download";
     }
     leaf creation-time {
       type string;
       description
         "Date and time when the download was created";
     }
     leaf scheduled-time {
       type string;
       description
         "Date and time when the download was requested to start";
     }
     leaf start-time {
       type string;
       description
         "Date and time when the download was actually started or restarted 
         after error";
     }
     leaf retry-time {
       type string;
       description
         "Date and time when the download is scheduled to start again after 
         error";
     }
     leaf retries-left {
       type string;
       description
         "Number of times the system will retry the download automatically 
         after error";
     }
     leaf completion-time {
       type string;
       description
         "Date and time when the download completed";
     }
     leaf error-count {
       type string;
       description
         "Number of times an error condition has been encountered during 
         download";
     }
     leaf error-message {
       type string;
       description
         "Error message";
     }
     list download-info-brief {
       description
         "Download status information";
       leaf download-id {
         type string;
         description
           "ID of the download";
       }
       leaf status {
         type string;
         description
           "Status of a download request";
       }
       leaf start-time {
         type string;
         description
           "Date and time when the download was actually started or 
           restarted after error";
       }
       leaf progress {
         type string;
         description
           "Percentage of download completed";
       }
       leaf download-url {
         type string;
         description
           "URL to download from";
       }
     }
     list download-info-detail {
       description
         "Detailed download status information";
       leaf download-id {
         type string;
         description
           "ID of the download";
       }
       leaf status {
         type string;
         description
           "Status of a download request";
       }
       leaf progress {
         type string;
         description
           "Percentage of download completed";
       }
       leaf download-url {
         type string;
         description
           "URL to download from";
       }
       leaf local-path {
         type string;
         description
           "Local path to which the file gets downloaded";
       }
       leaf max-rate {
         type string;
         description
           "Maximum rate for performing the download";
       }
       leaf creation-time {
         type string;
         description
           "Date and time when the download was created";
       }
       leaf scheduled-time {
         type string;
         description
           "Date and time when the download was requested to start";
       }
       leaf start-time {
         type string;
         description
           "Date and time when the download was actually started or 
           restarted after error";
       }
       leaf retry-time {
         type string;
         description
           "Date and time when the download is scheduled to start again 
           after error";
       }
       leaf completion-time {
         type string;
         description
           "Date and time when the download completed";
       }
       leaf error-count {
         type string;
         description
           "Number of times an error condition has been encountered during 
           download";
       }
       leaf retries-left {
         type string;
         description
           "Number of times the system will retry the download automatically
           after error";
       }
       leaf error-message {
         type string;
         description
           "Error message";
       }
     }
   }
   grouping system-evpn-block {
     leaf evpn-host {
       type string;
       description
         "Evpn host";
     }
     container vlans {
       leaf summary {
         type string;
         description
           "Summary";
       }
       leaf vlans-in-sync {
         type string;
         description
           "Vlans in sync";
       }
       leaf vlans-out-of-sync {
         type string;
         description
           "Vlans out of sync";
       }
       list mac-table {
         leaf instance {
           type string;
           description
             "Routing instance name";
         }
         leaf vlan {
           type string;
           description
             "Vlan name";
         }
         leaf entry {
           type string;
           description
             "Entry";
         }
         leaf error {
           type string;
           description
             "Error";
         }
       }
       list mac-ip-table {
         leaf instance {
           type string;
           description
             "Routing instance name";
         }
         leaf vlan {
           type string;
           description
             "Vlan name";
         }
         leaf entry {
           type string;
           description
             "Entry";
         }
         leaf error {
           type string;
           description
             "Error";
         }
       }
       list mac-table-hash {
         leaf instance {
           type string;
           description
             "Routing instance name";
         }
         leaf vlan {
           type string;
           description
             "Vlan name";
         }
         leaf l2-hash {
           type string;
           description
             "L2 hash";
         }
       }
       list mac-ip-table-hash {
         leaf instance {
           type string;
           description
             "Routing instance name";
         }
         leaf vlan {
           type string;
           description
             "Vlan name";
         }
         leaf l2-hash {
           type string;
           description
             "L2 hash";
         }
       }
     }
   }
   grouping cert-key-pair-block {
     leaf cert-key-pair-name {
       type string;
       description
         "Key pair name";
     }
     leaf cert-key-pair-size {
       type string;
       description
         "Key pair size";
     }
   }
   grouping cert-ca-load-status-block {
     leaf cert-ca-profile {
       type string;
       description
         "Certificate Authority profile";
     }
   }
   grouping default-trusted-ca-certs-download-block {
     leaf trusted-ca-certs-download-status {
       type string;
       description
         "Download default trusted CA cert status";
     }
   }
   grouping default-trusted-ca-certs-download-cs-block {
     leaf default-trusted-ca-certs-download-check-server-status {
       type string;
       description
         "Default trusted CA certs check CDN server status";
     }
   }
   grouping default-trusted-ca-certs-download-status-block {
     leaf default-trusted-ca-certs-version-on-system {
       type string;
       description
         "Existing default trusted CA certs on system status";
     }
   }
   grouping cert-load-status-block {
     leaf cert-certificate-id {
       type string;
       description
         "Certificate identifier";
     }
   }
   grouping ca-profile-group-cert-status-block {
     leaf ca-group-cert-status {
       type string;
       description
         "CA Profile Group CA Cert Status";
     }
     leaf ca-group-missing-certs {
       type string;
       description
         "CA Profile Group CA Cert Status";
     }
   }
   grouping verify-integrity-status-block {
     leaf int-check-verification-status {
       type string;
       description
         "Integrity check verification status";
     }
   }
   grouping bounce-interface-block {
     container bounce-operation-status {
       leaf interface-name {
         type string;
         description
           "Interface name";
       }
       leaf interval {
         type uint32;
       }
     }
   }
   grouping extension-service-daemonize-restart-status-block {
     leaf extension-service-stop-status {
       type string;
     }
     leaf extension-service-start-status {
       type string;
     }
   }
   grouping jdaf-request-no-response-block {
     leaf error-msg {
       type string;
       description
         "Error message";
     }
   }
   grouping tdir-flb-maintenance-down-status-block {
     leaf tdir-req-flb-destination-maintenance-down-status {
       type string;
       description
         "Prints the status";
     }
   }
   grouping lacp-link-switchover-block {
     leaf aggregate-name {
       type string;
       description
         "Aggregated Interface name";
     }
     leaf lacp-status {
       type string;
       description
         "Lacp return status";
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping snmp-spoof-trap-results-block {
     leaf snmp-spoofable-traps {
       type string;
       description
         "SNMP traps supported for spoofing";
     }
     leaf snmp-spoof-trap-result {
       type string;
       description
         "Result of SNMP 'spoof-trap' request";
     }
   }
   grouping snmp-utility-mib-results-block {
     leaf snmp-utility-mib-result {
       type string;
       description
         "Result of SNMP 'utility-mib' request";
     }
   }
   grouping chassis-fpc-state-block {
     leaf summary {
       type string;
     }
     leaf-list error-info {
       type string;
     }
   }
   grouping chassis-fabric-plane-state-block {
     leaf summary {
       type string;
     }
     leaf-list error-info {
       type string;
     }
   }
   grouping chassis-routing-engine-state-block {
     leaf summary {
       type string;
     }
     leaf message {
       type string;
     }
     leaf error {
       type string;
     }
     leaf master-switch-readiness-status {
       type string;
       description
         "Current status of graceful Routing Engine Switchover";
     }
     leaf nonstop-routing-status {
       type string;
       description
         "Current status of nonstop routing";
     }
   }
   grouping helper-self-mirror-enable-disable-block {
     leaf smpl-request-start-stop-status {
       type string;
       description
         "Request self port-mirroring status";
     }
   }
   grouping flight-recorder-information-block {
     container summary {
       leaf output {
         type string;
       }
     }
   }
   grouping virtual-chassis-diagnostic-information-block {
     container test-information {
       description
         "Details of the test";
       leaf test-name {
         type string;
         description
           "Name of the Device Reachability test";
       }
     }
     list current-test {
       description
         "Serial number of the test being performed";
       leaf test-number {
         type string;
         description
           "Serial Number of the test";
       }
     }
     list device-reachability-information {
       description
         "Device reachability statistics";
       leaf-list reachability-acknowledge {
         type string;
       }
       leaf connectivity-statistics-header {
         type string;
       }
       leaf session-information {
         type string;
       }
       leaf session-id {
         type uint32;
         description
           "Session ID";
       }
       leaf packet-response-information {
         type string;
       }
       leaf packet-count {
         type uint32;
         description
           "Total number of packets sent";
       }
       leaf packets-sent {
         type uint64;
       }
       leaf packets-received {
         type uint64;
       }
       leaf packets-sendfail {
         type uint32;
         description
           "Number of packets dropped";
       }
       leaf packet-breakup-information {
         type string;
       }
       leaf packets-unknown {
         type uint32;
         description
           "Number of unknown packets";
       }
       leaf packets-timedout {
         type uint32;
         description
           "Number of packets received after timeout";
       }
       leaf packets-duplicate-reply {
         type uint32;
         description
           "Number of duplicate reply packets";
       }
       leaf round-trip-information {
         type string;
       }
       leaf round-trip-time-minimum {
         type uint32;
         description
           "Minimum round trip time in seconds";
       }
       leaf round-trip-time-average {
         type uint32;
         description
           "Average round trip time in seconds";
       }
       leaf round-trip-time-maximum {
         type uint32;
         description
           "Minimum round trip time in seconds";
       }
       leaf test-interval {
         type string;
         description
           "Interval between successive tests";
       }
     }
     list virtual-chassis-diagnostic-error {
       leaf name {
         type string;
       }
     }
   }
 }
