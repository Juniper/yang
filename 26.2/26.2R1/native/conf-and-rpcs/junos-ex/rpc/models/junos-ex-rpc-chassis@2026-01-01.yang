/*
 * Copyright (c) 2026 Juniper Networks, Inc.
 * All rights reserved.
 */
 module junos-ex-rpc-chassis {
   namespace "http://yang.juniper.net/junos-ex/rpc/chassis";

   prefix chassis;

   import junos-common-types {
     prefix jt;
     revision-date 2026-01-01;
   }

   organization "Juniper Networks, Inc.";

   contact "yang-support@juniper.net";

   description "Junos RPC YANG module for chassis command(s)";

   revision 2026-01-01 {
     description "Junos: 26.2R1.7";
   }

   rpc get-alarm-information {
     description "Show alarm status";
     input {
       uses command-forwarding;
     }
     output {
       choice output-tags {
         case actual-tag {
           container alarm-information {
             uses alarm-information-block;
           }
         }
         case multichassis-tag {
           container multi-routing-engine-results {
             list multi-routing-engine-item {
               leaf re-name {
                 type string;
               }
               choice output-tags {
                 case actual-tag {
                   container alarm-information {
                     uses alarm-information-block;
                   }
                 }
               }
             }
           }
         }
       }
     }
   }
   rpc get-chassis-errors {
     description "Show chassis errors";
     input {
       leaf fpc-slot {
         description "Slot number of FPC";
         type union {
           type string {
             pattern "<.*>|$.*";
           }
           type uint32;
         }
         mandatory true;
       }
     }
     output {
       choice output-tags {
         case output-tag {
           leaf output {
             type string;
           }
         }
         case actual-tag {
           anyxml chassis-error-information;
         }
         case multichassis-tag {
           anyxml multi-routing-engine-results;
         }
       }
     }
   }
   rpc get-satellite-device-list {
     description "Displays active satellite devices";
     output {
       choice output-tags {
         case actual-tag {
           container satellite-device-list {
             uses satellite-device-list-block;
           }
         }
         case multichassis-tag {
           container multi-routing-engine-results {
             list multi-routing-engine-item {
               leaf re-name {
                 type string;
               }
               choice output-tags {
                 case actual-tag {
                   container satellite-device-list {
                     uses satellite-device-list-block;
                   }
                 }
               }
             }
           }
         }
       }
     }
   }
   rpc get-craft-information {
     description "Show craft interface status";
     input {
       uses command-forwarding;
     }
     output {
       choice output-tags {
         case actual-tag {
           container craft-information {
             uses craft-information-block;
           }
         }
         case multichassis-tag {
           container multi-routing-engine-results {
             list multi-routing-engine-item {
               leaf re-name {
                 type string;
               }
               choice output-tags {
                 case actual-tag {
                   container craft-information {
                     uses craft-information-block;
                   }
                 }
               }
             }
           }
         }
       }
     }
   }
   rpc get-ethernet-switch-information {
     description "Show Ethernet switch information";
     input {
       uses command-forwarding;
     }
     output {
       choice output-tags {
         case actual-tag {
           container ethernet-switch-information {
             uses ethernet-switch-information-block;
           }
         }
         case multichassis-tag {
           container multi-routing-engine-results {
             list multi-routing-engine-item {
               leaf re-name {
                 type string;
               }
               choice output-tags {
                 case actual-tag {
                   container ethernet-switch-information {
                     uses ethernet-switch-information-block;
                   }
                 }
               }
             }
           }
         }
       }
     }
   }
   rpc get-ethernet-switch-statistics-information {
     description "Show Ethernet switch traffic statistics";
     input {
       uses command-forwarding;
       leaf switch {
         description "Switch number";
         type union {
           type string {
             pattern "<.*>|$.*";
           }
           type uint32;
         }
       }
       leaf port {
         description "Port number";
         type union {
           type string {
             pattern "<.*>|$.*";
           }
           type uint32;
         }
       }
     }
     output {
       choice output-tags {
         case actual-tag {
           container ethernet-switch-statistics-information {
             uses ethernet-switch-statistics-information-block;
           }
         }
         case multichassis-tag {
           container multi-routing-engine-results {
             list multi-routing-engine-item {
               leaf re-name {
                 type string;
               }
               choice output-tags {
                 case actual-tag {
                   container ethernet-switch-statistics-information {
                     uses ethernet-switch-statistics-information-block;
                   }
                 }
               }
             }
           }
         }
       }
     }
   }
   rpc get-environment-information {
     description "Show component status and temperature, cooling system speeds";
     input {
       uses command-forwarding;
     }
     output {
       choice output-tags {
         case actual-tag {
           container environment-information {
             uses environment-information-block;
           }
         }
         case multichassis-tag {
           container multi-routing-engine-results {
             list multi-routing-engine-item {
               leaf re-name {
                 type string;
               }
               choice output-tags {
                 case actual-tag {
                   container environment-information {
                     uses environment-information-block;
                   }
                 }
               }
             }
           }
         }
       }
     }
   }
   rpc get-environment-sib-information {
     description "Show Switch Interface Board information";
     input {
       uses command-forwarding;
       leaf sib-slot {
         description "SIB slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-fpc-information {
     description "Show Flexible PIC Concentrator information";
     input {
       uses command-forwarding;
       leaf fpc-slot {
         description "FPC slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-cb-information {
     description "Show Control Board information";
     input {
       uses command-forwarding;
       leaf slot {
         description "CB slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-psu-information {
     description "Show Power Supply Unit information";
     input {
       uses command-forwarding;
       leaf slot {
         description "PSU slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-power-supply-unit-information {
     description "Show power supply unit information";
     input {
       uses command-forwarding;
       leaf slot {
         description "FPC slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-environment-re-information {
     description "Show Routing Engine information";
     input {
       uses command-forwarding;
       leaf slot {
         description "Routing Engine slot number";
         type union {
           type string {
             pattern "<.*>|$.*";
           }
           type uint32;
         }
       }
     }
     output {
       choice output-tags {
         case actual-tag {
           container environment-component-information {
             uses environment-component-information-block;
           }
         }
         case multichassis-tag {
           container multi-routing-engine-results {
             list multi-routing-engine-item {
               leaf re-name {
                 type string;
               }
               choice output-tags {
                 case actual-tag {
                   container environment-component-information {
                     uses environment-component-information-block;
                   }
                 }
               }
             }
           }
         }
       }
     }
   }
   rpc get-firmware-information {
     description "Show firmware and operating system version for components";
     input {
       uses command-forwarding;
     }
     output {
       choice output-tags {
         case actual-tag {
           container firmware-information {
             uses firmware-information-block;
           }
         }
         case multichassis-tag {
           container multi-routing-engine-results {
             list multi-routing-engine-item {
               leaf re-name {
                 type string;
               }
               choice output-tags {
                 case actual-tag {
                   container firmware-information {
                     uses firmware-information-block;
                   }
                 }
               }
             }
           }
         }
       }
     }
   }
   rpc get-firmware-information-detail {
     description "Show detailed output";
     output {
       choice output-tags {
         case actual-tag {
           container hardware-version-information {
             uses hardware-version-information-block;
           }
         }
         case multichassis-tag {
           container multi-routing-engine-results {
             list multi-routing-engine-item {
               leaf re-name {
                 type string;
               }
               choice output-tags {
                 case actual-tag {
                   container hardware-version-information {
                     uses hardware-version-information-block;
                   }
                 }
               }
             }
           }
         }
       }
     }
   }
   rpc get-usb-storage-status {
     description "Show USB storage status";
     output {
       choice output-tags {
         case output-tag {
           leaf output {
             type string;
           }
         }
         case actual-tag {
           anyxml usb-storage-status;
         }
         case multichassis-tag {
           anyxml multi-routing-engine-results;
         }
       }
     }
   }
   rpc get-fpc-information {
     description "Show Flexible PIC Concentrator status";
     input {
       uses command-forwarding;
       leaf detail {
         description "Display detailed output";
         type empty;
       }
       leaf fpc-slot {
         description "FPC slot number";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-pic-information {
     description "Show Physical Interface Cards installed in FPC";
     input {
       uses command-forwarding;
       leaf slot {
         description "FPC slot number";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-mic-information {
     description "Show Modular Interface Cards installed in FPC";
     input {
       leaf slot {
         description "FPC slot number";
         type union {
           type string {
             pattern "<.*>|$.*";
           }
           type uint32;
         }
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-fpc-ether-types-information {
     description "Show Ether Types";
     input {
       leaf slot {
         description "FPC slot number";
         type union {
           type string {
             pattern "<.*>|$.*";
           }
           type uint32;
         }
       }
     }
     output {
       choice output-tags {
         case actual-tag {
           container fpc-ether-types-information {
             uses fpc-ether-types-information-block;
           }
         }
         case multichassis-tag {
           container multi-routing-engine-results {
             list multi-routing-engine-item {
               leaf re-name {
                 type string;
               }
               choice output-tags {
                 case actual-tag {
                   container fpc-ether-types-information {
                     uses fpc-ether-types-information-block;
                   }
                 }
               }
             }
           }
         }
       }
     }
   }
   rpc get-fpc-port-information {
     description "Show Port status installed in FPC";
     input {
       leaf slot {
         description "FPC slot number";
         type union {
           type string {
             pattern "<.*>|$.*";
           }
           type uint32;
         }
       }
     }
     output {
       choice output-tags {
         case actual-tag {
           container fpc-port-information {
             uses fpc-port-information-block;
           }
         }
         case multichassis-tag {
           container multi-routing-engine-results {
             list multi-routing-engine-item {
               leaf re-name {
                 type string;
               }
               choice output-tags {
                 case actual-tag {
                   container fpc-port-information {
                     uses fpc-port-information-block;
                   }
                 }
               }
             }
           }
         }
       }
     }
   }
   rpc get-vcpu-information {
     description "Show Visibility CPU status";
     input {
       uses command-forwarding;
       leaf detail {
         description "Display detailed output";
         type empty;
       }
       leaf slot {
         description "VCPU slot number";
         type union {
           type string {
             pattern "<.*>|$.*";
           }
           type uint32;
         }
       }
     }
     output {
       choice output-tags {
         case output-tag {
           leaf output {
             type string;
           }
         }
         case actual-tag {
           anyxml vcpu-information;
         }
         case multichassis-tag {
           anyxml multi-routing-engine-results;
         }
       }
     }
   }
   rpc get-pic-detail {
     description "Show Physical Interface Card state, type, and uptime";
     input {
       uses command-forwarding;
       leaf fpc-slot {
         description "Slot number of FPC that houses PIC";
         type union {
           type string {
             pattern "<.*>|$.*";
           }
           type uint32;
         }
       }
       leaf pic-slot {
         description "PIC slot number";
         type union {
           type string {
             pattern "<.*>|$.*";
           }
           type int32;
         }
         mandatory true;
       }
     }
     output {
       choice output-tags {
         case actual-tag {
           container fpc-information {
             uses fpc-information-block;
           }
         }
         case multichassis-tag {
           container multi-routing-engine-results {
             list multi-routing-engine-item {
               leaf re-name {
                 type string;
               }
               choice output-tags {
                 case actual-tag {
                   container fpc-information {
                     uses fpc-information-block;
                   }
                 }
               }
             }
           }
         }
       }
     }
   }
   rpc get-sib-information {
     description "Show Switch Interface Board status";
     input {
       uses command-forwarding;
     }
     output {
       choice output-tags {
         case actual-tag {
           container sib-information {
             uses sib-information-block;
           }
         }
         case multichassis-tag {
           container multi-routing-engine-results {
             list multi-routing-engine-item {
               leaf re-name {
                 type string;
               }
               choice output-tags {
                 case actual-tag {
                   container sib-information {
                     uses sib-information-block;
                   }
                 }
               }
             }
           }
         }
       }
     }
   }
   rpc get-sibs-errors {
     description "Show ASIC errors on sib";
     input {
       leaf sib-slot {
         description "SIB slot number";
         type union {
           type string {
             pattern "<.*>|$.*";
           }
           type uint32;
         }
       }
     }
     output {
       choice output-tags {
         case actual-tag {
           container sib-information {
             uses sib-information-block;
           }
         }
         case multichassis-tag {
           container multi-routing-engine-results {
             list multi-routing-engine-item {
               leaf re-name {
                 type string;
               }
               choice output-tags {
                 case actual-tag {
                   container sib-information {
                     uses sib-information-block;
                   }
                 }
               }
             }
           }
         }
       }
     }
   }
   rpc get-replacement-status {
     description "Show fru replacement status";
     input {
       leaf replacement {
         description "Shows the replacemeent status";
         type enumeration {
           enum "status" {
             description "Shows the fru replacement status";
           }
         }
         mandatory true;
       }
     }
     output {
       choice output-tags {
         case output-tag {
           leaf output {
             type string;
           }
         }
         case multichassis-tag {
           anyxml multi-routing-engine-results;
         }
       }
     }
   }
   rpc get-fru-information {
     description "Show Line Card Chassis (LCC) status";
     output {
       choice output-tags {
         case actual-tag {
           container fru-information {
             uses fru-information-block;
           }
         }
         case multichassis-tag {
           container multi-routing-engine-results {
             list multi-routing-engine-item {
               leaf re-name {
                 type string;
               }
               choice output-tags {
                 case actual-tag {
                   container fru-information {
                     uses fru-information-block;
                   }
                 }
               }
             }
           }
         }
       }
     }
   }
   rpc get-jnu-satellites-information {
     description "Show jnu satellites information";
     output {
       choice output-tags {
         case actual-tag {
           container jnu-satellites-information {
             uses jnu-satellites-information-block;
           }
         }
         case multichassis-tag {
           container multi-routing-engine-results {
             list multi-routing-engine-item {
               leaf re-name {
                 type string;
               }
               choice output-tags {
                 case actual-tag {
                   container jnu-satellites-information {
                     uses jnu-satellites-information-block;
                   }
                 }
               }
             }
           }
         }
       }
     }
   }
   rpc get-jnu-role-information {
     description "Show jnu role";
     output {
       choice output-tags {
         case actual-tag {
           container jnu-role-information {
             uses jnu-role-information-block;
           }
         }
         case multichassis-tag {
           container multi-routing-engine-results {
             list multi-routing-engine-item {
               leaf re-name {
                 type string;
               }
               choice output-tags {
                 case actual-tag {
                   container jnu-role-information {
                     uses jnu-role-information-block;
                   }
                 }
               }
             }
           }
         }
       }
     }
   }
   rpc get-fm-fpc-state-information {
     description "Show summary fabric management FPC state from Routing Engine";
     input {
       uses command-forwarding;
     }
     output {
       choice output-tags {
         case actual-tag {
           container fm-fpc-state-information {
             uses fm-fpc-state-information-block;
           }
         }
         case multichassis-tag {
           container multi-routing-engine-results {
             list multi-routing-engine-item {
               leaf re-name {
                 type string;
               }
               choice output-tags {
                 case actual-tag {
                   container fm-fpc-state-information {
                     uses fm-fpc-state-information-block;
                   }
                 }
               }
             }
           }
         }
       }
     }
   }
   rpc get-fm-plane-location-information {
     description "Show fabric plane location";
     input {
       uses command-forwarding;
     }
     output {
       choice output-tags {
         case actual-tag {
           container fm-plane-location-information {
             uses fm-plane-location-information-block;
           }
         }
         case multichassis-tag {
           container multi-routing-engine-results {
             list multi-routing-engine-item {
               leaf re-name {
                 type string;
               }
               choice output-tags {
                 case actual-tag {
                   container fm-plane-location-information {
                     uses fm-plane-location-information-block;
                   }
                 }
               }
             }
           }
         }
       }
     }
   }
   rpc get-fm-topology {
     description "Show fabric topology for plane";
     input {
       uses command-forwarding;
       leaf plane {
         description "Fabric plane number";
         type union {
           type string {
             pattern "<.*>|$.*";
           }
           type uint32;
         }
       }
     }
     output {
       choice output-tags {
         case actual-tag {
           container fm-topology {
             uses fm-topology-block;
           }
         }
         case multichassis-tag {
           container multi-routing-engine-results {
             list multi-routing-engine-item {
               leaf re-name {
                 type string;
               }
               choice output-tags {
                 case actual-tag {
                   container fm-topology {
                     uses fm-topology-block;
                   }
                 }
               }
             }
           }
         }
       }
     }
   }
   rpc get-fm-plane-state-information {
     description "Show state of fabric management plane";
     input {
       uses command-forwarding;
       leaf display {
         type enumeration {
           enum "terse" {
             description "Show terse output";
           }
           enum "detail" {
             description "Show detail output";
           }
           enum "extensive" {
             description "Show extensive output";
           }
         }
       }
       leaf number {
         description "Fabric plane number";
         type union {
           type string {
             pattern "<.*>|$.*";
           }
           type uint32 {
             range "0 .. 4";
           }
         }
       }
     }
     output {
       choice output-tags {
         case actual-tag {
           container fm-plane-state-information {
             uses fm-plane-state-information-block;
           }
         }
         case multichassis-tag {
           container multi-routing-engine-results {
             list multi-routing-engine-item {
               leaf re-name {
                 type string;
               }
               choice output-tags {
                 case actual-tag {
                   container fm-plane-state-information {
                     uses fm-plane-state-information-block;
                   }
                 }
               }
             }
           }
         }
       }
     }
   }
   rpc get-fm-state-information {
     description "Show summary fabric management state";
     input {
       uses command-forwarding;
     }
     output {
       choice output-tags {
         case actual-tag {
           container fm-state-information {
             uses fm-state-information-block;
           }
         }
         case multichassis-tag {
           container multi-routing-engine-results {
             list multi-routing-engine-item {
               leaf re-name {
                 type string;
               }
               choice output-tags {
                 case actual-tag {
                   container fm-state-information {
                     uses fm-state-information-block;
                   }
                 }
               }
             }
           }
         }
       }
     }
   }
   rpc get-chassis-inventory {
     description "Show installed hardware components";
     input {
       uses command-forwarding;
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       choice output-tags {
         case actual-tag {
           container chassis-inventory {
             uses chassis-inventory-block;
           }
         }
         case multichassis-tag {
           container multi-routing-engine-results {
             list multi-routing-engine-item {
               leaf re-name {
                 type string;
               }
               choice output-tags {
                 case actual-tag {
                   container chassis-inventory {
                     uses chassis-inventory-block;
                   }
                 }
               }
             }
           }
         }
       }
     }
   }
   rpc get-power-budget-information {
     description "Show power budget chassis information";
     input {
       uses command-forwarding;
     }
     output {
       choice output-tags {
         case actual-tag {
           container power-budget-information {
             uses power-budget-information-block;
           }
         }
         case multichassis-tag {
           container multi-routing-engine-results {
             list multi-routing-engine-item {
               leaf re-name {
                 type string;
               }
               choice output-tags {
                 case actual-tag {
                   container power-budget-information {
                     uses power-budget-information-block;
                   }
                 }
               }
             }
           }
         }
       }
     }
   }
   rpc get-chassis-ae-lb-information {
     description "Show multicast load balancing settings";
     output {
       choice output-tags {
         case actual-tag {
           container chassis-ae-lb-information {
             uses chassis-ae-lb-information-block;
           }
         }
         case multichassis-tag {
           container multi-routing-engine-results {
             list multi-routing-engine-item {
               leaf re-name {
                 type string;
               }
               choice output-tags {
                 case actual-tag {
                   container chassis-ae-lb-information {
                     uses chassis-ae-lb-information-block;
                   }
                 }
               }
             }
           }
         }
       }
     }
   }
   rpc get-rps-chassis-information {
     description "Show redundant power system chassis information";
     output {
       choice output-tags {
         case actual-tag {
           container rps-chassis-information {
             uses rps-chassis-information-block;
           }
         }
         case multichassis-tag {
           container multi-routing-engine-results {
             list multi-routing-engine-item {
               leaf re-name {
                 type string;
               }
               choice output-tags {
                 case actual-tag {
                   container rps-chassis-information {
                     uses rps-chassis-information-block;
                   }
                 }
               }
             }
           }
         }
       }
     }
   }
   rpc get-chassis-mac-addresses {
     description "Show media access control addresses";
     input {
       uses command-forwarding;
     }
     output {
       choice output-tags {
         case actual-tag {
           container chassis-mac-addresses {
             uses chassis-mac-addresses-block;
           }
         }
         case multichassis-tag {
           container multi-routing-engine-results {
             list multi-routing-engine-item {
               leaf re-name {
                 type string;
               }
               choice output-tags {
                 case actual-tag {
                   container chassis-mac-addresses {
                     uses chassis-mac-addresses-block;
                   }
                 }
               }
             }
           }
         }
       }
     }
   }
   rpc get-route-engine-information {
     description "Show Routing Engine status";
     input {
       uses command-forwarding;
       leaf slot {
         description "Routing Engine slot number";
         type union {
           type string {
             pattern "<.*>|$.*";
           }
           type uint32;
         }
       }
     }
     output {
       choice output-tags {
         case actual-tag {
           container route-engine-information {
             uses route-engine-information-block;
           }
         }
         case multichassis-tag {
           container multi-routing-engine-results {
             list multi-routing-engine-item {
               leaf re-name {
                 type string;
               }
               choice output-tags {
                 case actual-tag {
                   container route-engine-information {
                     uses route-engine-information-block;
                   }
                 }
               }
             }
           }
         }
       }
     }
   }
   rpc get-bios-version-information {
     description "Show BIOS firmware version";
     input {
       uses command-forwarding;
     }
     output {
       choice output-tags {
         case actual-tag {
           container route-engine-information {
             uses route-engine-information-block;
           }
         }
         case multichassis-tag {
           container multi-routing-engine-results {
             list multi-routing-engine-item {
               leaf re-name {
                 type string;
               }
               choice output-tags {
                 case actual-tag {
                   container route-engine-information {
                     uses route-engine-information-block;
                   }
                 }
               }
             }
           }
         }
       }
     }
   }
   rpc get-chassis-hard-disk-test {
     description "Show smartd self tests status on hard disks";
     input {
       leaf status {
         description "Display status of test";
         type empty;
         mandatory true;
       }
       leaf disk {
         description "Name of hard disk";
         type string;
         mandatory true;
       }
     }
     output {
       choice output-tags {
         case actual-tag {
           container raid-information {
             uses raid-information-block;
           }
         }
         case multichassis-tag {
           container multi-routing-engine-results {
             list multi-routing-engine-item {
               leaf re-name {
                 type string;
               }
               choice output-tags {
                 case actual-tag {
                   container raid-information {
                     uses raid-information-block;
                   }
                 }
               }
             }
           }
         }
       }
     }
   }
   rpc get-chassis-routing-engine-errors {
     description "Show RE errors";
     input {
       uses command-forwarding;
     }
     output {
       choice output-tags {
         case actual-tag {
           container route-engine-resiliency-information {
             uses route-engine-resiliency-information-block;
           }
         }
         case multichassis-tag {
           container multi-routing-engine-results {
             list multi-routing-engine-item {
               leaf re-name {
                 type string;
               }
               choice output-tags {
                 case actual-tag {
                   container route-engine-resiliency-information {
                     uses route-engine-resiliency-information-block;
                   }
                 }
               }
             }
           }
         }
       }
     }
   }
   rpc get-fan-information {
     description "Show fan and fan tray information";
     input {
       uses command-forwarding;
     }
     output {
       choice output-tags {
         case actual-tag {
           container fan-information {
             uses fan-information-block;
           }
         }
         case multichassis-tag {
           container multi-routing-engine-results {
             list multi-routing-engine-item {
               leaf re-name {
                 type string;
               }
               choice output-tags {
                 case actual-tag {
                   container fan-information {
                     uses fan-information-block;
                   }
                 }
               }
             }
           }
         }
       }
     }
   }
   rpc get-fan-speed-change-history {
     description "Show fan speed change history";
     output {
       choice output-tags {
         case actual-tag {
           container fan-information {
             uses fan-information-block;
           }
         }
         case multichassis-tag {
           container multi-routing-engine-results {
             list multi-routing-engine-item {
               leaf re-name {
                 type string;
               }
               choice output-tags {
                 case actual-tag {
                   container fan-information {
                     uses fan-information-block;
                   }
                 }
               }
             }
           }
         }
       }
     }
   }
   rpc get-chassis-location {
     description "Show physical location of chassis";
     input {
       uses command-forwarding;
     }
     output {
       choice output-tags {
         case actual-tag {
           container chassis-location {
             uses chassis-location-block;
           }
         }
         case multichassis-tag {
           container multi-routing-engine-results {
             list multi-routing-engine-item {
               leaf re-name {
                 type string;
               }
               choice output-tags {
                 case actual-tag {
                   container chassis-location {
                     uses chassis-location-block;
                   }
                 }
               }
             }
           }
         }
       }
     }
   }
   rpc get-temperature-threshold-information {
     description "Show chassis temperature threshold settings";
     input {
       uses command-forwarding;
     }
     output {
       choice output-tags {
         case actual-tag {
           container temperature-threshold-information {
             uses temperature-threshold-information-block;
           }
         }
         case multichassis-tag {
           container multi-routing-engine-results {
             list multi-routing-engine-item {
               leaf re-name {
                 type string;
               }
               choice output-tags {
                 case actual-tag {
                   container temperature-threshold-information {
                     uses temperature-threshold-information-block;
                   }
                 }
               }
             }
           }
         }
       }
     }
   }
   rpc get-enh-temperature-threshold-information {
     description "Show chassis temperature threshold settings";
     output {
       choice output-tags {
         case actual-tag {
           container enh-temperature-threshold-information {
             uses enh-temperature-threshold-information-block;
           }
         }
         case multichassis-tag {
           container multi-routing-engine-results {
             list multi-routing-engine-item {
               leaf re-name {
                 type string;
               }
               choice output-tags {
                 case actual-tag {
                   container enh-temperature-threshold-information {
                     uses enh-temperature-threshold-information-block;
                   }
                 }
               }
             }
           }
         }
       }
     }
   }
   rpc get-nonstop-upgrade-status {
     description "Show nonstop upgrade status";
     input {
       uses command-forwarding;
     }
     output {
       choice output-tags {
         case actual-tag {
           container in-service-upgrade-status {
             uses in-service-upgrade-status-block;
           }
         }
         case multichassis-tag {
           container multi-routing-engine-results {
             list multi-routing-engine-item {
               leaf re-name {
                 type string;
               }
               choice output-tags {
                 case actual-tag {
                   container in-service-upgrade-status {
                     uses in-service-upgrade-status-block;
                   }
                 }
               }
             }
           }
         }
       }
     }
   }
   rpc get-chassis-oss-map {
     description "Show Operation Supported System's translated model";
     output {
       choice output-tags {
         case actual-tag {
           container chassis-oss-map {
             uses chassis-oss-map-block;
           }
         }
         case multichassis-tag {
           container multi-routing-engine-results {
             list multi-routing-engine-item {
               leaf re-name {
                 type string;
               }
               choice output-tags {
                 case actual-tag {
                   container chassis-oss-map {
                     uses chassis-oss-map-block;
                   }
                 }
               }
             }
           }
         }
       }
     }
   }
   rpc get-lcd-information {
     description "Show LCD display";
     input {
       uses command-forwarding;
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-lcd-fpc-information {
     description "Show LCD display for FPC slot number";
     input {
       uses command-forwarding;
       leaf fpc-slot {
         description "FPC slot number";
         type union {
           type string {
             pattern "<.*>|$.*";
           }
           type uint32;
         }
       }
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-lcd-menu-information {
     description "Show active LCD menu items";
     input {
       uses command-forwarding;
     }
     output {
       choice output-tags {
         case output-tag {
           leaf output {
             type string;
           }
         }
         case actual-tag {
           anyxml lcd-information;
         }
         case multichassis-tag {
           anyxml multi-routing-engine-results;
         }
       }
     }
   }
   rpc get-led-information {
     description "Show LED status";
     input {
       uses command-forwarding;
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-led-fpc-information {
     description "Show LED status for FPC slot number";
     input {
       uses command-forwarding;
       leaf fpc-slot {
         description "FPC slot number";
         type union {
           type string {
             pattern "<.*>|$.*";
           }
           type uint32;
         }
       }
     }
     output {
       choice output-tags {
         case actual-tag {
           container craft-lcd-led-information {
             uses craft-lcd-led-information-block;
           }
         }
         case multichassis-tag {
           container multi-routing-engine-results {
             list multi-routing-engine-item {
               leaf re-name {
                 type string;
               }
               choice output-tags {
                 case actual-tag {
                   container craft-lcd-led-information {
                     uses craft-lcd-led-information-block;
                   }
                 }
               }
             }
           }
         }
       }
     }
   }
   rpc get-chassis-pic-mode-information {
     description "Show a member's chassis pic-mode";
     input {
       uses command-forwarding;
     }
     output {
       choice output-tags {
         case actual-tag {
           container chassis-pic-mode-information {
             uses chassis-pic-mode-information-block;
           }
         }
         case multichassis-tag {
           container multi-routing-engine-results {
             list multi-routing-engine-item {
               leaf re-name {
                 type string;
               }
               choice output-tags {
                 case actual-tag {
                   container chassis-pic-mode-information {
                     uses chassis-pic-mode-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping alarm-information-block {
     container alarm-summary {
       description
         "Number of alarms currently active";
       leaf active-alarm-count {
         type int32;
         description
           "Number of active alarms";
       }
       leaf no-active-alarms {
         type empty;
         description
           "No active alarms";
       }
       leaf active-fpc-slot {
         type int32;
         description
           "FPC slot with active alarms";
       }
       leaf no-active-fpc-slot {
         type int32;
         description
           "FPC slot with non active alarms";
       }
     }
     list alarm-detail {
       description
         "Detailed information about an active alarm";
       leaf alarm-time {
         type string;
         description
           "Time of the alarm";
       }
       leaf alarm-class {
         type string;
         description
           "Class of the alarm";
       }
       leaf alarm-description {
         type string;
         description
           "Description of the alarm";
       }
       leaf alarm-short-description {
         type string;
         description
           "Short description of the alarm";
       }
       leaf alarm-type {
         type string;
         description
           "Type (class) of the alarm";
       }
     }
   }
   grouping satellite-device-list-block {
     list satellite-device {
       key "slot";
       leaf slot {
         type int32;
       }
       leaf description {
         type string;
         description
           "Description of this component";
       }
       leaf ip-address {
         type jt:ipaddr;
       }
       leaf target-mode {
         type string;
       }
       leaf mac-address-base {
         type jt:mac-addr;
       }
       leaf mac-address-count {
         type int32;
       }
       leaf-list cascade-port {
         type string;
       }
     }
   }
   grouping craft-information-block {
     leaf-list output {
       type string;
       description
         "Formatted ASCII output displayed by the CLI";
     }
     container front-panel {
       description
         "Information from the craft interface";
       container display-panel {
         description
           "Text currently appearing on the craft interface display";
         leaf-list display-line {
           type string;
           description
             "Single line of text currently appearing on the craft interface
             display";
         }
       }
       container re-panel {
         description
           "State of status LEDs on the craft interface for one or more 
           Routing Engines. The front panel of each Routing Engine has the 
           same LEDs.";
         list re {
           key "slot";
           description
             "State of status LEDs on the craft interface for a Routing 
             Engine. The front panel of the Routing Engine has the same 
             LEDs.";
           leaf slot {
             type int32;
           }
           leaf ok-led {
             type empty;
             description
               "OK LED is lit";
           }
           leaf fail-led {
             type empty;
             description
               "Fail LED is lit";
           }
           leaf master-led {
             type empty;
             description
               "Master LED is lit";
           }
         }
       }
       container alarm-indicators {
         description
           "Information about alarms from the craft interface";
         leaf red-led {
           type empty;
           description
             "Red LED is lit";
         }
         leaf yellow-led {
           type empty;
           description
             "Yellow LED is lit";
         }
         leaf major-alarm-relay {
           type empty;
           description
             "Major (red) alarm relay is active";
         }
         leaf minor-alarm-relay {
           type empty;
           description
             "Minor (yellow) alarm relay is active";
         }
       }
       container fpc-panel {
         description
           "State of status LEDs on the craft interface for Flexible PIC 
           Concentrators";
         list fpccraft {
           key "slot";
           description
             "State of status LEDs on the craft interface for Flexible 
             PICConcentrators.";
           leaf slot {
             type int32;
           }
           leaf red-led {
             type empty;
             description
               "Red LED is lit";
           }
           leaf green-led {
             type empty;
             description
               "Green LED is lit";
           }
         }
       }
       container sib-panel {
         description
           "State of the status LEDs on the faceplate of one or more Switch 
           Interface Boards. Some of the LEDs also appear on the craft 
           interface.";
         container sib {
           leaf ok-led {
             type empty;
             description
               "OK LED is lit";
           }
           leaf fail-led {
             type empty;
             description
               "Fail LED is lit";
           }
           leaf active-led {
             type empty;
             description
               "Active LED is lit";
           }
         }
       }
       container ccg-panel {
         description
           "State of the status LEDs on the faceplate of one or more SONET 
           ClockGenerators";
         container ccg {
           description
             "State of the CCG status LEDs on the craft interface";
           leaf slot {
             type int32;
           }
           leaf ok-led {
             type empty;
             description
               "OK LED is lit";
           }
           leaf fail-led {
             type empty;
             description
               "Fail LED is lit";
           }
           leaf master-led {
             type empty;
             description
               "Master LED is lit";
           }
         }
       }
       container cb-panel {
         description
           "State of status LEDs on one or more Control Boards";
         list cb {
           key "slot";
           description
             "State of status LEDs on a Control Board";
           leaf slot {
             type int32;
           }
           leaf amber-led {
             type empty;
             description
               "Amber LED is lit";
           }
           leaf green-led {
             type empty;
             description
               "Green LED is lit";
           }
           leaf blue-led {
             type empty;
             description
               "Blue LED is lit";
           }
         }
       }
       container fan-tray-panel {
         description
           "State of status LEDs on the craft interface for Fan Trays";
         container fan-tray {
           description
             "State of the status LEDs on the craft interface for a fan tray";
           leaf slot {
             type int32;
           }
           leaf red-led {
             type empty;
             description
               "Red LED is lit";
           }
           leaf green-led {
             type empty;
             description
               "Green LED is lit";
           }
         }
       }
       container power-supply-panel {
         description
           "State of the status LEDs on the faceplate of one or more power 
           supplies";
         list power-supply {
           description
             "State of the status LEDs on the faceplate of a power supply";
           leaf slot {
             type int32;
           }
           leaf amber-led {
             type empty;
             description
               "Amber LED is lit";
           }
           leaf green-led {
             type empty;
             description
               "Green LED is lit";
           }
           leaf blue-led {
             type empty;
             description
               "Blue LED is lit";
           }
         }
         container pdu {
           description
             "State of the PDU status LEDs on the craft interface";
           leaf slot {
             type int32;
           }
           leaf red-led {
             type empty;
             description
               "Red LED is lit";
           }
           leaf green-led {
             type empty;
             description
               "Green LED is lit";
           }
           container psm {
             description
               "State of the PSM status LEDs on the craft interface";
             leaf slot {
               type int32;
             }
             leaf red-led {
               type empty;
               description
                 "Red LED is lit";
             }
             leaf green-led {
               type empty;
               description
                 "Green LED is lit";
             }
           }
         }
       }
     }
     container recb-panel {
       description
         "Information about LEDs from the craft interface";
       container ha-led {
         description
           "State of the HA LED on the craft interface";
         leaf red-led {
           type empty;
           description
             "Red LED is lit";
         }
         leaf yellow-led {
           type empty;
           description
             "Yellow LED is lit";
         }
         leaf amber-led {
           type empty;
           description
             "Amber LED is lit";
         }
       }
       container rps-led {
         description
           "State of the RPS LED on the craft interface";
         leaf red-led {
           type empty;
           description
             "Red LED is lit";
         }
         leaf green-led {
           type empty;
           description
             "Green LED is lit";
         }
         leaf led-off {
           type empty;
           description
             "LED is off";
         }
       }
       container mpim1-led {
         description
           "State of the MPIM1 LED on the craft interface";
         leaf green-led {
           type empty;
           description
             "Green LED is lit";
         }
         leaf led-off {
           type empty;
           description
             "LED is off";
         }
       }
       container mpim2-led {
         description
           "State of the MPIM2 LED on the craft interface";
         leaf green-led {
           type empty;
           description
             "Green LED is lit";
         }
         leaf led-off {
           type empty;
           description
             "LED is off";
         }
       }
       container storage-led {
         description
           "State of the external storage LED on the craft interface";
         leaf green-led {
           type empty;
           description
             "Green LED is lit";
         }
         leaf led-off {
           type empty;
           description
             "LED is off";
         }
       }
       container sfb-led {
         description
           "State of the SFB LED on the craft interface";
         leaf red-led {
           type empty;
           description
             "Red LED is lit";
         }
         leaf yellow-led {
           type empty;
           description
             "Yellow LED is lit";
         }
         leaf amber-led {
           type empty;
           description
             "Amber LED is lit";
         }
         leaf blink-led {
           type empty;
           description
             "LED is blinking";
         }
       }
       container cfm-ok-fail-led {
         description
           "State of the CFM Ok/Fail LED on the craft interface";
         leaf red-led {
           type empty;
           description
             "Red LED is lit";
         }
         leaf yellow-led {
           type empty;
           description
             "Yellow LED is lit";
         }
         leaf amber-led {
           type empty;
           description
             "Amber LED is lit";
         }
       }
       container cfm-service-led {
         description
           "State of the CFM Service LED on the craft interface";
         leaf red-led {
           type empty;
           description
             "Red LED is lit";
         }
         leaf yellow-led {
           type empty;
           description
             "Yellow LED is lit";
         }
         leaf amber-led {
           type empty;
           description
             "Amber LED is lit";
         }
       }
       container sysio-status-led {
         description
           "State of the SYSIO Status LED on the craft interface";
         leaf red-led {
           type empty;
           description
             "Red LED is lit";
         }
         leaf yellow-led {
           type empty;
           description
             "Yellow LED is lit";
         }
         leaf amber-led {
           type empty;
           description
             "Amber LED is lit";
         }
         leaf blink-led {
           type empty;
           description
             "LED is blinking";
         }
       }
     }
     container mcs-panel {
       description
         "State of the status LEDs on the faceplate of one or more 
         Miscellaneous Control Subsystems";
       container mcs {
         description
           "State of the status LEDs on the faceplate of a Miscellaneous 
           Control Subsystem";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container sfm-panel {
       description
         "State of the status LEDs on the faceplate of one or more Switching
         and Forwarding Modules";
       container sfm {
         description
           "State of the status LEDs on the faceplate of a Switching 
           andForwarding Module";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container pcg-panel {
       description
         "State of the status LEDs on the faceplate of one or more Packet 
         Forwarding Engine Clock Generators";
       container pcg {
         description
           "State of the status LEDs on the faceplate of a Packet Forwarding
           Engine Clock Generator";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container cb-panel {
       description
         "State of status LEDs on one or more Control Boards";
       list cb {
         key "slot";
         description
           "State of status LEDs on a Control Board";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container sib-panel {
       description
         "State of the status LEDs on the faceplate of one or more Switch 
         Interface Boards. Some of the LEDs also appear on the craft 
         interface.";
       container sib {
         leaf ok-led {
           type empty;
           description
             "OK LED is lit";
         }
         leaf fail-led {
           type empty;
           description
             "Fail LED is lit";
         }
         leaf active-led {
           type empty;
           description
             "Active LED is lit";
         }
       }
     }
     container scg-panel {
       description
         "State of the status LEDs on the faceplate of one or more SONET 
         ClockGenerators";
       container scg {
         description
           "State of the status LEDs on the faceplate of a SONET Clock 
           Generator";
         leaf slot {
           type int32;
         }
         leaf amber-led {
           type empty;
           description
             "Amber LED is lit";
         }
         leaf green-led {
           type empty;
           description
             "Green LED is lit";
         }
         leaf blue-led {
           type empty;
           description
             "Blue LED is lit";
         }
       }
     }
     container feb-panel {
       description
         "State of the status LEDs on the faceplate of one or more 
         Forwarding Engine Boards";
       container feb {
         description
           "State of the status LEDs on the faceplate of a Forwarding Engine
           Board";
         leaf slot {
           type int32;
         }
         leaf ok-led {
           type empty;
           description
             "OK LED is lit";
         }
         leaf fail-led {
           type empty;
           description
             "Fail LED is lit";
         }
         leaf active-led {
           type empty;
           description
             "Active LED is lit";
         }
       }
     }
     container power-supply-panel {
       description
         "State of the status LEDs on the faceplate of one or more power 
         supplies";
       list power-supply {
         description
           "State of the status LEDs on the faceplate of a power supply";
         leaf slot {
           type int32;
         }
         leaf amber-led {
           type empty;
           description
             "Amber LED is lit";
         }
         leaf green-led {
           type empty;
           description
             "Green LED is lit";
         }
         leaf blue-led {
           type empty;
           description
             "Blue LED is lit";
         }
       }
       container pdu {
         description
           "State of the PDU status LEDs on the craft interface";
         leaf slot {
           type int32;
         }
         leaf red-led {
           type empty;
           description
             "Red LED is lit";
         }
         leaf green-led {
           type empty;
           description
             "Green LED is lit";
         }
         container psm {
           description
             "State of the PSM status LEDs on the craft interface";
           leaf slot {
             type int32;
           }
           leaf red-led {
             type empty;
             description
               "Red LED is lit";
           }
           leaf green-led {
             type empty;
             description
               "Green LED is lit";
           }
         }
       }
     }
     container fan-tray-panel {
       description
         "State of status LEDs on the craft interface for Fan Trays";
       container fan-tray {
         description
           "State of the status LEDs on the craft interface for a fan tray";
         leaf slot {
           type int32;
         }
         leaf red-led {
           type empty;
           description
             "Red LED is lit";
         }
         leaf green-led {
           type empty;
           description
             "Green LED is lit";
         }
       }
     }
   }
   grouping ethernet-switch-information-block {
     leaf summary {
       type string;
     }
     list link-info {
       leaf admin-status {
         type string;
       }
       leaf interface-name {
         type string;
       }
       leaf port-number {
         type int32;
         description
           "Port number on the PIC";
       }
       leaf connected-to {
         type string;
       }
       leaf speed {
         type string;
       }
       leaf duplex {
         type string;
       }
       leaf autonegotiate {
         type string;
       }
       leaf flow-control-tx {
         type string;
       }
       leaf flow-control-rx {
         type string;
       }
       leaf-list error-message {
         type string;
       }
     }
   }
   grouping ethernet-switch-statistics-information-block {
     leaf summary {
       type string;
     }
     list link-up-info {
       leaf ge-summary {
         type string;
       }
       leaf gt-64 {
         type uint64;
       }
       leaf gt-127 {
         type uint64;
       }
       leaf gt-255 {
         type uint64;
       }
       leaf gt-511 {
         type uint64;
       }
       leaf gt-1023 {
         type uint64;
       }
       leaf gt-1518 {
         type uint64;
       }
       leaf gt-2047 {
         type uint64;
       }
       leaf gt-4095 {
         type uint64;
       }
       leaf gt-9216 {
         type uint64;
       }
       leaf gt-mgv {
         type uint64;
       }
       leaf gt-pkt {
         type uint64;
       }
       leaf gt-mca {
         type uint64;
       }
       leaf gt-bca {
         type uint64;
       }
       leaf gt-scl {
         type uint64;
       }
       leaf gt-mcl {
         type uint64;
       }
       leaf gt-lcl {
         type uint64;
       }
       leaf gt-xcl {
         type uint64;
       }
       leaf gt-ncl {
         type uint64;
       }
       leaf gt-xpf {
         type uint64;
       }
       leaf gt-xcf {
         type uint64;
       }
       leaf gt-dfr {
         type uint64;
       }
       leaf gt-edf {
         type uint64;
       }
       leaf gt-ovr {
         type uint64;
       }
       leaf gt-jbr {
         type uint64;
       }
       leaf gt-fcs {
         type uint64;
       }
       leaf gt-frg {
         type uint64;
       }
       leaf gt-byt {
         type uint64;
       }
       leaf gr-64 {
         type uint64;
       }
       leaf gr-127 {
         type uint64;
       }
       leaf gr-255 {
         type uint64;
       }
       leaf gr-511 {
         type uint64;
       }
       leaf gr-1023 {
         type uint64;
       }
       leaf gr-1518 {
         type uint64;
       }
       leaf gr-2047 {
         type uint64;
       }
       leaf gr-4095 {
         type uint64;
       }
       leaf gr-9216 {
         type uint64;
       }
       leaf gr-pkt {
         type uint64;
       }
       leaf gr-mca {
         type uint64;
       }
       leaf gr-bca {
         type uint64;
       }
       leaf gr-fcs {
         type uint64;
       }
       leaf gr-aln {
         type uint64;
       }
       leaf gr-frg {
         type uint64;
       }
       leaf gr-cde {
         type uint64;
       }
       leaf gr-xuo {
         type uint64;
       }
       leaf gr-flr {
         type uint64;
       }
       leaf gr-fcr {
         type uint64;
       }
       leaf gr-und {
         type uint64;
       }
       leaf gr-ovr {
         type uint64;
       }
       leaf gr-jbr {
         type uint64;
       }
       leaf gr-mgv {
         type uint64;
       }
       leaf gr-mtue {
         type uint64;
       }
       leaf gr-xcf {
         type uint64;
       }
       leaf gr-xpf {
         type uint64;
       }
       leaf gr-byt {
         type uint64;
       }
       leaf xe-summary {
         type string;
       }
       leaf it-64 {
         type uint64;
       }
       leaf it-127 {
         type uint64;
       }
       leaf it-255 {
         type uint64;
       }
       leaf it-511 {
         type uint64;
       }
       leaf it-1023 {
         type uint64;
       }
       leaf it-1518 {
         type uint64;
       }
       leaf it-2047 {
         type uint64;
       }
       leaf it-4095 {
         type uint64;
       }
       leaf it-9216 {
         type uint64;
       }
       leaf it-16383 {
         type uint64;
       }
       leaf it-pkt {
         type uint64;
       }
       leaf it-mca {
         type uint64;
       }
       leaf it-bca {
         type uint64;
       }
       leaf it-xpf {
         type uint64;
       }
       leaf it-ovr {
         type uint64;
       }
       leaf it-fcs {
         type uint64;
       }
       leaf it-frg {
         type uint64;
       }
       leaf it-byt {
         type uint64;
       }
       leaf ir-64 {
         type uint64;
       }
       leaf ir-127 {
         type uint64;
       }
       leaf ir-255 {
         type uint64;
       }
       leaf ir-511 {
         type uint64;
       }
       leaf ir-1023 {
         type uint64;
       }
       leaf ir-1518 {
         type uint64;
       }
       leaf ir-2047 {
         type uint64;
       }
       leaf ir-4095 {
         type uint64;
       }
       leaf ir-9216 {
         type uint64;
       }
       leaf ir-16383 {
         type uint64;
       }
       leaf ir-pkt {
         type uint64;
       }
       leaf ir-mca {
         type uint64;
       }
       leaf ir-bca {
         type uint64;
       }
       leaf ir-fcs {
         type uint64;
       }
       leaf ir-frg {
         type uint64;
       }
       leaf ir-xuo {
         type uint64;
       }
       leaf ir-flr {
         type uint64;
       }
       leaf ir-und {
         type uint64;
       }
       leaf ir-ovr {
         type uint64;
       }
       leaf ir-jbr {
         type uint64;
       }
       leaf ir-xcf {
         type uint64;
       }
       leaf ir-xpf {
         type uint64;
       }
       leaf ir-byt {
         type uint64;
       }
       leaf-list error-message {
         type string;
       }
     }
   }
   grouping environment-information-block {
     list environment-item {
       key "name";
       leaf class {
         type string;
       }
       leaf name {
         type string;
         description
           "Name of this component";
       }
       leaf status {
         type string;
         description
           "Status of clock synchronization source";
       }
       leaf temperature {
         type string;
         description
           "Temperature of the item";
       }
       leaf comment {
         type string;
       }
       leaf humidity {
         type string;
       }
     }
   }
   grouping environment-component-information-block {
     list environment-component-item {
       key "name";
       description
         "Chassis environment component";
       leaf name {
         type string;
         description
           "Name of this component";
       }
       leaf state {
         type string;
         description
           "Status of the component";
       }
       leaf bus-revision {
         type int32;
         description
           "Bus revision";
       }
       leaf cmb-revision {
         type int32;
         description
           "CMB revision";
       }
       leaf fpga-revision {
         type int32;
         description
           "FPGA revision";
       }
       leaf ac-feed0-voltage {
         type string;
         description
           "AC feed0 voltage";
       }
       leaf ac-feed0-current {
         type string;
         description
           "AC feed0 current";
       }
       leaf ac-feed0-power {
         type string;
         description
           "AC feed0 power";
       }
       leaf ac-feed1-voltage {
         type string;
         description
           "AC feed1 voltage";
       }
       leaf ac-feed1-current {
         type string;
         description
           "AC feed1 current";
       }
       leaf ac-feed1-power {
         type string;
         description
           "AC feed1 power";
       }
       leaf reason {
         type string;
         description
           "Reason";
       }
       leaf frequency {
         type string;
         description
           "Frequency";
       }
       leaf slave-revision {
         type uint32;
         description
           "Slave revision";
       }
       leaf load {
         type string;
         description
           "Load";
       }
       leaf time-used {
         type string;
         description
           "Length of time this component has been used";
       }
       leaf check-input1-alarm {
         type string;
         description
           "Check input1 alarm";
       }
       leaf check-input2-alarm {
         type string;
         description
           "Check input2 alarm";
       }
       leaf ac-input_status {
         type string;
         description
           "AC input status";
       }
       container temperature-reading {
         leaf temperature-name {
           type string;
         }
         leaf temperature {
           type string;
           description
             "Temperature of the item";
         }
       }
       container fan-speed-reading {
         leaf fan-name {
           type string;
         }
         leaf fan-speed {
           type string;
           description
             "Fan speed in RPM";
         }
       }
       container fpga-revision-detail {
         description
           "FPGA revision in detail";
         leaf fpga-revision-name {
           type string;
         }
         leaf fpga-revision-value {
           type string;
         }
       }
       container revision {
         leaf revision-name {
           type string;
           description
             "Revision Name";
         }
         leaf revision-number {
           type uint32;
           description
             "Revision Number";
         }
       }
       container slave-registers-information {
         leaf slave-registers-title {
           type string;
           description
             "Title for the dump of slave registers";
         }
         container slave-registers {
           description
             "Slave register values";
           leaf slave-registers-name {
             type string;
           }
           leaf slave-registers-value {
             type string;
           }
           leaf slave-registers-desc {
             type string;
           }
         }
       }
       container fpga-registers {
         description
           "FPGA register values";
         leaf fpga-registers-type {
           type string;
         }
         leaf fpga-registers-name {
           type string;
         }
         leaf fpga-registers-value {
           type string;
         }
       }
       container power-information {
         leaf voltage-title {
           type string;
           description
             "Title for the display of voltage";
         }
         leaf max-power-consumption-ambient-temp {
           type int32;
         }
         leaf psm-hours-used {
           type uint32;
           description
             "Hours used for this component";
         }
         container power-title {
           leaf power-type {
             type string;
             description
               "Title for the display of power";
           }
           leaf power-state {
             type string;
             description
               "State of power";
           }
         }
         container voltage {
           leaf reference-voltage {
             type string;
             description
               "Voltage of the item in Volts";
           }
           leaf actual-voltage {
             type int32;
             description
               "Voltage of the item in mVlots";
           }
         }
         container current {
           leaf reference-curr {
             type string;
             description
               "Current of the item in Amps";
           }
           leaf actual-curr {
             type int32;
             description
               "Current of the item in mAmps";
           }
         }
         container voltage-current {
           leaf reference-volt-string {
             type string;
             description
               "Voltage of the item in Volts";
           }
           leaf actual-volt-in {
             type int32;
             description
               "Voltage in of the item in mVolts";
           }
           leaf actual-current-in {
             type int32;
             description
               "Current of the item in mAmps";
           }
         }
         container voltage-power {
           leaf reference-volt {
             type string;
             description
               "Voltage of the item in Volts";
           }
           leaf actual-volt {
             type int32;
             description
               "Voltage of the item in mVlots";
           }
           leaf actual-current {
             type int32;
             description
               "Current of the item in mAmps";
           }
           leaf actual-power {
             type int32;
             description
               "Power of the item in mWatts";
           }
         }
         list voltage-power-temperature-only {
           leaf voltage-string {
             type string;
             description
               "Name of the component";
           }
           leaf actual-temperature {
             type int32;
             description
               "Temperature of the item in degree (C)";
           }
         }
         container voltage-power-volt-only {
           leaf reference-volt-only {
             type string;
             description
               "Voltage of the item in Volts";
           }
           leaf actual-volt-only {
             type int32;
             description
               "Voltage of the item in mVlots";
           }
         }
       }
       container pcg-frequency {
         description
           "PCG Frequency";
         leaf pcg-frequency-setting {
           type string;
         }
         leaf pcg-frequency-measurement {
           type string;
         }
       }
       container dc-information {
         leaf dc-feed0-voltage {
           type string;
           description
             "DC feed0 voltage";
         }
         leaf dc-feed0-current {
           type string;
           description
             "DC feed0 current";
         }
         leaf dc-feed0-power {
           type string;
           description
             "DC feed0 power";
         }
         leaf dc-feed1-voltage {
           type string;
           description
             "DC feed1 voltage";
         }
         leaf dc-feed1-current {
           type string;
           description
             "DC feed1 current";
         }
         leaf dc-feed1-power {
           type string;
           description
             "DC feed1 power";
         }
         leaf dc-input {
           type string;
           description
             "DC input state";
         }
         leaf dc-output {
           type string;
           description
             "DC output state";
         }
         leaf ac-input {
           type string;
           description
             "AC input state";
         }
         leaf ac-output {
           type string;
           description
             "AC output state";
         }
         leaf dc-input-status {
           type string;
           description
             "DC input status";
         }
         leaf dc-input1 {
           type string;
           description
             "DC input1 state";
         }
         leaf dc-input2 {
           type string;
           description
             "DC input2 state";
         }
         leaf ac-input1 {
           type string;
           description
             "AC input1 state";
         }
         leaf ac-input2 {
           type string;
           description
             "AC input2 state";
         }
         container dc-detail {
           description
             "Detailed DC information";
           leaf dc-device {
             type string;
           }
           leaf dc-voltage {
             type uint32;
           }
           leaf dc-current {
             type uint32;
           }
           leaf dc-power {
             type uint32;
           }
           leaf dc-load {
             type uint32;
           }
           leaf str-dc-voltage {
             type string;
           }
           leaf str-dc-current {
             type string;
           }
           leaf str-dc-power {
             type string;
           }
           leaf str-dc-load {
             type string;
           }
           leaf str2-dc-voltage {
             type string;
           }
           leaf str2-dc-current {
             type string;
           }
           leaf str2-dc-power {
             type string;
           }
           leaf str2-dc-load {
             type string;
           }
           leaf str3-dc-voltage {
             type string;
           }
           leaf str3-dc-current {
             type string;
           }
           leaf max-power {
             type uint32;
           }
         }
         container dc-in-detail2 {
           description
             "Detailed DC input information";
           leaf dc-in-device2 {
             type string;
           }
           leaf dc-in-voltage-string {
             type string;
           }
           leaf dc-in-current-string {
             type string;
           }
           leaf dc-in-power-string {
             type string;
           }
           leaf dc-in-load-string {
             type string;
           }
         }
         container dc-detail2 {
           description
             "Detailed DC information";
           leaf dc-device2 {
             type string;
           }
           leaf dc-voltage-string {
             type string;
           }
           leaf dc-current-string {
             type string;
           }
           leaf dc-power-string {
             type string;
           }
           leaf dc-load-string {
             type string;
           }
         }
         leaf dc-inp0 {
           type string;
           description
             "DC input0 state";
         }
         leaf dc-inp1 {
           type string;
           description
             "DC input1 state";
         }
         leaf dc2-input-a0 {
           type string;
           description
             "DC2 input a0 state";
         }
         leaf dc2-input-b0 {
           type string;
           description
             "DC2 input b0 state";
         }
         leaf dc2-input-a1 {
           type string;
           description
             "DC2 input a1 state";
         }
         leaf dc2-input-b1 {
           type string;
           description
             "DC2 input b1 state";
         }
         leaf ac-inp0 {
           type string;
           description
             "AC input0 state";
         }
         leaf ac-inp1 {
           type string;
           description
             "AC input1 state";
         }
       }
       container pmbus-table {
         container pmbus-table-entry {
           description
             "Power Management Bus Device information";
           leaf pmbus-device-name {
             type string;
           }
           leaf pmbus-expected-voltage {
             type uint32;
           }
           leaf pmbus-actual-voltage {
             type uint32;
           }
           leaf pmbus-actual-current {
             type uint32;
           }
           leaf pmbus-calculated-power {
             type uint32;
           }
         }
       }
       container airflow-direction {
         leaf airflow {
           type string;
         }
         leaf direction {
           type string;
           description
             "Airflow direction";
         }
       }
       container input-voltage {
         leaf voltage-name {
           type string;
           description
             "Input voltage";
         }
         leaf voltage-value {
           type uint32;
         }
       }
       container output-detail {
         description
           "Detailed power output information";
         leaf output-voltage {
           type uint32;
         }
         leaf output-current {
           type uint32;
           description
             "Output Current in Ampere(A)";
         }
       }
       container pdu-information {
         leaf hours-used {
           type uint32;
           description
             "Hours used for this component";
         }
         leaf pdu-status {
           type string;
         }
         container efuse {
           description
             "PDU efuse information";
           leaf name {
             type string;
             description
               "Name of this component";
           }
           leaf state {
             type string;
             description
               "Status of the component";
           }
         }
         container pdu-firmware {
           description
             "PDU firmware information";
           leaf firmware-name {
             type string;
             description
               "Name of this component";
           }
           leaf firmware-version {
             type string;
             description
               "Firmware version string for this component";
           }
         }
         container pdu-component {
           description
             "PDU specific component information";
           leaf component-name {
             type string;
             description
               "PDU component name";
           }
           leaf component-state {
             type string;
             description
               "PDU component state";
           }
         }
       }
       container psm-information {
         leaf temperature {
           type string;
           description
             "Temperature of the item";
         }
         leaf hours-used {
           type uint32;
           description
             "Hours used for this component";
         }
         leaf firmware-version {
           type string;
           description
             "Firmware version string for this component";
         }
         container psm-status {
           leaf fans {
             type string;
             description
               "Fan status for this component";
           }
           leaf dc-input {
             type string;
             description
               "DC input state";
           }
           leaf dc-input1 {
             type string;
             description
               "DC input1 state";
           }
           leaf dc-input2 {
             type string;
             description
               "DC input2 state";
           }
           leaf ac-input {
             type string;
             description
               "AC input state";
           }
           leaf ac-input1 {
             type string;
             description
               "AC input1 state";
           }
           leaf ac-input2 {
             type string;
             description
               "AC input2 state";
           }
           leaf check-input1-alarm {
             type string;
             description
               "Check input1 alarm";
           }
           leaf check-input2-alarm {
             type string;
             description
               "Check input2 alarm";
           }
           leaf dc-output {
             type string;
             description
               "DC output state";
           }
           leaf ac-output {
             type string;
             description
               "AC output state";
           }
           leaf psm-health-check-status {
             type string;
             description
               "Show health check status of all PSMs";
           }
           leaf dc-inp0 {
             type string;
             description
               "DC input0 state";
           }
           leaf dc-inp1 {
             type string;
             description
               "DC input1 state";
           }
           leaf dc2-input-a0 {
             type string;
             description
               "DC2 input a0 state";
           }
           leaf dc2-input-b0 {
             type string;
             description
               "DC2 input b0 state";
           }
           leaf dc2-input-a1 {
             type string;
             description
               "DC2 input a1 state";
           }
           leaf dc2-input-b1 {
             type string;
             description
               "DC2 input b1 state";
           }
           leaf ac-inp0 {
             type string;
             description
               "AC input0 state";
           }
           leaf ac-inp1 {
             type string;
             description
               "AC input1 state";
           }
           leaf check-input-a0-alarm {
             type string;
             description
               "Check input a0 alarm";
           }
           leaf check-input-b0-alarm {
             type string;
             description
               "Check input b0 alarm";
           }
           leaf check-input-a1-alarm {
             type string;
             description
               "Check input a1 alarm";
           }
           leaf check-input-b1-alarm {
             type string;
             description
               "Check input b1 alarm";
           }
           list psm-input-status {
             leaf psm-input-feed-name {
               type string;
             }
             leaf psm-input-feed-status {
               type string;
             }
           }
           list psm-input-alarm {
             leaf input-feed-alarm-name {
               type string;
             }
             leaf input-feed-alarm-status {
               type string;
             }
           }
         }
         leaf fan-status {
           type string;
           description
             "Fan status for this component";
         }
         leaf firmware-primary-mcu {
           type string;
         }
         leaf firmware-secondary-mcu {
           type string;
         }
         leaf firmware-communication-mcu {
           type string;
         }
         leaf firmware-led-mcu {
           type string;
         }
         leaf firmware-version-psm {
           type string;
         }
         leaf hvdc-mode {
           type string;
           description
             "HVDC mode";
         }
         leaf temperature-name {
           type string;
         }
         container fan-speed-reading-psm {
           leaf fan1-speed {
             type string;
           }
           leaf fan2-speed {
             type string;
           }
         }
       }
       container pem-information {
         leaf fpc-slot {
           type int32;
           description
             "FPC slot";
         }
         leaf pem-slot {
           type uint32;
         }
         leaf pem-state {
           type string;
           description
             "State of power supply unit";
         }
         leaf pem-temperature {
           type uint32;
           description
             "Temperature in (C)";
         }
         leaf input-current {
           type uint32;
           description
             "Input Current in Ampere(A)";
         }
         leaf input-volt {
           type uint32;
           description
             "Input Volt in Volt(V)";
         }
         leaf input-power {
           type uint32;
           description
             "Input Power in Watt(W)";
         }
         leaf output-current {
           type uint32;
           description
             "Output Current in Ampere(A)";
         }
         leaf output-volt {
           type uint32;
           description
             "Output Volt in Volt(V)";
         }
         leaf output-power {
           type uint32;
           description
             "Output Power in Watt(W)";
         }
       }
       leaf ac-input-state {
         type string;
         description
           "Input type";
       }
       leaf dc-input-state {
         type string;
         description
           "Input type";
       }
       leaf ac-input {
         type string;
         description
           "Input type";
       }
       leaf check-input-a0-alarm {
         type string;
         description
           "Check input a0 alarm";
       }
       leaf check-input-b0-alarm {
         type string;
         description
           "Check input b0 alarm";
       }
       leaf check-input-a1-alarm {
         type string;
         description
           "Check input a1 alarm";
       }
       leaf check-input-b1-alarm {
         type string;
         description
           "Check input b1 alarm";
       }
       container feed-info {
         leaf feed-name {
           type string;
         }
         leaf feed-state {
           type string;
         }
       }
       container cowra-registers-information {
         leaf cowra-registers-title {
           type string;
           description
             "Title for the dump of cowra registers";
         }
         container cowra-registers {
           description
             "Cowra register values";
           leaf cowra-registers-name {
             type string;
           }
           leaf cowra-registers-value {
             type string;
           }
         }
       }
       list firmware {
         description
           "Firmware version";
         leaf firmware-name {
           type string;
           description
             "Name of this component";
         }
         leaf firmware-version {
           type string;
           description
             "Firmware version string for this component";
         }
         leaf firmware-version-psm {
           type string;
         }
         leaf firmware-primary-mcu {
           type string;
         }
         leaf firmware-secondary-mcu {
           type string;
         }
         leaf firmware-communication-mcu {
           type string;
         }
         leaf firmware-led-mcu {
           type string;
         }
       }
       container input-detail2 {
         leaf input-feed-name {
           type string;
           description
             "Input Feed Name";
         }
         leaf input-feed-volt {
           type string;
           description
             "Input Feed Voltage";
         }
         leaf input-feed-current {
           type string;
           description
             "Input Feed Current";
         }
         leaf input-feed-power {
           type string;
           description
             "Input Feed Power";
         }
       }
       container ac-pem-input-detail {
         leaf ac-pem-input-volt {
           type string;
           description
             "Input Voltage";
         }
         leaf ac-pem-input-current {
           type string;
           description
             "Input Current";
         }
         leaf ac-pem-input-power {
           type string;
           description
             "Input Power";
         }
       }
       container dc-pem-input-detail {
         leaf dc-pem-input-volt {
           type string;
           description
             "Input Voltage";
         }
         leaf dc-pem-input-current {
           type string;
           description
             "Input Current";
         }
         leaf dc-pem-input-power {
           type string;
           description
             "Input Power";
         }
       }
       container psm-health-check-detail {
         leaf health-check-status {
           type string;
         }
         leaf health-check-state-str {
           type string;
           description
             "Current Health Check State";
         }
         leaf health-check-last-result-str {
           type string;
           description
             "Result of Last Execution";
         }
         leaf health-check-last-exec-str {
           type string;
           description
             "Time of Last Health Check Test Execution";
         }
         leaf health-check-next-sched-run-str {
           type string;
           description
             "Time of Next Scheduled Health Check Test";
         }
       }
     }
   }
   grouping firmware-information-block {
     container chassis {
       description
         "Hardware inventory of this chassis";
       leaf name {
         type string;
         description
           "Name of this component";
       }
       leaf version {
         type string;
         description
           "Version of this component";
       }
       leaf part-number {
         type string;
         description
           "Part number of this component";
       }
       leaf serial-number {
         type string;
         description
           "Serial number of this component";
       }
       leaf description {
         type string;
         description
           "Description of this component";
       }
       leaf hardware-incomplete {
         type empty;
       }
       leaf model-number {
         type string;
         description
           "Model number of this component";
       }
       leaf clei-code {
         type string;
         description
           "Common Language Equipment Identifier code of this component";
       }
       container i2c-information {
         leaf jedec-code {
           type string;
         }
         leaf eeprom-version {
           type string;
         }
         leaf part-number {
           type string;
           description
             "Part number of this component";
         }
         leaf serial-number {
           type string;
           description
             "Serial number of this component";
         }
         leaf assembly-identifier {
           type string;
         }
         leaf assembly-version {
           type string;
         }
         leaf manufacture-date {
           type string;
           description
             "Date this component was manufactured";
         }
         leaf assembly-flags {
           type string;
         }
         leaf i2c-version {
           type string;
         }
         leaf clei-code {
           type string;
           description
             "Common Language Equipment Identifier code of this component";
         }
         leaf i2c-identifier {
           type string;
         }
         leaf model-number {
           type string;
           description
             "Model number of this component";
         }
         leaf board-information-record {
           type string;
           description
             "Hex dump of board information record";
         }
         leaf i2c-data {
           type string;
           description
             "Hex dump of I2C data";
         }
       }
       list chassis-module {
         key "name";
         leaf name {
           type string;
           description
             "Name of this component";
         }
         leaf version {
           type string;
           description
             "Version of this component";
         }
         leaf part-number {
           type string;
           description
             "Part number of this component";
         }
         leaf serial-number {
           type string;
           description
             "Serial number of this component";
         }
         leaf description {
           type string;
           description
             "Description of this component";
         }
         leaf ir-mode {
           type string;
           description
             "R/IR mode configured";
         }
         container i2c-information {
           leaf jedec-code {
             type string;
           }
           leaf eeprom-version {
             type string;
           }
           leaf part-number {
             type string;
             description
               "Part number of this component";
           }
           leaf serial-number {
             type string;
             description
               "Serial number of this component";
           }
           leaf assembly-identifier {
             type string;
           }
           leaf assembly-version {
             type string;
           }
           leaf manufacture-date {
             type string;
             description
               "Date this component was manufactured";
           }
           leaf assembly-flags {
             type string;
           }
           leaf i2c-version {
             type string;
           }
           leaf clei-code {
             type string;
             description
               "Common Language Equipment Identifier code of this component";
           }
           leaf i2c-identifier {
             type string;
           }
           leaf model-number {
             type string;
             description
               "Model number of this component";
           }
           leaf board-information-record {
             type string;
             description
               "Hex dump of board information record";
           }
           leaf i2c-data {
             type string;
             description
               "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description
               "Type of this component";
           }
           leaf firmware-version {
             type string;
             description
               "Firmware version string for this component";
           }
         }
         list chassis-sub-module {
           key "name";
           leaf name {
             type string;
             description
               "Name of this component";
           }
           leaf version {
             type string;
             description
               "Version of this component";
           }
           leaf part-number {
             type string;
             description
               "Part number of this component";
           }
           leaf serial-number {
             type string;
             description
               "Serial number of this component";
           }
           leaf description {
             type string;
             description
               "Description of this component";
           }
           container i2c-information {
             leaf jedec-code {
               type string;
             }
             leaf eeprom-version {
               type string;
             }
             leaf part-number {
               type string;
               description
                 "Part number of this component";
             }
             leaf serial-number {
               type string;
               description
                 "Serial number of this component";
             }
             leaf assembly-identifier {
               type string;
             }
             leaf assembly-version {
               type string;
             }
             leaf manufacture-date {
               type string;
               description
                 "Date this component was manufactured";
             }
             leaf assembly-flags {
               type string;
             }
             leaf i2c-version {
               type string;
             }
             leaf clei-code {
               type string;
               description
                 "Common Language Equipment Identifier code of this 
                 component";
             }
             leaf i2c-identifier {
               type string;
             }
             leaf model-number {
               type string;
               description
                 "Model number of this component";
             }
             leaf board-information-record {
               type string;
               description
                 "Hex dump of board information record";
             }
             leaf i2c-data {
               type string;
               description
                 "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             key "name";
             leaf name {
               type string;
               description
                 "Name of this component";
             }
             leaf version {
               type string;
               description
                 "Version of this component";
             }
             leaf part-number {
               type string;
               description
                 "Part number of this component";
             }
             leaf serial-number {
               type string;
               description
                 "Serial number of this component";
             }
             leaf description {
               type string;
               description
                 "Description of this component";
             }
             leaf model-number {
               type string;
               description
                 "Model number of this component";
             }
             leaf clei-code {
               type string;
               description
                 "Common Language Equipment Identifier code of this 
                 component";
             }
             list chassis-sub-sub-sub-module {
               key "name";
               leaf name {
                 type string;
                 description
                   "Name of this component";
               }
               leaf version {
                 type string;
                 description
                   "Version of this component";
               }
               leaf part-number {
                 type string;
                 description
                   "Part number of this component";
               }
               leaf serial-number {
                 type string;
                 description
                   "Serial number of this component";
               }
               leaf description {
                 type string;
                 description
                   "Description of this component";
               }
               leaf model-number {
                 type string;
                 description
                   "Model number of this component";
               }
               leaf clei-code {
                 type string;
                 description
                   "Common Language Equipment Identifier code of this 
                   component";
               }
             }
             container i2c-information {
               leaf jedec-code {
                 type string;
               }
               leaf eeprom-version {
                 type string;
               }
               leaf part-number {
                 type string;
                 description
                   "Part number of this component";
               }
               leaf serial-number {
                 type string;
                 description
                   "Serial number of this component";
               }
               leaf assembly-identifier {
                 type string;
               }
               leaf assembly-version {
                 type string;
               }
               leaf manufacture-date {
                 type string;
                 description
                   "Date this component was manufactured";
               }
               leaf assembly-flags {
                 type string;
               }
               leaf i2c-version {
                 type string;
               }
               leaf clei-code {
                 type string;
                 description
                   "Common Language Equipment Identifier code of this 
                   component";
               }
               leaf i2c-identifier {
                 type string;
               }
               leaf model-number {
                 type string;
                 description
                   "Model number of this component";
               }
               leaf board-information-record {
                 type string;
                 description
                   "Hex dump of board information record";
               }
               leaf i2c-data {
                 type string;
                 description
                   "Hex dump of I2C data";
               }
             }
           }
           leaf model-number {
             type string;
             description
               "Model number of this component";
           }
           leaf clei-code {
             type string;
             description
               "Common Language Equipment Identifier code of this component";
           }
         }
         list chassis-re-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         list chassis-re-usb-module {
           key "name";
           leaf name {
             type string;
             description
               "Name of this component";
           }
           leaf product {
             type string;
           }
           leaf product-number {
             type int32;
           }
           leaf vendor {
             type string;
           }
           leaf description {
             type string;
             description
               "Description of this component";
           }
         }
         list chassis-re-dimm-module {
           key "name";
           leaf name {
             type string;
             description
               "Name of this component";
           }
           leaf part-number {
             type string;
             description
               "Part number of this component";
           }
           leaf die-rev {
             type string;
             description
               " DIE revision of the DIMM";
           }
           leaf pcb-rev {
             type string;
             description
               "PCB revision ";
           }
           leaf mfr-id {
             type string;
             description
               "Manufacture Id of the DIMM";
           }
         }
         list chassis-compute-node-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         leaf license-mode {
           type string;
           description
             "PTX R/IR mode configured";
         }
         leaf model-number {
           type string;
           description
             "Model number of this component";
         }
         leaf clei-code {
           type string;
           description
             "Common Language Equipment Identifier code of this component";
         }
       }
     }
     list system-firmware {
       leaf firmware-name {
         type string;
         description
           "Name of this component";
       }
       leaf firmware-type {
         type string;
         description
           "Type of this component";
       }
       leaf firmware-tag {
         type int32;
         description
           "Multiple firmware per FRU delimiter";
       }
       leaf firmware-revision {
         type string;
         description
           "Firmware version for this component";
       }
       leaf firmware-revision-available {
         type string;
         description
           "Firmware version available on disk for this component";
       }
       leaf firmware-status {
         type string;
         description
           "Firmware status for this component";
       }
       container system-module {
         leaf firmware-name {
           type string;
           description
             "Name of this component";
         }
         container firmware-state {
           description
             "Firmware status per component type";
           leaf firmware-type {
             type string;
             description
               "Type of this component";
           }
           leaf firmware-status {
             type string;
             description
               "Firmware status for this component";
           }
         }
       }
       container system-sub-module-firmware-list {
         list system-sub-module-firmware {
           description
             "Firmware sub module";
           leaf firmware-name {
             type string;
             description
               "Name of this component";
           }
           leaf firmware-type {
             type string;
             description
               "Type of this component";
           }
           leaf firmware-tag {
             type int32;
             description
               "Multiple firmware per FRU delimiter";
           }
           leaf firmware-revision {
             type string;
             description
               "Firmware version for this component";
           }
           leaf firmware-revision-available {
             type string;
             description
               "Firmware version available on disk for this component";
           }
           leaf firmware-status {
             type string;
             description
               "Firmware status for this component";
           }
         }
       }
     }
   }
   grouping hardware-version-information-block {
     list chassis-version {
       leaf component-name {
         type string;
         description
           "PDU component name";
       }
       leaf component-version {
         type string;
       }
       list chassis-module-version {
         leaf component-name {
           type string;
           description
             "PDU component name";
         }
         leaf component-version {
           type string;
         }
         list chassis-module-sub-version {
           leaf component-name {
             type string;
             description
               "PDU component name";
           }
           leaf component-version {
             type string;
           }
           list chassis-module-sub-sub-version {
             leaf component-name {
               type string;
               description
                 "PDU component name";
             }
             leaf component-version {
               type string;
             }
           }
         }
       }
     }
   }
   grouping fpc-information-block {
     list fpc {
       leaf slot {
         type int32;
       }
       leaf state {
         type string;
         description
           "Status of the component";
       }
       leaf comment {
         type string;
       }
       leaf temperature {
         type string;
         description
           "Temperature of the item";
       }
       leaf memory-rldram-size {
         type int32;
         description
           "RLDRAM";
       }
       leaf memory-xr2-size {
         type int32;
         description
           "XR2";
       }
       leaf memory-ddr-dram-size {
         type int32;
         description
           "DDR DRAM";
       }
       container pic-detail {
         container port-information {
           container port {
             leaf port-number {
               type int32;
               description
                 "Port number on the PIC";
             }
             leaf cable-type {
               type string;
               description
                 "Port cable type";
             }
             leaf fiber-mode {
               type string;
               description
                 "Single or multi-mode";
             }
             leaf sfp-vendor-name {
               type string;
               description
                 "SFP vendor name";
             }
             leaf sfp-vendor-pno {
               type string;
               description
                 "SFP vendor part number";
             }
             leaf wavelength {
               type string;
               description
                 "Wavelength of the optical transceiver";
             }
             leaf sfp-vendor-fw-ver {
               type string;
               description
                 "Vendor firmware version";
             }
             leaf sfp-jnpr-ver {
               type string;
               description
                 "Juniper revision";
             }
             leaf sfp-msa-version {
               type string;
               description
                 "MSA version";
             }
             leaf short-long-port {
               type string;
               description
                 "Short or long Port";
             }
           }
         }
         container package-information {
           container package {
             leaf package-name {
               type string;
             }
           }
         }
         container port-profile-speed-information {
           leaf active-portprofile-cfg {
             type string;
             description
               "Current Port Profile Config";
           }
           container profile-port {
             leaf profile-port-number {
               type int32;
               description
                 "PIC port profile port number";
             }
             leaf current-speed {
               type string;
               description
                 "PIC port current speed";
             }
             leaf default-speed {
               type string;
               description
                 "PIC port default speed";
             }
             leaf port-profile-speed-capability {
               type string;
               description
                 "Port profile speed capabilities";
             }
           }
           container port-profile-note-information {
             leaf note-speed {
               type string;
               description
                 "PIC Note";
             }
           }
           container port-profile-channel-note-information {
             leaf note-channel-speed {
               type string;
               description
                 "PIC channel Note";
             }
           }
         }
         container port-group-speed-information {
           container port1 {
             leaf port-number2 {
               type int32;
               description
                 "PIC pg port number";
             }
             leaf pfe-number1 {
               type int32;
               description
                 "PIC pg PFE number";
             }
             leaf pg-number {
               type int32;
               description
                 "PIC port group number";
             }
             leaf speed-capability1 {
               type string;
               description
                 "Port speed capabilities";
             }
           }
         }
         container port-speed-information {
           list port {
             key "port-number1";
             leaf port-number1 {
               type int32;
               description
                 "PIC port number";
             }
             leaf pfe-number {
               type int32;
               description
                 "PIC PFE number";
             }
             leaf speed-capability {
               type string;
               description
                 "Port speed capabilities";
             }
           }
         }
         container pic-error-information {
           container error {
             leaf errnumber {
               type int32;
               description
                 "Serial No";
             }
             leaf errmsg {
               type string;
               description
                 "Configuration Errors";
             }
           }
         }
         container fec-error-information {
           container error {
             leaf errnumber {
               type int32;
               description
                 "Serial No";
             }
             leaf errmsg {
               type string;
               description
                 "Configuration Errors";
             }
           }
         }
         leaf slot {
           type int32;
         }
         leaf pic-slot {
           type int32;
         }
         leaf pic-type {
           type string;
         }
         leaf comment {
           type string;
         }
         leaf asic-type {
           type string;
           description
             "Type of ASIC on the PIC";
         }
         leaf account-layer2-overhead {
           type string;
           description
             "Account Layer2 Overhead Knob Status";
         }
         leaf state {
           type string;
           description
             "Status of the component";
         }
         leaf pic-version {
           type string;
           description
             "PIC hardware version";
         }
         leaf cpu-sw-version {
           type string;
           description
             "Version of operating system running on the PIC";
         }
         leaf cpu-rom-version {
           type string;
           description
             "PIC ROM version";
         }
         leaf cpu-total {
           type int32;
           description
             "Percentage of CPU utilized";
         }
         leaf cpu-interrupt {
           type int32;
           description
             "Percentage of CPU utilized by interrupt processing";
         }
         leaf memory-dram-size {
           type string;
           description
             "DRAM";
         }
         leaf memory-buffer-utilization {
           type int32;
           description
             "Percentage of buffer memory utilized";
         }
         leaf memory-heap-utilization {
           type int32;
           description
             "Percentage of heap memory utilized";
         }
         leaf up-time {
           type string;
           description
             "Length of time this component has been operational";
         }
         leaf pic-package {
           type string;
         }
         leaf pic-clock-sync {
           type string;
           description
             "PIC Clock Synchronization";
         }
         leaf pic-multirate-mode {
           type string;
         }
         leaf pic-channelization-mode {
           type string;
           description
             "PIC Channelization Mode";
         }
         leaf configured-mode {
           type string;
         }
         leaf control-cores {
           type int32;
         }
         leaf data-cores {
           type int32;
         }
         leaf object-cache-size {
           type int32;
         }
         leaf policy-db-size {
           type int32;
         }
         leaf forwarding-db-size {
           type int32;
         }
         leaf wired-process-mem-size {
           type int32;
         }
         leaf wired-max-processes {
           type int32;
         }
         container pic-transport-information {
           leaf pic-transport-admin-state {
             type string;
           }
           leaf pic-transport-oper-state {
             type string;
           }
         }
         leaf slc-slot {
           type int32;
           description
             "SLC id number";
         }
       }
       list mic {
         leaf comment {
           type string;
         }
         leaf mic-slot {
           type int32;
         }
         leaf mic-state {
           type string;
         }
         leaf mic-type {
           type string;
         }
       }
       list pfe-info-values {
         key "pfeid";
         leaf ppfe-id {
           type string;
         }
         leaf pfe-instance {
           type int32;
         }
         leaf pfeid {
           type int32;
         }
         leaf pfe-state {
           type string;
         }
         leaf pfe-temp-perf-throt {
           type string;
         }
         leaf pfe-temp-volt-reduction {
           type string;
         }
       }
       list pfeid-info-values {
         key "pfeid";
         leaf pfe-instance {
           type int32;
         }
         leaf ppfe-id {
           type string;
         }
         leaf pfe-state {
           type string;
         }
         leaf pfe-temp-perf-throt {
           type string;
         }
         leaf pfe-temp-volt-reduction {
           type string;
         }
         leaf pfeid {
           type int32;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
       leaf cpu-total {
         type int32;
         description
           "Percentage of CPU utilized";
       }
       leaf cpu-interrupt {
         type int32;
         description
           "Percentage of CPU utilized by interrupt processing";
       }
       leaf cpu-1min-avg {
         type int32;
         description
           "Percentage of one min average CPU utilized";
       }
       leaf cpu-5min-avg {
         type int32;
         description
           "Percentage of five min average CPU utilized";
       }
       leaf cpu-15min-avg {
         type int32;
         description
           "Percentage of fifteen min average CPU utilized";
       }
       leaf memory-dram-size {
         type string;
         description
           "DRAM";
       }
       leaf memory-heap-utilization {
         type int32;
         description
           "Percentage of heap memory utilized";
       }
       leaf memory-buffer-utilization {
         type int32;
         description
           "Percentage of buffer memory utilized";
       }
       leaf error-code {
         type int32;
         description
           "Code resulting from major or minor error";
       }
       leaf logical-slot {
         type int32;
       }
       leaf cpu-less-info-str {
         type string;
         description
           "Flexible PIC Concentrator (FPC) without CPU";
       }
       leaf memory-sram-size {
         type int32;
         description
           "SRAM";
       }
       leaf memory-sdram-size {
         type int32;
         description
           "SDRAM";
       }
       leaf memory-notification-sdram-size {
         type int32;
         description
           "Notification SDRAM";
       }
       leaf asic-information {
         type string;
       }
       leaf start-time {
         type string;
         description
           "Time this component was started";
       }
       leaf up-time {
         type string;
         description
           "Length of time this component has been operational";
       }
       leaf max-power-consumption {
         type int32;
       }
       leaf memory-hbm-size {
         type int32;
         description
           "HBM";
       }
       leaf last-reboot-reason {
         type string;
         description
           "Last reboot reason of routing engine";
       }
       leaf max-mpc-base-power-consumption {
         type int32;
       }
       leaf max-mic0-power-consumption {
         type int32;
       }
       leaf max-mic1-power-consumption {
         type int32;
       }
       leaf max-mic2-power-consumption {
         type int32;
       }
       leaf max-mic3-power-consumption {
         type int32;
       }
       leaf max-mpc-total-power-consumption {
         type int32;
       }
       leaf fips-capable {
         type string;
         description
           "Does the FPC support FIPS";
       }
       leaf fips-mode {
         type string;
         description
           "Is the FPC in FIPS mode";
       }
       leaf configured-bandwidth {
         type int32;
       }
       leaf operating-bandwidth {
         type int32;
       }
       leaf high-performance-mode-support {
         type string;
         description
           "Is high-performance mode supported";
       }
       leaf pics-in-high-performance-mode {
         type string;
         description
           "PFEs in high-performance mode";
       }
       leaf fpc-pfe-type {
         type string;
       }
       list fpc-pfe-information {
         leaf fpc-pfe-num {
           type int32;
         }
         leaf fpc-pfe-power-state {
           type string;
         }
         leaf fpc-pfe-bandwidth {
           type string;
         }
         leaf fpc-pfe-slc {
           type int32;
           description
             "SLC id number";
         }
       }
       container fpc-slc-information {
         leaf fpc-slc-slot {
           type int32;
           description
             "SLC id number";
         }
         leaf fpc-slc-state {
           type string;
           description
             "SLC state";
         }
         leaf fpc-slc-error-code {
           type int32;
           description
             "Code resulting from major or minor error";
         }
         leaf fpc-slc-version {
           type string;
         }
         leaf fpc-slc-cpu-cores {
           type int32;
           description
             "Cpu cores assigned to SLC";
         }
         leaf fpc-slc-memory-dram-size {
           type string;
           description
             "DRAM";
         }
         leaf fpc-slc-memory-rldram-size {
           type int32;
           description
             "RLDRAM";
         }
         leaf fpc-slc-memory-xr2-size {
           type int32;
           description
             "XR2";
         }
         leaf fpc-slc-memory-ddr-dram-size {
           type int32;
           description
             "DDR DRAM";
         }
         leaf fpc-slc-memory-hbm-size {
           type int32;
           description
             "HBM";
         }
         leaf fpc-slc-start-time {
           type string;
           description
             "Time this component was started";
         }
         leaf fpc-slc-up-time {
           type string;
           description
             "Length of time this component has been operational";
         }
         leaf fpc-slc-comment {
           type string;
         }
         leaf fpc-slc-configured-bandwidth {
           type int32;
         }
         leaf fpc-slc-operating-bandwidth {
           type int32;
         }
         leaf fpc-slot {
           type int32;
           description
             "FPC slot";
         }
         leaf fpc-slc-temperature {
           type int32;
           description
             "Temperature in (C)";
         }
         leaf fpc-slc-cpu-total {
           type int32;
           description
             "Percentage of CPU utilized";
         }
         leaf fpc-slc-cpu-interrupt {
           type int32;
           description
             "Percentage of CPU utilized by interrupt processing";
         }
         leaf fpc-slc-cpu-1min-avg {
           type int32;
           description
             "Percentage of one min average CPU utilized";
         }
         leaf fpc-slc-cpu-5min-avg {
           type int32;
           description
             "Percentage of five min average CPU utilized";
         }
         leaf fpc-slc-cpu-15min-avg {
           type int32;
           description
             "Percentage of fifteen min average CPU utilized";
         }
         leaf fpc-slc-memory-heap-utilization {
           type int32;
           description
             "Percentage of heap memory utilized";
         }
         leaf fpc-slc-memory-buffer-utilization {
           type int32;
           description
             "Percentage of buffer memory utilized";
         }
         leaf fpc-slc-gnf-id {
           type string;
           description
             "Gnf id assigned to SLC";
         }
       }
       leaf description {
         type string;
         description
           "Description of this component";
       }
       list pic {
         leaf pic-slot {
           type int32;
         }
         leaf pic-state {
           type string;
         }
         leaf pic-type {
           type string;
         }
         leaf comment {
           type string;
         }
       }
       leaf gnf-id {
         type string;
       }
       container slc {
         leaf slc-id {
           type int32;
           description
             "SLC id number";
         }
         leaf slc-state {
           type string;
           description
             "SLC state";
         }
         leaf slc-info {
           type string;
           description
             "SLC config info";
         }
         leaf slc-gnf-id {
           type int32;
           description
             "Gnf id assigned to SLC";
         }
       }
     }
     leaf fpc-slot {
       type int32;
       description
         "FPC slot";
     }
     leaf fpc-status {
       type string;
       description
         "FPC status";
     }
     leaf fpc-power-limit {
       type string;
       description
         "FPC power limit";
     }
     leaf fpc-power {
       type string;
       description
         "Total FPC power consumption";
     }
     leaf fpc-priority {
       type string;
       description
         "Priority options";
     }
     leaf fpc-firmware-version {
       type string;
       description
         "POE firmware version";
     }
   }
   grouping fpc-ether-types-information-block {
     list ether {
       leaf slot {
         type int32;
       }
       leaf ether-slot {
         type int32;
       }
       leaf ether-type-default {
         type int32;
       }
       leaf ether-type-configurable {
         type string;
       }
       leaf ether-type-active {
         type int32;
       }
       leaf comment {
         type string;
       }
     }
   }
   grouping fpc-port-information-block {
     list fpc {
       key "slot";
       leaf slot {
         type int32;
       }
       leaf port-num {
         type int32;
       }
       leaf port-config-map {
         type string;
       }
       leaf port-map {
         type string;
       }
       list mic {
         leaf comment {
           type string;
         }
       }
       container pic-detail {
         container port-information {
         }
         container port-profile-speed-information {
         }
         container package-information {
           container package {
             leaf package-name {
               type string;
             }
           }
         }
         container port-group-speed-information {
         }
         container port-speed-information {
         }
         container pic-error-information {
         }
         container fec-error-information {
         }
       }
       list pfe-info-values {
         leaf ppfe-id {
           type string;
         }
       }
       list pfeid-info-values {
         leaf pfe-instance {
           type int32;
         }
         leaf ppfe-id {
           type string;
         }
         leaf pfe-state {
           type string;
         }
         leaf pfe-temp-perf-throt {
           type string;
         }
         leaf pfe-temp-volt-reduction {
           type string;
         }
       }
       list scope-level {
       }
       container fpc-slc-error-information {
         list scope-level {
         }
       }
       list fpc-error {
         list fpc-error-group-detail {
           leaf fpc-error-group-name {
             type string;
           }
           leaf fpc-error-group-occurred {
             type int32;
           }
           leaf fpc-error-group-cleared {
             type int32;
           }
           leaf fpc-error-group-error-id {
             type int32;
           }
         }
       }
     }
   }
   grouping sib-information-block {
     leaf use-cli-info {
       type string;
     }
     container sib {
       leaf slot {
         type int32;
       }
       leaf state {
         type string;
         description
           "Status of the component";
       }
       leaf link-error {
         type string;
         description
           "Link error count";
       }
       leaf destination-error {
         type string;
         description
           "Destination error count";
       }
       leaf up-time {
         type string;
         description
           "Length of time this component has been operational";
       }
       leaf comment {
         type string;
       }
       leaf ok-led {
         type empty;
         description
           "OK LED is lit";
       }
       leaf fail-led {
         type empty;
         description
           "Fail LED is lit";
       }
       leaf active-led {
         type empty;
         description
           "Active LED is lit";
       }
       leaf sib-cable-errors {
         type string;
         description
           "SIB cable errors";
       }
       leaf slot-type {
         type string;
       }
       leaf sib-type {
         type string;
       }
       leaf sib-link-state {
         type string;
         description
           "SIB fabric link state";
       }
       leaf sib-link-errors {
         type string;
         description
           "SIB fabric link errors";
       }
       leaf temperature {
         type string;
         description
           "Temperature of the item";
       }
       leaf start-time {
         type string;
         description
           "Time this component was started";
       }
       leaf sib-errors {
         type string;
         description
           "SIB errors";
       }
     }
   }
   grouping fru-information-block {
     container fru {
       leaf slot {
         type int32;
       }
       leaf state {
         type string;
         description
           "Status of the component";
       }
       leaf up-time {
         type string;
         description
           "Length of time this component has been operational";
       }
       leaf comment {
         type string;
       }
       list error-module {
         container device-entry {
           leaf error-timestamp {
             type int32;
             description
               "Error Timestamp";
           }
         }
       }
     }
   }
   grouping jnu-satellites-information-block {
     list satellite-information {
       leaf satellite-ip {
         type string;
         description
           "Satellite name or ip";
       }
       leaf alive {
         type string;
         description
           "Ping";
       }
       leaf satellite-model {
         type string;
         description
           "Satellite model";
       }
       leaf satellite-version {
         type string;
         description
           "Junos version";
       }
     }
   }
   grouping jnu-role-information-block {
     leaf role {
       type string;
       description
         "JNU Role";
     }
   }
   grouping fm-fpc-state-information-block {
     list fm-fpc-ln {
       list fm-pfe-ln {
         list fm-sib-ln {
           leaf sib-slot {
             type int32;
             description
               "SIB slot number";
           }
           leaf sib-core {
             type int32;
           }
           leaf sib-plane {
             type int32;
           }
           leaf pfe-core-link-state {
             type string;
           }
           leaf sib-fm-state {
             type string;
           }
           leaf sib-asic {
             type int32;
           }
           leaf ln-name {
             type string;
           }
         }
         leaf pfe-slot {
           type int32;
         }
         container fm-plane-ln {
           leaf plane-slot {
             type uint32;
           }
           leaf plane-fm-state {
             type string;
           }
         }
         container fm-link-ln {
           leaf link {
             type uint32;
           }
           leaf link-fm-state {
             type string;
           }
         }
       }
       leaf slot {
         type int32;
       }
     }
     list fm-fpc-ln1 {
       leaf fpc-slot1 {
         type int32;
       }
       list fm-pfe-ln1 {
         leaf pfe-slot1 {
           type int32;
         }
         list fm-pfe-core-ln {
           leaf sib-slot {
             type int32;
             description
               "SIB slot number";
           }
           leaf sib-core {
             type int32;
           }
           leaf sib-plane {
             type int32;
           }
           leaf pfe-core-link-state {
             type string;
           }
           leaf sib-asic {
             type int32;
           }
           leaf ln-name {
             type string;
           }
         }
         list fm-pfe-core-ln-extended {
           leaf sib-slot {
             type int32;
             description
               "SIB slot number";
           }
           leaf sib-core {
             type int32;
           }
           leaf sib-asic {
             type int32;
           }
           leaf sib-plane {
             type int32;
           }
           leaf pfe-core-link-state {
             type string;
           }
           leaf ln-name {
             type string;
           }
         }
       }
     }
     leaf comment {
       type string;
     }
   }
   grouping fm-plane-location-information-block {
     container fm-plane-location {
       leaf plane {
         type string;
         description
           "Plane information";
       }
       leaf sib-f13-slot {
         type string;
         description
           "F13 SIB information";
       }
       leaf sib-f2-slot {
         type string;
         description
           "F2 SIB information";
       }
       leaf sib-l-slot {
         type string;
         description
           "LCC SIB information";
       }
       leaf plane-slot {
         type uint32;
       }
       leaf cb-slot {
         type uint32;
       }
       leaf sfb-plane {
         type uint32;
       }
       leaf sfb-slot {
         type uint32;
       }
       leaf sib-slot {
         type int32;
         description
           "SIB slot number";
       }
       leaf planes {
         type string;
         description
           "Planes associated with the SIB";
       }
       leaf plane-number {
         type uint32;
         description
           "Planes number";
       }
       leaf fab-fru-slot {
         type int32;
         description
           "Fabric FRU slot number";
       }
     }
   }
   grouping fm-topology-block {
     container fm-topo-link-src-des {
       leaf fm-topo-link-msg {
         type string;
       }
       container fm-topo-link-src {
         leaf fm-topo-link-src-in {
           type string;
         }
         leaf fm-topo-link-src-out {
           type string;
         }
         leaf hsl2-state-src {
           type string;
         }
       }
       container fm-topo-link-des {
         leaf fm-topo-link-des-in {
           type string;
         }
         leaf fm-topo-link-des-out {
           type string;
         }
         leaf hsl2-state-des {
           type string;
         }
       }
     }
     container fm-topo-link-io {
       leaf fm-topo-link-header-message {
         type string;
         description
           "Header messages for this command";
       }
       container fm-topo-link-sib {
         leaf fm-topo-link-sibnum {
           type int32;
           description
             "SIB number";
         }
         leaf fm-topo-link-sib-message {
           type string;
           description
             "SIB messages";
         }
         container fm-topo-link-fchip {
           leaf fm-topo-link-fchipnum {
             type int32;
             description
               "FCHIP number";
           }
           container fm-topo-link-fcore {
             leaf fm-topo-link-fcorenum {
               type int32;
               description
                 "FCORE number";
             }
             leaf fm-topo-link-detail-message {
               type string;
               description
                 "Link detail messages";
             }
             container fm-topo-link-source {
               leaf fm-topo-link-in {
                 type string;
                 description
                   "In-link name";
               }
               leaf link-state-source {
                 type string;
                 description
                   "In-link state";
               }
             }
             container fm-topo-link-destination {
               leaf fm-topo-link-out {
                 type string;
                 description
                   "Out-link name";
               }
               leaf link-state-destination {
                 type string;
                 description
                   "Out-link state";
               }
             }
             list fm-topo-link-entry {
               description
                 "Link entry";
               container fm-topo-link-source {
                 description
                   "Source link detail";
                 leaf fm-topo-link-in {
                   type string;
                   description
                     "In-link name";
                 }
                 leaf link-state-source {
                   type string;
                   description
                     "In-link state";
                 }
               }
               container fm-topo-link-destination {
                 description
                   "Destination link detail";
                 leaf fm-topo-link-out {
                   type string;
                   description
                     "Out-link name";
                 }
                 leaf link-state-destination {
                   type string;
                   description
                     "Out-link state";
                 }
               }
             }
           }
         }
       }
     }
     container fm-topo-link {
       leaf fm-topo-sib {
         type string;
         description
           "SIB information";
       }
       leaf fm-topo-dbl-line {
         type string;
         description
           "Under line of the header";
       }
       leaf fm-topo-fail-msg {
         type string;
         description
           "Details of the failure";
       }
       container fm-topo-link-details {
         leaf fm-topo-link-type {
           type string;
           description
             "Type of the link";
         }
         leaf fm-topo-sib-source {
           type string;
           description
             "Source sib";
         }
         leaf fm-topo-sib-dest {
           type string;
           description
             "Destination sib";
         }
         leaf source-pfe-xc-link {
           type string;
           description
             "Source pfe link";
         }
         leaf dest-pfe-xc-link {
           type string;
           description
             "Destination pfe link";
         }
         leaf vcsel-status {
           type string;
           description
             "VCSEL status";
         }
         leaf hsl2-channel {
           type string;
           description
             "HSL2 channel number";
         }
         leaf hsl2-status {
           type string;
           description
             "HSL2 channel status";
         }
         container fm-topo-link-in-out {
           leaf fm-topo-link-type {
             type string;
             description
               "Type of the link";
           }
         }
         container fm-topo-link-details-head-lcc {
           leaf fm-topo-sib-source {
             type string;
             description
               "Source sib";
           }
           leaf fm-topo-sib-dest {
             type string;
             description
               "Destination sib";
           }
         }
         container fm-topo-link-details-lcc {
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
         }
         container fm-topo-link-details-head-sfc {
           leaf fm-topo-sib-source {
             type string;
             description
               "Source sib";
           }
           leaf fm-topo-sib-dest {
             type string;
             description
               "Destination sib";
           }
         }
         container fm-topo-link-details-sfc {
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
         }
       }
       container fm-topo-link-information {
         leaf fm-topo-sib {
           type string;
           description
             "SIB information";
         }
         leaf fm-topo-dbl-line {
           type string;
           description
             "Under line of the header";
         }
         container fm-topo-link-fail {
           leaf fm-topo-sib {
             type string;
             description
               "SIB information";
           }
           leaf fm-topo-fail-msg {
             type string;
             description
               "Details of the failure";
           }
         }
         container fm-topo-link-details {
           leaf fm-topo-link-type {
             type string;
             description
               "Type of the link";
           }
           leaf fm-topo-sib-source {
             type string;
             description
               "Source sib";
           }
           leaf fm-topo-sib-dest {
             type string;
             description
               "Destination sib";
           }
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
           container fm-topo-link-in-out {
             leaf fm-topo-link-type {
               type string;
               description
                 "Type of the link";
             }
           }
           container fm-topo-link-details-head-lcc {
             leaf fm-topo-sib-source {
               type string;
               description
                 "Source sib";
             }
             leaf fm-topo-sib-dest {
               type string;
               description
                 "Destination sib";
             }
           }
           container fm-topo-link-details-lcc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
           container fm-topo-link-details-head-sfc {
             leaf fm-topo-sib-source {
               type string;
               description
                 "Source sib";
             }
             leaf fm-topo-sib-dest {
               type string;
               description
                 "Destination sib";
             }
           }
           container fm-topo-link-details-sfc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
         }
       }
       container fm-topo-link-information-sgl {
         container fm-topo-link-fail-sgl {
           leaf fm-topo-sib {
             type string;
             description
               "SIB information";
           }
           leaf fm-topo-fail-msg {
             type string;
             description
               "Details of the failure";
           }
         }
         container fm-topo-link-details {
           leaf fm-topo-link-type {
             type string;
             description
               "Type of the link";
           }
           leaf fm-topo-sib-source {
             type string;
             description
               "Source sib";
           }
           leaf fm-topo-sib-dest {
             type string;
             description
               "Destination sib";
           }
           leaf source-pfe-xc-link {
             type string;
             description
               "Source pfe link";
           }
           leaf dest-pfe-xc-link {
             type string;
             description
               "Destination pfe link";
           }
           leaf vcsel-status {
             type string;
             description
               "VCSEL status";
           }
           leaf hsl2-channel {
             type string;
             description
               "HSL2 channel number";
           }
           leaf hsl2-status {
             type string;
             description
               "HSL2 channel status";
           }
           container fm-topo-link-in-out {
             leaf fm-topo-link-type {
               type string;
               description
                 "Type of the link";
             }
           }
           container fm-topo-link-details-head-lcc {
             leaf fm-topo-sib-source {
               type string;
               description
                 "Source sib";
             }
             leaf fm-topo-sib-dest {
               type string;
               description
                 "Destination sib";
             }
           }
           container fm-topo-link-details-lcc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
           container fm-topo-link-details-head-sfc {
             leaf fm-topo-sib-source {
               type string;
               description
                 "Source sib";
             }
             leaf fm-topo-sib-dest {
               type string;
               description
                 "Destination sib";
             }
           }
           container fm-topo-link-details-sfc {
             leaf source-pfe-xc-link {
               type string;
               description
                 "Source pfe link";
             }
             leaf dest-pfe-xc-link {
               type string;
               description
                 "Destination pfe link";
             }
             leaf vcsel-status {
               type string;
               description
                 "VCSEL status";
             }
             leaf hsl2-channel {
               type string;
               description
                 "HSL2 channel number";
             }
             leaf hsl2-status {
               type string;
               description
                 "HSL2 channel status";
             }
           }
         }
       }
     }
     container fm-topo-map {
       container fm-topo-map-ln {
         leaf fm-fpc-slot {
           type uint32;
         }
         leaf fm-pfe-slot {
           type uint32;
           description
             "PFE slot";
         }
         leaf fm-cb-slot {
           type uint32;
         }
         leaf port {
           type uint32;
         }
         leaf link-state {
           type string;
         }
       }
     }
     container fm-topo-link-io-b2b {
       leaf fm-topo-link-header-message {
         type string;
         description
           "Header messages for this command";
       }
       container fm-topo-link-fpc {
         leaf fm-topo-link-fpcnum {
           type int32;
           description
             "FPC number";
         }
         leaf fm-topo-link-fpc-message {
           type string;
           description
             "FPC messages";
         }
         container fm-topo-link-fpfe {
           leaf fm-topo-link-fpfenum {
             type int32;
             description
               "FPFE number";
           }
           container fm-topo-link-fcore {
             leaf fm-topo-link-detail-message {
               type string;
               description
                 "Link detail messages";
             }
             list fm-topo-link-entry {
               description
                 "Link entry";
               container fm-topo-link-source {
                 description
                   "Source link detail";
                 leaf fm-topo-link-in {
                   type string;
                   description
                     "In-link name";
                 }
                 leaf link-state-source {
                   type string;
                   description
                     "In-link state";
                 }
               }
               container fm-topo-link-destination {
                 description
                   "Destination link detail";
                 leaf fm-topo-link-out {
                   type string;
                   description
                     "Out-link name";
                 }
                 leaf link-state-destination {
                   type string;
                   description
                     "Out-link state";
                 }
               }
             }
           }
         }
       }
     }
   }
   grouping fm-plane-state-information-block {
     leaf comment {
       type string;
     }
     container fmp-plane {
       leaf slot {
         type int32;
       }
       leaf state {
         type string;
         description
           "Status of the component";
       }
       leaf fru-name {
         type string;
       }
       leaf fru-slot {
         type int32;
         description
           "FRU slot number";
       }
       leaf pfe-slot {
         type int32;
       }
       leaf pfe-link-status {
         type string;
         description
           "PFE link status information";
       }
       leaf lcc-adc-slot {
         type int32;
         description
           "ADC slot number";
       }
       container fru-plane-info {
         leaf fru-name {
           type string;
         }
         leaf fru-slot {
           type int32;
           description
             "FRU slot number";
         }
         container pfe-plane-info {
           leaf pfe-slot {
             type int32;
           }
           leaf pfe-link-status {
             type string;
             description
               "PFE link status information";
           }
         }
       }
       leaf link-error {
         type string;
         description
           "Link error count";
       }
       leaf destination-error {
         type string;
         description
           "Destination error count";
       }
       leaf up-time {
         type string;
         description
           "Length of time this component has been operational";
       }
       leaf plane-cable-errors {
         type string;
         description
           "Number of cable errors in the plane";
       }
       leaf plane-state {
         type string;
         description
           "Plane state information";
       }
       leaf sib-name {
         type string;
         description
           "SIB name";
       }
       leaf sibs-slot {
         type string;
         description
           "Chassis SIB slot number";
       }
       leaf sib-f13-name {
         type string;
         description
           "F13 SIB name";
       }
       leaf f13-slot {
         type int32;
         description
           "F13 slot number";
       }
       leaf even-odd {
         type string;
         description
           "Even or Odd part of SIB F13";
       }
       leaf lcc-slot {
         type int32;
         description
           "LCC slot number";
       }
       leaf sibl-slot {
         type int32;
         description
           "LCC SIB slot number";
       }
       leaf sibl-link-state {
         type string;
         description
           "LCC SIB link state information";
       }
       leaf sgasic-number {
         type int32;
         description
           "SG number on SFC";
       }
       leaf sgasic-port-number {
         type int32;
         description
           "SG port number on SFC";
       }
       leaf sgasic-port-link-state {
         type string;
         description
           "SG port link status on SFC";
       }
       leaf sibs-lcc-pfe-slot {
         type int32;
         description
           "SFC PFE slot number";
       }
       leaf sibs-lcc-pfe-link-state {
         type string;
         description
           "SFC PFE link state information";
       }
       leaf sib-f2-name {
         type string;
         description
           "F2 SIB name";
       }
       leaf sibs2-slot {
         type string;
         description
           "Chassis F2 SIB slot number";
       }
       leaf f2-link-state {
         type string;
         description
           "F2 link state information";
       }
       leaf lcc-sib-link-state {
         type string;
         description
           "LCC SIB link state information";
       }
       leaf lcc-sgasic-number {
         type int32;
         description
           "SG number on LCC";
       }
       leaf lcc-sgasic-port-number {
         type int32;
         description
           "SG port number on LCC";
       }
       leaf lcc-sgasic-port-link-state {
         type string;
         description
           "SG port link status on LCC";
       }
       leaf sibl-lcc-pfe-slot {
         type int32;
         description
           "LCC PFE slot number";
       }
       leaf sibl-lcc-pfe-link-state {
         type string;
         description
           "LCC PFE link state information";
       }
       leaf lcc-fpc-slot {
         type int32;
         description
           "FPC slot number";
       }
       leaf lcc-pfe-slot {
         type int32;
         description
           "PFE slot number";
       }
       leaf lcc-pfe-link-state {
         type string;
         description
           "PFE link state information";
       }
     }
     leaf fabric-header {
       type string;
       description
         "Fabric header";
     }
   }
   grouping fm-state-information-block {
     leaf comment {
       type string;
     }
     container fm-state-item {
       leaf plane-slot {
         type uint32;
       }
       leaf state {
         type string;
         description
           "Status of the component";
       }
       leaf up-time {
         type string;
         description
           "Length of time this component has been operational";
       }
       leaf link-error {
         type string;
         description
           "Link error count";
       }
       leaf link-tf {
         type string;
         description
           "Count of training failure links";
       }
       leaf local-reachability-error {
         type string;
         description
           "Local Reachability error count";
       }
       leaf remote-reachability-error {
         type string;
         description
           "Remote Reachability error count";
       }
     }
   }
   grouping chassis-inventory-block {
     container chassis {
       description
         "Hardware inventory of this chassis";
       leaf name {
         type string;
         description
           "Name of this component";
       }
       leaf version {
         type string;
         description
           "Version of this component";
       }
       leaf part-number {
         type string;
         description
           "Part number of this component";
       }
       leaf serial-number {
         type string;
         description
           "Serial number of this component";
       }
       leaf description {
         type string;
         description
           "Description of this component";
       }
       leaf hardware-incomplete {
         type empty;
       }
       leaf model-number {
         type string;
         description
           "Model number of this component";
       }
       leaf clei-code {
         type string;
         description
           "Common Language Equipment Identifier code of this component";
       }
       container i2c-information {
         leaf jedec-code {
           type string;
         }
         leaf eeprom-version {
           type string;
         }
         leaf part-number {
           type string;
           description
             "Part number of this component";
         }
         leaf serial-number {
           type string;
           description
             "Serial number of this component";
         }
         leaf assembly-identifier {
           type string;
         }
         leaf assembly-version {
           type string;
         }
         leaf manufacture-date {
           type string;
           description
             "Date this component was manufactured";
         }
         leaf assembly-flags {
           type string;
         }
         leaf i2c-version {
           type string;
         }
         leaf clei-code {
           type string;
           description
             "Common Language Equipment Identifier code of this component";
         }
         leaf i2c-identifier {
           type string;
         }
         leaf model-number {
           type string;
           description
             "Model number of this component";
         }
         leaf board-information-record {
           type string;
           description
             "Hex dump of board information record";
         }
         leaf i2c-data {
           type string;
           description
             "Hex dump of I2C data";
         }
       }
       list chassis-module {
         key "name";
         leaf name {
           type string;
           description
             "Name of this component";
         }
         leaf version {
           type string;
           description
             "Version of this component";
         }
         leaf part-number {
           type string;
           description
             "Part number of this component";
         }
         leaf serial-number {
           type string;
           description
             "Serial number of this component";
         }
         leaf description {
           type string;
           description
             "Description of this component";
         }
         leaf ir-mode {
           type string;
           description
             "R/IR mode configured";
         }
         container i2c-information {
           leaf jedec-code {
             type string;
           }
           leaf eeprom-version {
             type string;
           }
           leaf part-number {
             type string;
             description
               "Part number of this component";
           }
           leaf serial-number {
             type string;
             description
               "Serial number of this component";
           }
           leaf assembly-identifier {
             type string;
           }
           leaf assembly-version {
             type string;
           }
           leaf manufacture-date {
             type string;
             description
               "Date this component was manufactured";
           }
           leaf assembly-flags {
             type string;
           }
           leaf i2c-version {
             type string;
           }
           leaf clei-code {
             type string;
             description
               "Common Language Equipment Identifier code of this component";
           }
           leaf i2c-identifier {
             type string;
           }
           leaf model-number {
             type string;
             description
               "Model number of this component";
           }
           leaf board-information-record {
             type string;
             description
               "Hex dump of board information record";
           }
           leaf i2c-data {
             type string;
             description
               "Hex dump of I2C data";
           }
         }
         list firmware {
           leaf firmware-version-psm {
             type string;
           }
           leaf firmware-primary-mcu {
             type string;
           }
           leaf firmware-secondary-mcu {
             type string;
           }
           leaf firmware-communication-mcu {
             type string;
           }
           leaf firmware-led-mcu {
             type string;
           }
           leaf type {
             type string;
             description
               "Type of this component";
           }
           leaf firmware-version {
             type string;
             description
               "Firmware version string for this component";
           }
         }
         list chassis-sub-module {
           key "name";
           leaf name {
             type string;
             description
               "Name of this component";
           }
           leaf version {
             type string;
             description
               "Version of this component";
           }
           leaf part-number {
             type string;
             description
               "Part number of this component";
           }
           leaf serial-number {
             type string;
             description
               "Serial number of this component";
           }
           leaf description {
             type string;
             description
               "Description of this component";
           }
           container i2c-information {
             leaf jedec-code {
               type string;
             }
             leaf eeprom-version {
               type string;
             }
             leaf part-number {
               type string;
               description
                 "Part number of this component";
             }
             leaf serial-number {
               type string;
               description
                 "Serial number of this component";
             }
             leaf assembly-identifier {
               type string;
             }
             leaf assembly-version {
               type string;
             }
             leaf manufacture-date {
               type string;
               description
                 "Date this component was manufactured";
             }
             leaf assembly-flags {
               type string;
             }
             leaf i2c-version {
               type string;
             }
             leaf clei-code {
               type string;
               description
                 "Common Language Equipment Identifier code of this 
                 component";
             }
             leaf i2c-identifier {
               type string;
             }
             leaf model-number {
               type string;
               description
                 "Model number of this component";
             }
             leaf board-information-record {
               type string;
               description
                 "Hex dump of board information record";
             }
             leaf i2c-data {
               type string;
               description
                 "Hex dump of I2C data";
             }
           }
           list firmware {
             leaf firmware-version-psm {
               type string;
             }
             leaf firmware-primary-mcu {
               type string;
             }
             leaf firmware-secondary-mcu {
               type string;
             }
             leaf firmware-communication-mcu {
               type string;
             }
             leaf firmware-led-mcu {
               type string;
             }
           }
           list chassis-sub-sub-module {
             key "name";
             leaf name {
               type string;
               description
                 "Name of this component";
             }
             leaf version {
               type string;
               description
                 "Version of this component";
             }
             leaf part-number {
               type string;
               description
                 "Part number of this component";
             }
             leaf serial-number {
               type string;
               description
                 "Serial number of this component";
             }
             leaf description {
               type string;
               description
                 "Description of this component";
             }
             leaf model-number {
               type string;
               description
                 "Model number of this component";
             }
             leaf clei-code {
               type string;
               description
                 "Common Language Equipment Identifier code of this 
                 component";
             }
             list chassis-sub-sub-sub-module {
               key "name";
               leaf name {
                 type string;
                 description
                   "Name of this component";
               }
               leaf version {
                 type string;
                 description
                   "Version of this component";
               }
               leaf part-number {
                 type string;
                 description
                   "Part number of this component";
               }
               leaf serial-number {
                 type string;
                 description
                   "Serial number of this component";
               }
               leaf description {
                 type string;
                 description
                   "Description of this component";
               }
               leaf model-number {
                 type string;
                 description
                   "Model number of this component";
               }
               leaf clei-code {
                 type string;
                 description
                   "Common Language Equipment Identifier code of this 
                   component";
               }
             }
             container i2c-information {
               leaf jedec-code {
                 type string;
               }
               leaf eeprom-version {
                 type string;
               }
               leaf part-number {
                 type string;
                 description
                   "Part number of this component";
               }
               leaf serial-number {
                 type string;
                 description
                   "Serial number of this component";
               }
               leaf assembly-identifier {
                 type string;
               }
               leaf assembly-version {
                 type string;
               }
               leaf manufacture-date {
                 type string;
                 description
                   "Date this component was manufactured";
               }
               leaf assembly-flags {
                 type string;
               }
               leaf i2c-version {
                 type string;
               }
               leaf clei-code {
                 type string;
                 description
                   "Common Language Equipment Identifier code of this 
                   component";
               }
               leaf i2c-identifier {
                 type string;
               }
               leaf model-number {
                 type string;
                 description
                   "Model number of this component";
               }
               leaf board-information-record {
                 type string;
                 description
                   "Hex dump of board information record";
               }
               leaf i2c-data {
                 type string;
                 description
                   "Hex dump of I2C data";
               }
             }
           }
           leaf model-number {
             type string;
             description
               "Model number of this component";
           }
           leaf clei-code {
             type string;
             description
               "Common Language Equipment Identifier code of this component";
           }
         }
         list chassis-re-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         list chassis-re-usb-module {
           key "name";
           leaf name {
             type string;
             description
               "Name of this component";
           }
           leaf product {
             type string;
           }
           leaf product-number {
             type int32;
           }
           leaf vendor {
             type string;
           }
           leaf description {
             type string;
             description
               "Description of this component";
           }
         }
         list chassis-re-dimm-module {
           key "name";
           leaf name {
             type string;
             description
               "Name of this component";
           }
           leaf part-number {
             type string;
             description
               "Part number of this component";
           }
           leaf die-rev {
             type string;
             description
               " DIE revision of the DIMM";
           }
           leaf pcb-rev {
             type string;
             description
               "PCB revision ";
           }
           leaf mfr-id {
             type string;
             description
               "Manufacture Id of the DIMM";
           }
         }
         list chassis-compute-node-disk-module {
           key "name";
           leaf name {
             type string;
             description
               "Name of this component";
           }
           leaf disk-size {
             type int32;
             description
               "Disk size (megabytes)";
           }
           leaf model {
             type string;
           }
           leaf serial-number {
             type string;
             description
               "Serial number of this component";
           }
           leaf description {
             type string;
             description
               "Description of this component";
           }
         }
         leaf license-mode {
           type string;
           description
             "PTX R/IR mode configured";
         }
         leaf model-number {
           type string;
           description
             "Model number of this component";
         }
         leaf clei-code {
           type string;
           description
             "Common Language Equipment Identifier code of this component";
         }
       }
     }
   }
   grouping power-budget-information-block {
     leaf psu-slot {
       type int32;
       description
         "PSU slot";
     }
     leaf-list psu-type {
       type string;
       description
         "PSU type";
     }
     leaf power-supplied-psu {
       type int32;
       description
         "Power supplied by that PSU";
     }
     leaf power-supply-state {
       type string;
       description
         "State of PSU";
     }
     leaf total-power-supplied {
       type int32;
       description
         "Total Power supplied by all Online PSUs";
     }
     leaf-list psu-redundancy-config {
       type string;
       description
         "PSU redundancy Config";
     }
     leaf base-power {
       type int32;
       description
         "Reserved Power for the chassis";
     }
     leaf line-card-slot {
       type int32;
       description
         "Line card slot";
     }
     leaf-list line-card-type {
       type string;
       description
         "Line card type";
     }
     leaf line-card-power {
       type int32;
       description
         "Power used by that line card";
     }
     leaf line-card-poe-power {
       type int32;
       description
         "Power allocated for PoE per FPC";
     }
     leaf line-card-priority {
       type int32;
       description
         "Priority of the FPC";
     }
     leaf actual-power-used {
       type int32;
       description
         "Actual Power consumed by the chassis";
     }
     leaf total-poe-power-allocated {
       type int32;
       description
         "Total power allocated for Power over Ethernet(PoE)";
     }
     leaf power-available-redundant-case {
       type int32;
       description
         "Power available for use in redundant (N+1) case";
     }
     leaf total-power-available {
       type int32;
       description
         "Power available for use in non redundant (N) case";
     }
     list power-budget {
       key "line-card-slot";
       leaf total-power-supplied {
         type int32;
         description
           "Total Power supplied by all Online PSUs";
       }
       leaf-list psu-redundancy-config {
         type string;
         description
           "PSU redundancy Config";
       }
       leaf base-power {
         type int32;
         description
           "Reserved Power for the chassis";
       }
       leaf line-card-slot {
         type int32;
         description
           "Line card slot";
       }
       leaf-list line-card-type {
         type string;
         description
           "Line card type";
       }
       leaf line-card-power {
         type int32;
         description
           "Power used by that line card";
       }
       leaf line-card-poe-power {
         type int32;
         description
           "Power allocated for PoE per FPC";
       }
       leaf line-card-priority {
         type int32;
         description
           "Priority of the FPC";
       }
       leaf actual-power-used {
         type int32;
         description
           "Actual Power consumed by the chassis";
       }
       leaf total-poe-power-allocated {
         type int32;
         description
           "Total power allocated for Power over Ethernet(PoE)";
       }
       leaf power-available-redundant-case {
         type int32;
         description
           "Power available for use in redundant (N+1) case";
       }
       leaf total-power-available {
         type int32;
         description
           "Power available for use in non redundant (N) case";
       }
       list power-supply {
         key "psu-slot";
         description
           "State of the status LEDs on the faceplate of a power supply";
         leaf psu-slot {
           type int32;
           description
             "PSU slot";
         }
         leaf-list psu-type {
           type string;
           description
             "PSU type";
         }
         leaf power-supplied-psu {
           type int32;
           description
             "Power supplied by that PSU";
         }
         leaf power-supply-state {
           type string;
           description
             "State of PSU";
         }
         leaf slot {
           type int32;
         }
         leaf amber-led {
           type empty;
           description
             "Amber LED is lit";
         }
         leaf green-led {
           type empty;
           description
             "Green LED is lit";
         }
         leaf blue-led {
           type empty;
           description
             "Blue LED is lit";
         }
       }
       leaf fan-tray-slot {
         type int32;
         description
           "Fan Tray slot";
       }
       leaf-list fan-tray-type {
         type string;
         description
           "Fan Tray type";
       }
       leaf fan-tray-base-power {
         type int32;
         description
           "Fan Tray base power";
       }
       leaf fan-tray-actual-power {
         type empty;
         description
           "Actual Power consumed by Fan Tray";
       }
       leaf line-card-actual-power {
         type empty;
         description
           "Power actually used by that line card";
       }
       leaf actual-poe-power-used {
         type int32;
         description
           "Power used for Power over Ethernet (PoE)";
       }
       leaf total-poe-power-available {
         type int32;
         description
           "Total power available for Power over Ethernet (PoE)";
       }
     }
     leaf fan-tray-slot {
       type int32;
       description
         "Fan Tray slot";
     }
     leaf-list fan-tray-type {
       type string;
       description
         "Fan Tray type";
     }
     leaf fan-tray-base-power {
       type int32;
       description
         "Fan Tray base power";
     }
     leaf fan-tray-actual-power {
       type empty;
       description
         "Actual Power consumed by Fan Tray";
     }
     leaf line-card-actual-power {
       type empty;
       description
         "Power actually used by that line card";
     }
     leaf actual-poe-power-used {
       type int32;
       description
         "Power used for Power over Ethernet (PoE)";
     }
     leaf total-poe-power-available {
       type int32;
       description
         "Total power available for Power over Ethernet (PoE)";
     }
   }
   grouping chassis-ae-lb-information-block {
     leaf chassis-ae-lb-state {
       type string;
       description
         "Chassis Multicast Loadbalancing setting";
     }
     leaf chassis-ae-lb-mode {
       type string;
       description
         "Chassis Multicast Loadbalancing mode";
     }
   }
   grouping rps-chassis-information-block {
     list rps-member-list {
       leaf rps-member-id {
         type int32;
       }
       leaf rps-backup-status {
         type string;
       }
       leaf rps-serial-number {
         type string;
       }
       leaf rps-port-number {
         type int32;
       }
     }
   }
   grouping chassis-mac-addresses-block {
     list chassis-mac-addresses-edge-info {
       container re-mac-address {
         leaf re-fc-mac-base {
           type string;
         }
         leaf re-fc-mac-count {
           type string;
         }
         leaf re-vlan-mac {
           type string;
         }
       }
       list fpc-mac-address {
         key "name";
         leaf name {
           type string;
           description
             "Name of this component";
         }
         leaf fpc-mac-base {
           type string;
         }
         leaf fpc-mac-count {
           type string;
         }
       }
     }
     list mac-address-information {
       leaf public-base-address {
         type string;
       }
       leaf public-count {
         type string;
       }
       leaf private-base-address {
         type string;
       }
       leaf private-count {
         type string;
       }
     }
     container external-mac-address-information {
       leaf external-base-address {
         type string;
       }
       leaf external-count {
         type string;
       }
       leaf external-available {
         type string;
       }
     }
   }
   grouping route-engine-information-block {
     list route-engine {
       leaf slot {
         type int32;
       }
       leaf physical-slot {
         type int32;
       }
       leaf mastership-state {
         type string;
         description
           "Current state of mastership on this Routing Engine";
       }
       leaf mastership-priority {
         type string;
         description
           "Configured priority for mastership on this Routing Engine";
       }
       leaf temperature {
         type string;
         description
           "Temperature of the item";
       }
       leaf cpu-temperature {
         type string;
       }
       leaf memory-dram-size {
         type string;
         description
           "DRAM";
       }
       leaf memory-installed-size {
         type string;
         description
           "Installed RAM";
       }
       leaf memory-buffer-utilization {
         type int32;
         description
           "Percentage of buffer memory utilized";
       }
       leaf memory-system-total {
         type int32;
         description
           "Display the total system memory";
       }
       leaf memory-system-total-used {
         type int32;
         description
           "Display overall utilization of system memory";
       }
       leaf memory-system-total-util {
         type int32;
         description
           "Display overall %utilization of system memory";
       }
       leaf memory-control-plane {
         type int32;
         description
           "Display the total memory with control plane";
       }
       leaf memory-control-plane-used {
         type int32;
         description
           "Display the memory utilization of control plane mem";
       }
       leaf memory-control-plane-util {
         type int32;
         description
           "Display the %memory utilization of control plane mem";
       }
       leaf memory-data-plane {
         type int32;
         description
           "Display the total memory preallocated for data plane";
       }
       leaf memory-data-plane-used {
         type int32;
         description
           "Display the memory utilization of data plane mem";
       }
       leaf memory-data-plane-util {
         type int32;
         description
           "Display the %memory utilization of data plane mem";
       }
       leaf control-plane-cpu-count {
         type int32;
         description
           "Display the number of CPUS dedicated for control-plane";
       }
       leaf data-plane-cpu-count {
         type int32;
         description
           "Display the number of CPUS dedicated for data-plane";
       }
       leaf cpu-user {
         type int32;
         description
           "Percentage of CPU utilized by user processes";
       }
       leaf cpu-real-time {
         type int32;
         description
           "Percentage of CPU utilized by real-time threads";
       }
       leaf cpu-background {
         type int32;
         description
           "Percentage of CPU utilized by background processes";
       }
       leaf cpu-system {
         type int32;
         description
           "Percentage of CPU utilized by the kernel";
       }
       leaf cpu-interrupt {
         type int32;
         description
           "Percentage of CPU utilized by interrupt processing";
       }
       leaf cpu-idle {
         type int32;
         description
           "Percentage of CPU idle time";
       }
       leaf cpu-user1 {
         type int32;
         description
           "Percentage of CPU utilized by user processes";
       }
       leaf cpu-background1 {
         type int32;
         description
           "Percentage of CPU utilized by background processes";
       }
       leaf cpu-system1 {
         type int32;
         description
           "Percentage of CPU utilized by the kernel";
       }
       leaf cpu-interrupt1 {
         type int32;
         description
           "Percentage of CPU utilized by the Interrupt";
       }
       leaf cpu-idle1 {
         type int32;
         description
           "Percentage of CPU idle time";
       }
       leaf cpu-user2 {
         type int32;
         description
           "Percentage of CPU utilized by user processes";
       }
       leaf cpu-background2 {
         type int32;
         description
           "Percentage of CPU utilized by background processes";
       }
       leaf cpu-system2 {
         type int32;
         description
           "Percentage of CPU utilized by the kernel";
       }
       leaf cpu-interrupt2 {
         type int32;
         description
           "Percentage of CPU utilized by the Interrupt";
       }
       leaf cpu-idle2 {
         type int32;
         description
           "Percentage of CPU idle time";
       }
       leaf cpu-user3 {
         type int32;
         description
           "Percentage of CPU utilized by user processes";
       }
       leaf cpu-background3 {
         type int32;
         description
           "Percentage of CPU utilized by background processes";
       }
       leaf cpu-system3 {
         type int32;
         description
           "Percentage of CPU utilized by the kernel";
       }
       leaf cpu-interrupt3 {
         type int32;
         description
           "Percentage of CPU utilized by the Interrupt";
       }
       leaf cpu-idle3 {
         type int32;
         description
           "Percentage of CPU idle time";
       }
       leaf model {
         type string;
       }
       leaf serial-number {
         type string;
         description
           "Serial number of this component";
       }
       leaf start-time {
         type string;
         description
           "Time this component was started";
       }
       leaf up-time {
         type string;
         description
           "Length of time this component has been operational";
       }
       leaf last-reboot-reason {
         type string;
         description
           "Last reboot reason of routinge engine";
       }
       leaf load-average-one {
         type string;
       }
       leaf load-average-five {
         type string;
       }
       leaf load-average-fifteen {
         type string;
       }
       leaf bios-version {
         type string;
         description
           "Routing engine BIOS version";
       }
       leaf bios-date {
         type string;
         description
           "Routing engine BIOS date";
       }
       leaf bios-id {
         type string;
         description
           "Routing engine BIOS ID";
       }
       leaf description {
         type string;
         description
           "Description of this component";
       }
       leaf status {
         type string;
         description
           "Status of clock synchronization source";
       }
       leaf loader-name {
         type string;
         description
           "Routing engine Loader name";
       }
       leaf loader-version {
         type string;
         description
           "Routing engine Loader version";
       }
       leaf icrt-version {
         type string;
         description
           "Routing engine iCRT version";
       }
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping route-engine-resiliency-information-block {
     list route-engine-resiliency-entry {
       leaf reerror-module-name {
         type string;
         description
           "Module_name";
       }
       leaf reerror-error-id {
         type uint64;
         description
           "Error_id";
       }
       leaf reerror-threshold {
         type int32;
         description
           "Threshold";
       }
       leaf reerror-count {
         type int32;
         description
           "Count";
       }
       leaf reerror-occured {
         type int32;
         description
           "Occured";
       }
       leaf reerror-cleared {
         type int32;
         description
           "Cleared";
       }
       leaf reerror-errdesc {
         type string;
         description
           "Desc";
       }
       leaf reerror-timestamp {
         type int32;
         description
           "Timestamp";
       }
       leaf reerror-module-id {
         type int32;
         description
           "Module_id";
       }
     }
   }
   grouping fan-information-block {
     leaf name {
       type string;
       description
         "Name of this component";
     }
     leaf status {
       type string;
       description
         "Status of clock synchronization source";
     }
     leaf rpm {
       type string;
       description
         "Fan speed in RPM";
     }
     leaf rpm-percent {
       type string;
       description
         "Fan speed in % RPM";
     }
     leaf comment {
       type string;
     }
     container fan-information-rpm-item {
       leaf name {
         type string;
         description
           "Name of this component";
       }
       leaf status {
         type string;
         description
           "Status of clock synchronization source";
       }
       leaf rpm {
         type string;
         description
           "Fan speed in RPM";
       }
       leaf comment {
         type string;
       }
     }
     container fan-information-percent-rpm-item {
       leaf name {
         type string;
         description
           "Name of this component";
       }
       leaf status {
         type string;
         description
           "Status of clock synchronization source";
       }
       leaf rpm-percent {
         type string;
         description
           "Fan speed in % RPM";
       }
       leaf comment {
         type string;
       }
     }
     list fan-speed-change-history-item {
       key "timestamp";
       leaf timestamp {
         type string;
       }
       leaf fru-name {
         type string;
       }
       leaf temp-sensor-name {
         type string;
       }
       leaf speed-percent {
         type string;
       }
     }
   }
   grouping chassis-location-block {
     list chassis-location-information {
       leaf country-code {
         type string;
         description
           "Country code";
       }
       leaf postal-code {
         type string;
         description
           "Postal code";
       }
       leaf npa-nxx {
         type string;
         description
           "Six digits of the phone number";
       }
       leaf altitude {
         type int32;
         description
           "Feet above (or below) sea level";
       }
       leaf lata {
         type string;
         description
           "Long distance service area";
       }
       leaf latitude {
         type string;
         description
           "Latitude";
       }
       leaf longitude {
         type string;
         description
           "Longitude";
       }
       leaf vcoord {
         type string;
         description
           "Bellcore vertical coordinate";
       }
       leaf hcoord {
         type string;
         description
           "Bellcore horizontal coordinate";
       }
       leaf building {
         type string;
         description
           "Building information";
       }
       leaf floor {
         type uint32;
         description
           "Floor in building";
       }
       leaf rack {
         type uint32;
         description
           "Rack";
       }
     }
   }
   grouping temperature-threshold-information-block {
     list temperature-threshold {
       key "name";
       description
         "Temperature threshold information for a component on the routing 
         platform.";
       leaf name {
         type string;
         description
           "Name of this component";
       }
       leaf fan-normal-speed {
         type string;
         description
           "Temperature above which fans are set to normal speed";
       }
       leaf fan-high-speed {
         type string;
         description
           "Temperature above which fans are set to high speed";
       }
       leaf yellow-alarm {
         type string;
         description
           "Temperature above which yellow alarm is raised";
       }
       leaf bad-fan-yellow-alarm {
         type string;
         description
           "Temperature above which yellow alarm is raised if one or more 
           fans are bad";
       }
       leaf red-alarm {
         type string;
         description
           "Temperature above which red alarm is raised";
       }
       leaf bad-fan-red-alarm {
         type string;
         description
           "Temperature above which red alarm is raised if one or more fans 
           are bad";
       }
       leaf fire-shutdown {
         type string;
         description
           "Temperature above which fire-shutdown occurs";
       }
     }
   }
   grouping enh-temperature-threshold-information-block {
     list enh-temperature-threshold {
       key "name";
       description
         "Temperature threshold information for a component on the routing 
         platform.";
       leaf name {
         type string;
         description
           "Name of this component";
       }
       leaf enh-fan-normal-speed {
         type string;
         description
           "Temperature above which fans are set to normal speed";
       }
       leaf enh-fan-high-speed {
         type string;
         description
           "Temperature above which fans are set to high speed";
       }
       leaf enh-fan-full-speed {
         type string;
         description
           "Temperature above which fans are set to full speed";
       }
       leaf enh-bad-fan-full-speed {
         type string;
         description
           "Temperature above which fans are set to high speed";
       }
       leaf enh-yellow-alarm {
         type string;
         description
           "Temperature above which yellow alarm is raised";
       }
       leaf enh-bad-fan-yellow-alarm {
         type string;
         description
           "Temperature above which yellow alarm is raised if one or more 
           fans are bad";
       }
       leaf enh-red-alarm {
         type string;
         description
           "Temperature above which red alarm is raised";
       }
       leaf enh-bad-fan-red-alarm {
         type string;
         description
           "Temperature above which red alarm is raised if one or more fans 
           are bad";
       }
       leaf enh-fire-shutdown {
         type string;
         description
           "Temperature above which fire-shutdown occurs";
       }
       leaf enh-state {
         type string;
         description
           "Temperature sensor EM policy state";
       }
     }
   }
   grouping in-service-upgrade-status-block {
     list in-service-upgrade-fru-status {
       description
         "In-Service Software Upgrade status for chassis";
       leaf fru-name {
         type string;
       }
       leaf fru-status {
         type string;
       }
       leaf fru-reason {
         type string;
       }
       list in-service-upgrade-pic-status {
         leaf fru-name {
           type string;
         }
         leaf fru-status {
           type string;
         }
         leaf fru-reason {
           type string;
         }
       }
     }
   }
   grouping chassis-oss-map-block {
     leaf chassis-model {
       type string;
       description
         "Actual chassis model";
     }
     leaf oss-map {
       type string;
       description
         "Configured OSS chassis model";
     }
   }
   grouping craft-lcd-led-information-block {
     leaf display-row-1 {
       type string;
     }
     leaf display-row-2 {
       type string;
     }
     leaf name {
       type string;
       description
         "Name of this component";
     }
     list front-panel-lcd {
       description
         "Information from the LCD-LED interfaces";
       container front-panel-title {
         leaf name {
           type string;
           description
             "Name of this component";
         }
         leaf delimiter {
           type string;
         }
       }
       container display-panel-lcd {
         description
           "Text currently appearing on the LCD interface display";
         leaf display-row-1 {
           type string;
         }
         leaf display-row-2 {
           type string;
         }
       }
       container system-led {
         description
           "State of system LEDs on the front panel";
         list system-led-display {
           key "name";
           leaf name {
             type string;
             description
               "Name of this component";
           }
           leaf led-status {
             type string;
           }
         }
       }
       container pic-status-led {
         description
           "State of QIC STATUS LEDs";
         list pic-status-led-display {
           leaf pic-name {
             type string;
           }
           leaf led-status {
             type string;
           }
         }
       }
       container interface-led {
         description
           "State of the Interface LEDs on the front panel";
         leaf interface-display-title {
           type string;
         }
         list interface-led-display {
           leaf interface-name {
             type string;
           }
           leaf led-status {
             type string;
           }
           leaf activity-led {
             type string;
             description
               "State of the Port Activity LED";
           }
         }
       }
     }
   }
   grouping chassis-pic-mode-information-block {
     leaf chassis-pic-mode {
       type string;
       description
         "Pic Mode";
     }
   }
 }
