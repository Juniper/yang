module junos-genstate-stitch-release-os-test-2 {
   yang-version 1;
   namespace "http://yang.juniper.net/junos/genstate/stitch-release-os-test-2";
   prefix jgsrot2;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for stitch-release-os-test-2.

      Copyright (c) 2026 Juniper Networks, Inc.
      All rights reserved.";

   revision 2026-01-01 {
     description "Junos: 26.2R1.7";
   }

   grouping stitch-release-os-test-2-top {
     description
       "Top-level grouping";
     container stitch-release-os-test-2 {
       description
         "Top-level container";
       leaf simple-int {
         type int32;
       }
       leaf simple-string-leaf {
         type string;
       }
     }
   }
   augment "/jgs:genstate" {
     description
       "Adds stitch-release-os-test-2 container to top-level genstate 
       container";
     uses stitch-release-os-test-2-top;
   }
 }
