module junos-genstate-bmp-report-statistics-information {
   yang-version 1;
   namespace "http://yang.juniper.net/junos/genstate/bmp-report-statistics-information";
   prefix jgbrsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bmp-report-statistics-information.

      Copyright (c) 2026 Juniper Networks, Inc.
      All rights reserved.";

   revision 2026-01-01 {
     description "Junos: 26.2R1.7";
   }

   grouping bmp-report-statistics-information-top {
     description
       "Top-level grouping";
     container bmp-report-statistics-information {
       description
         "BMP statistics-report statistics information";
       leaf bmp-report-statistics-header {
         type string;
       }
       list bmp-report {
         key "bmp-station-name";
         leaf bmp-station-name {
           type string;
         }
         container bmp-report-statistics {
           leaf report-count {
             type int32;
             description
               "Total report count";
           }
           leaf report-last-sent-time-stamp {
             type string;
             description
               "Time when last report sent";
           }
         }
       }
     }
   }
   augment "/jgs:genstate" {
     description
       "Adds bmp-report-statistics-information container to top-level 
       genstate container";
     uses bmp-report-statistics-information-top;
   }
 }
