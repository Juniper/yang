module junos-genstate-commit-information {
   yang-version 1;
   namespace "http://yang.juniper.net/junos/genstate/commit-information";
   prefix jgci;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for commit-information.

      Copyright (c) 2026 Juniper Networks, Inc.
      All rights reserved.";

   revision 2026-01-01 {
     description "Junos: 26.2R1.7";
   }

   grouping commit-information-top {
     description
       "Top-level grouping";
     container commit-information {
       description
         "Top-level container";
       container pending-commit {
         leaf user {
           type string;
           description
             "User name executing this script";
         }
         leaf client {
           type string;
           description
             "This client application performed the commit";
         }
         leaf date-time {
           type string;
         }
         leaf log {
           type string;
           description
             "Log message for this commit";
         }
       }
       container prepared-commit {
         leaf user {
           type string;
           description
             "User name executing this script";
         }
         leaf client {
           type string;
           description
             "This client application performed the commit";
         }
         leaf log {
           type string;
           description
             "Log message for this commit";
         }
       }
       list commit-history {
         key "sequence-number";
         leaf sequence-number {
           type int32;
           description
             "Commit sequence number, 0 being the most recent";
         }
         leaf date-time {
           type string;
         }
         leaf user {
           type string;
           description
             "User name executing this script";
         }
         leaf client {
           type string;
           description
             "This client application performed the commit";
         }
         leaf comment {
           type string;
         }
         leaf configuration-revision {
           type string;
           description
             "Configuration revision information";
         }
         leaf log {
           type string;
           description
             "Log message for this commit";
         }
         leaf commit-confirmed {
           type string;
           description
             "Commit confirmed rollback state";
         }
       }
       container rescue-configuration {
         leaf date-time {
           type string;
         }
         leaf user {
           type string;
           description
             "User name executing this script";
         }
         leaf client {
           type string;
           description
             "This client application performed the commit";
         }
         leaf comment {
           type string;
         }
         leaf log {
           type string;
           description
             "Log message for this commit";
         }
       }
     }
   }
   augment "/jgs:genstate" {
     description
       "Adds commit-information container to top-level genstate container";
     uses commit-information-top;
   }
 }
