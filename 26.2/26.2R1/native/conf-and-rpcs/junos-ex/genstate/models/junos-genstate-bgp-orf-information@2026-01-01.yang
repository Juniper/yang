module junos-genstate-bgp-orf-information {
   yang-version 1;
   namespace "http://yang.juniper.net/junos/genstate/bgp-orf-information";
   prefix jgboi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bgp-orf-information.

      Copyright (c) 2026 Juniper Networks, Inc.
      All rights reserved.";

   revision 2026-01-01 {
     description "Junos: 26.2R1.7";
   }

   grouping bgp-orf-information-top {
     description
       "Top-level grouping";
     container bgp-orf-information {
       description
         "Operational information on BGP Outbound Route filtering";
       container bgp-orf {
         leaf peer-address {
           type jt:ipaddr;
         }
         leaf peer-type {
           type string;
         }
         leaf group-name {
           type string;
         }
         list bgp-orf-nlri-info {
           key "nlri-name";
           leaf nlri-name {
             type string;
           }
           leaf filter-out-updates {
             type int32;
           }
           leaf filter-qcount {
             type int32;
           }
           leaf filter-in-updates {
             type int32;
           }
           leaf immediate-count {
             type int32;
           }
           list bgp-orf-filter-information {
             key "filter-type";
             leaf filter-type {
               type string;
             }
             leaf filter-mode {
               type string;
             }
             leaf filter-out-updates {
               type int32;
             }
             leaf filter-qcount {
               type int32;
             }
             leaf filter-in-updates {
               type int32;
             }
             container bgp-orf-filter-info {
             }
           }
         }
       }
     }
   }
   augment "/jgs:genstate" {
     description
       "Adds bgp-orf-information container to top-level genstate container";
     uses bgp-orf-information-top;
   }
 }
