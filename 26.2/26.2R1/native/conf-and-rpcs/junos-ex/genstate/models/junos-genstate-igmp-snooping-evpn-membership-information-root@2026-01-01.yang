module junos-genstate-igmp-snooping-evpn-membership-information-root {
   yang-version 1;
   namespace "http://yang.juniper.net/junos/genstate/igmp-snooping-evpn-membership-information-root";
   prefix jgisemir;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for igmp-snooping-evpn-membership-information-root.

      Copyright (c) 2026 Juniper Networks, Inc.
      All rights reserved.";

   revision 2026-01-01 {
     description "Junos: 26.2R1.7";
   }

   grouping igmp-snooping-evpn-membership-information-root-top {
     description
       "Top-level grouping";
     container igmp-snooping-evpn-membership-information-root {
       description
         "Top-level container";
       list igmp-snooping-evpn-membership-information-per-instance {
         key "instance-name";
         leaf instance-name {
           type string;
         }
         list igmp-snooping-evpn-membership-information-per-bridge-domain {
           key "bridge-domain";
           leaf bridge-domain {
             type string;
             description
               "Bridge Domain";
           }
           leaf evpn-core-nh {
             type uint32;
             description
               "EVPN core nexthop index";
           }
           list igmp-snooping-evpn-membership-information-per-learning-domain {
             key "learning-domain";
             leaf learning-domain {
               type string;
               description
                 "Bridge or VPLS learning domain";
             }
             list mgm-interface-evpn-groups {
               key "interface-name";
               leaf interface-name {
                 type string;
                 description
                   "Name of interface";
               }
               leaf mgm-evpn-groups-count {
                 type int32;
               }
               list mgm-evpn-groups {
                 key "multicast-group-address";
                 leaf multicast-group-address {
                   type jt:ipaddr;
                   description
                     "Group address";
                 }
                 leaf mgm-group-mode-type {
                   type string;
                   description
                     "Group operational mode (Include/Exclude).";
                 }
                 leaf multicast-source-address {
                   type jt:ipaddr;
                   description
                     "Source address";
                 }
                 leaf mgm-evpn-group-type {
                   type string;
                 }
               }
             }
           }
         }
         list igmp-snooping-evpn-membership-information-per-vlan {
           key "vlan";
           leaf vlan {
             type string;
             description
               "Vlan";
           }
           leaf evpn-core-nh {
             type uint32;
             description
               "EVPN core nexthop index";
           }
           list igmp-snooping-evpn-membership-information-per-learning-domain {
             key "learning-domain";
             leaf learning-domain {
               type string;
               description
                 "Bridge or VPLS learning domain";
             }
             list mgm-interface-evpn-groups {
               key "interface-name";
               leaf interface-name {
                 type string;
                 description
                   "Name of interface";
               }
               leaf mgm-evpn-groups-count {
                 type int32;
               }
               list mgm-evpn-groups {
                 key "multicast-group-address";
                 leaf multicast-group-address {
                   type jt:ipaddr;
                   description
                     "Group address";
                 }
                 leaf mgm-group-mode-type {
                   type string;
                   description
                     "Group operational mode (Include/Exclude).";
                 }
                 leaf multicast-source-address {
                   type jt:ipaddr;
                   description
                     "Source address";
                 }
                 leaf mgm-evpn-group-type {
                   type string;
                 }
               }
             }
           }
         }
       }
     }
   }
   augment "/jgs:genstate" {
     description
       "Adds igmp-snooping-evpn-membership-information-root container to 
       top-level genstate container";
     uses igmp-snooping-evpn-membership-information-root-top;
   }
 }
