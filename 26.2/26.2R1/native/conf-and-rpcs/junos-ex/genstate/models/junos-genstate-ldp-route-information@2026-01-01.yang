module junos-genstate-ldp-route-information {
   yang-version 1;
   namespace "http://yang.juniper.net/junos/genstate/ldp-route-information";
   prefix jglri;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ldp-route-information.

      Copyright (c) 2026 Juniper Networks, Inc.
      All rights reserved.";

   revision 2026-01-01 {
     description "Junos: 26.2R1.7";
   }

   grouping ldp-route-information-top {
     description
       "Top-level grouping";
     container ldp-route-information {
       description
         "Top-level container";
       list ldp-route {
         key "ldp-prefix";
         leaf ldp-prefix {
           type string;
         }
         leaf ldp-label {
           type int32;
         }
         leaf ldp-no-label {
           type empty;
         }
         leaf ldp-topology-entry {
           type int32;
         }
         leaf ldp-ingress-route-status {
           type string;
           description
             "Status about whether the ingress route is present or not";
         }
         leaf ldp-ingress-route-last-modified-time {
           type int32;
           description
             "Time since the ingress route was modified";
         }
         leaf ldp-ingress-route-session-id {
           type uint32;
           description
             "Ingress route session id";
         }
         leaf ldp-ingress-route-session-id-version {
           type uint32;
           description
             "Version";
         }
         leaf ldp-merged-next-hop {
           type empty;
           description
             "Both active and non-active next hop will be merged together";
         }
         leaf ldp-inet0-data {
           type int32;
         }
         leaf ldp-reference-count {
           type int32;
         }
         leaf ldp-fec-nexthop-route {
           type string;
           description
             "Nexthop route for longest match FEC";
         }
         leaf-list ldp-fec-events {
           type string;
           description
             "LDP FEC pending events";
         }
         leaf ldp-p2mp-ref-count {
           type int32;
         }
         list ldp-nexthop {
           key "interface-name lsp-name nh-table";
           leaf interface-name {
             type string;
             description
               "Name of interface";
           }
           leaf lsp-name {
             type string;
             description
               "Tunneled into an RSVP LSP";
           }
           leaf nh-table {
             type string;
             description
               "Indirect pointing to another table";
           }
           leaf lsp-no-ldp-tunneling {
             type empty;
             description
               "LDP tunneling is not configured on LSP";
           }
           leaf interface-address {
             type jt:ipaddr;
           }
           leaf ldp-session-id {
             type string;
           }
           leaf ldp-label-request-state {
             type string;
           }
           leaf ldp-label-request-status-code {
             type string;
             description
               "Status of label request from downstream session";
           }
           leaf ldp-route-backoff-time {
             type int32;
             description
               "Time since label request backoff timer started";
           }
         }
         container ldp-route-types {
           description
             "Route types";
           leaf-list ldp-route-type {
             type string;
             description
               "LDP Route type";
           }
         }
         container ldp-route-flags {
           description
             "LDP Route flags";
           leaf-list ldp-route-flag {
             type string;
             description
               "LDP Route flag";
           }
         }
         list ldp-oam-bfd-session {
           key "ldp-oam-destination-address";
           description
             "LDP OAM state information";
           leaf ldp-oam-destination-address {
             type jt:ipaddr;
           }
           leaf ldp-oam-bfd-session-state {
             type string;
           }
           leaf ldp-oam-lsp-ping-state {
             type string;
           }
           leaf ldp-oam-nexthop-address {
             type jt:ipaddr;
           }
           leaf ldp-oam-interface-name {
             type string;
           }
           leaf ldp-oam-nexthop-lsp {
             type string;
           }
         }
         container ldp-fec-history {
           description
             "Log over time of Fec related events";
           leaf ldp-fec-hist-sequence-number {
             type int32;
           }
           leaf ldp-fec-hist-time {
             type string;
           }
           leaf ldp-fec-hist-log {
             type string;
           }
           leaf ldp-fec-hist-more-info {
             type string;
           }
         }
       }
     }
   }
   augment "/jgs:genstate" {
     description
       "Adds ldp-route-information container to top-level genstate container";
     uses ldp-route-information-top;
   }
 }
