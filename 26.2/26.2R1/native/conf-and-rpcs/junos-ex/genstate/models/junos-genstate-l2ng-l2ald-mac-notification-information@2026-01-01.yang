module junos-genstate-l2ng-l2ald-mac-notification-information {
   yang-version 1;
   namespace "http://yang.juniper.net/junos/genstate/l2ng-l2ald-mac-notification-information";
   prefix jgllmni;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for l2ng-l2ald-mac-notification-information.

      Copyright (c) 2026 Juniper Networks, Inc.
      All rights reserved.";

   revision 2026-01-01 {
     description "Junos: 26.2R1.7";
   }

   grouping l2ng-l2ald-mac-notification-information-top {
     description
       "Top-level grouping";
     container l2ng-l2ald-mac-notification-information {
       description
         "Top-level container";
       leaf l2ng-l2ald-mac-notification-status {
         type string;
         description
           "MAC notification status";
       }
       leaf l2ng-l2ald-mac-notification-interval {
         type int32;
         description
           "MAC notification interval";
       }
       leaf l2ng-l2ald-mac-notification-sent {
         type int32;
         description
           "MAC notification(s) sent";
       }
       leaf l2ng-l2ald-mac-notification-max-tablesize {
         type int32;
         description
           "MAC notification(s) maximum table size";
       }
     }
   }
   augment "/jgs:genstate" {
     description
       "Adds l2ng-l2ald-mac-notification-information container to top-level 
       genstate container";
     uses l2ng-l2ald-mac-notification-information-top;
   }
 }
