/*
 * Copyright (c) 2026 Juniper Networks, Inc.
 * All rights reserved.
 */
 module junos-es-rpc-dialer {
   namespace "http://yang.juniper.net/junos-es/rpc/dialer";

   prefix dialer;

   import junos-common-types {
     prefix jt;
     revision-date 2026-01-01;
   }

   organization "Juniper Networks, Inc.";

   contact "yang-support@juniper.net";

   description "Junos RPC YANG module for dialer command(s)";

   revision 2026-01-01 {
     description "Junos: 26.2R1.7";
   }

   rpc get-dialer-interface-information {
     description "Show interface information";
     input {
       leaf level {
         type enumeration {
           enum "brief" {
             description "Display brief output";
           }
           enum "detail" {
             description "Display detailed output";
           }
         }
       }
       leaf interface-name {
         description "Name of dialer logical interface";
         type string;
       }
     }
     output {
       choice output-tags {
         case actual-tag {
           container dialer-interface-information {
             uses dialer-interface-information-block;
           }
         }
         case multichassis-tag {
           container multi-routing-engine-results {
             list multi-routing-engine-item {
               leaf re-name {
                 type string;
               }
               choice output-tags {
                 case actual-tag {
                   container dialer-interface-information {
                     uses dialer-interface-information-block;
                   }
                 }
               }
             }
           }
         }
       }
     }
   }
   rpc get-dialer-pool-information {
     description "Show pool information";
     input {
       leaf level {
         type enumeration {
           enum "brief" {
             description "Display brief output";
           }
           enum "detail" {
             description "Display detailed output";
           }
         }
       }
       leaf pool-name {
         description "Dialer pool identifier";
         type string;
       }
     }
     output {
       choice output-tags {
         case actual-tag {
           container dialer-pool-information {
             uses dialer-pool-information-block;
           }
         }
         case multichassis-tag {
           container multi-routing-engine-results {
             list multi-routing-engine-item {
               leaf re-name {
                 type string;
               }
               choice output-tags {
                 case actual-tag {
                   container dialer-pool-information {
                     uses dialer-pool-information-block;
                   }
                 }
               }
             }
           }
         }
       }
     }
   }
   rpc get-dialer-defaults-information {
     description "Show dialer services software defaults";
     output {
       choice output-tags {
         case actual-tag {
           container dialer-defaults-information {
             uses dialer-defaults-information-block;
           }
         }
         case multichassis-tag {
           container multi-routing-engine-results {
             list multi-routing-engine-item {
               leaf re-name {
                 type string;
               }
               choice output-tags {
                 case actual-tag {
                   container dialer-defaults-information {
                     uses dialer-defaults-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping dialer-interface-information-block {
     container dialer-interface {
       leaf dialer-interface-name {
         type string;
         description
           "Interface name";
       }
       leaf dialer-interface-state {
         type string;
         description
           "Dialer interface state";
       }
       leaf pool-id {
         type string;
         description
           "Pool identifier";
       }
       leaf primary-interface {
         type string;
         description
           "Primary interface";
       }
       container dialer-interface-flags {
         description
           "Flags indicating interface configuration";
         leaf backup {
           type empty;
           description
             "Dialer backup";
         }
         leaf multilink {
           type empty;
           description
             "Dialer multilink";
         }
         leaf watchlist {
           type empty;
           description
             "Dialer watchlist";
         }
         leaf interesting-detected {
           type empty;
           description
             "Interesting packet detected";
         }
       }
       list dial-string-list {
         leaf dial-string {
           type string;
           description
             "Dial string";
         }
       }
       list sub-interface-list {
         leaf sub-interface-name {
           type string;
           description
             "Subordinate interface name";
         }
       }
       list watch-list {
         leaf watch-route {
           type string;
           description
             "Watch route";
         }
       }
       leaf activation-delay {
         type string;
         description
           "Activation delay";
       }
       leaf deactivation-delay {
         type string;
         description
           "Deactivation delay";
       }
       leaf activation-delay-elapsed {
         type string;
         description
           "Activation delay elapsed";
       }
       leaf deactivation-delay-elapsed {
         type string;
         description
           "Deactivation delay elapsed";
       }
       leaf call-idle-timeout {
         type string;
         description
           "Call idle timeout";
       }
       leaf initial-route-check {
         type string;
         description
           "Initial route check delay";
       }
       leaf redial-delay {
         type string;
         description
           "Delay before dialer dials out again (seconds)";
       }
       leaf callback-wait-period {
         type string;
         description
           "Delay before dialer attempts callback (seconds)";
       }
       leaf callback-wait-period-elapsed {
         type string;
         description
           "Number of seconds in callback wait period that have elapsed";
       }
       leaf load-threshold {
         type string;
         description
           "Load threshold that determines when interfaces are added to 
           bundle";
       }
       leaf load-interval {
         type string;
         description
           "Interval over which average load is calculated";
       }
     }
   }
   grouping dialer-pool-information-block {
     container dialer-pool {
       leaf pool-id {
         type string;
         description
           "Pool identifier";
       }
       list pool-member-list {
         container dialer-info {
           leaf dialer-interface-name {
             type string;
             description
               "Interface name";
           }
           leaf dialer-interface-state {
             type string;
             description
               "Dialer interface state";
           }
         }
         container sub-info {
           leaf sub-interface-name {
             type string;
             description
               "Subordinate interface name";
           }
           leaf sub-interface-flags {
             type string;
             description
               "Flags indicating subordinate interface status";
           }
           leaf pool-priority {
             type string;
             description
               "Pool priority";
           }
         }
       }
     }
   }
   grouping dialer-defaults-information-block {
     leaf default-idle-timeout {
       type int32;
       description
         "Default value of dialer idle timeout";
     }
     leaf default-activation-delay {
       type int32;
       description
         "Default value of dialer activation delay";
     }
     leaf default-deactivation-delay {
       type int32;
       description
         "Default value of dialer deactivation delay";
     }
     leaf default-initial-route-check {
       type int32;
       description
         "Default value of dialer watch initial route check time";
     }
     leaf default-pool-priority {
       type int32;
       description
         "Default value of dialer pool priority";
     }
     leaf default-load-threshold {
       type int32;
       description
         "Default value of dialer load threshold";
     }
     leaf default-load-interval {
       type int32;
       description
         "Default value of dialer load interval";
     }
     leaf default-redial-delay {
       type int32;
       description
         "Default value for dialer redial delay which determines how long to
         wait before dialer attempts to redial";
     }
     leaf default-callback-wait-period {
       type int32;
       description
         "Default value of dialer callback wait period which determines how 
         long to wait before dialer attempts a callback";
     }
   }
 }
