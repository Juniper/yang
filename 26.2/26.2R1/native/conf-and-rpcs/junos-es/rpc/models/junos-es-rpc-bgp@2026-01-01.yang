/*
 * Copyright (c) 2026 Juniper Networks, Inc.
 * All rights reserved.
 */
 module junos-es-rpc-bgp {
   namespace "http://yang.juniper.net/junos-es/rpc/bgp";

   prefix bgp;

   import junos-common-types {
     prefix jt;
     revision-date 2026-01-01;
   }

   organization "Juniper Networks, Inc.";

   contact "yang-support@juniper.net";

   description "Junos RPC YANG module for bgp command(s)";

   revision 2026-01-01 {
     description "Junos: 26.2R1.7";
   }

   rpc get-bgp-summary-information {
     description "Show overview of BGP information";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf group {
         description "Show overview of bgp information for a particular group";
         type string;
       }
       leaf exact-instance {
         description "Show peer information for a particular instance";
         type string;
       }
       leaf instance {
         description "Show peer information for instances with this prefix";
         type string;
       }
       leaf auto-discovered {
         description "Show Auto-discovered peers";
         type empty;
       }
       leaf allowed-neighbors {
         description "Show neighbors brought up via allow";
         type empty;
       }
       leaf dynamic-neighbor-template {
         description "Show neighbors brought up via dynamic-neighbor allow";
         type string;
       }
       leaf fabric-color {
         description "Show neighbors with the specified fabric color";
         type string;
       }
     }
     output {
       choice output-tags {
         case actual-tag {
           container bgp-information {
             uses bgp-information-block;
           }
         }
         case multichassis-tag {
           container multi-routing-engine-results {
             list multi-routing-engine-item {
               leaf re-name {
                 type string;
               }
               choice output-tags {
                 case actual-tag {
                   container bgp-information {
                     uses bgp-information-block;
                   }
                 }
               }
             }
           }
         }
       }
     }
   }
   rpc get-bgp-group-information {
     description "Show the BGP group database";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf verbosity_level {
         default "brief";
         type enumeration {
           enum "summary" {
             description "Display summary output";
           }
           enum "brief" {
             description "Display brief output (default)";
           }
           enum "detail" {
             description "Display detailed output";
           }
         }
       }
       leaf exact-instance {
         description "Show peer information for a particular instance";
         type string;
       }
       leaf instance {
         description "Show peer information for instances with this prefix";
         type string;
       }
       leaf group-name {
         description "Show group information for a particular group";
         type string;
       }
     }
     output {
       choice output-tags {
         case actual-tag {
           container bgp-group-information {
             uses bgp-group-information-block;
           }
         }
         case multichassis-tag {
           container multi-routing-engine-results {
             list multi-routing-engine-item {
               leaf re-name {
                 type string;
               }
               choice output-tags {
                 case actual-tag {
                   container bgp-group-information {
                     uses bgp-group-information-block;
                   }
                 }
               }
             }
           }
         }
       }
     }
   }
   rpc get-bgp-group-output-queue-information {
     description "Show BGP output queues by priority";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf group-name {
         description "Show group information for a particular group";
         type string;
       }
     }
     output {
       choice output-tags {
         case actual-tag {
           container bgp-group-information {
             uses bgp-group-information-block;
           }
         }
         case multichassis-tag {
           container multi-routing-engine-results {
             list multi-routing-engine-item {
               leaf re-name {
                 type string;
               }
               choice output-tags {
                 case actual-tag {
                   container bgp-group-information {
                     uses bgp-group-information-block;
                   }
                 }
               }
             }
           }
         }
       }
     }
   }
   rpc get-bgp-rtf-information {
     description "Show route target filtering information";
     input {
       choice daemon-select {
         case rib-sharding {
           leaf rib-sharding {
             description "Name of rib shard";
             type string {
             }
           }
         }
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       choice output-tags {
         case actual-tag {
           container bgp-rtf-information {
             uses bgp-rtf-information-block;
           }
         }
         case multichassis-tag {
           container multi-routing-engine-results {
             list multi-routing-engine-item {
               leaf re-name {
                 type string;
               }
               choice output-tags {
                 case actual-tag {
                   container bgp-rtf-information {
                     uses bgp-rtf-information-block;
                   }
                 }
               }
             }
           }
         }
       }
     }
   }
   rpc get-bgp-traffic-statistics-information {
     description "Show packet statistics for labeled BGP routes";
     input {
       choice daemon-select {
         case rib-sharding {
           leaf rib-sharding {
             description "Name of rib shard";
             type string {
             }
           }
         }
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       choice output-tags {
         case actual-tag {
           container bgp-traffic-statistics-information {
             uses bgp-traffic-statistics-information-block;
           }
         }
         case multichassis-tag {
           container multi-routing-engine-results {
             list multi-routing-engine-item {
               leaf re-name {
                 type string;
               }
               choice output-tags {
                 case actual-tag {
                   container bgp-traffic-statistics-information {
                     uses bgp-traffic-statistics-information-block;
                   }
                 }
               }
             }
           }
         }
       }
     }
   }
   rpc get-bgp-traffic-stats-ingress-labeled-info {
     description "Show ingress labeled path statistics";
     input {
       choice daemon-select {
         case rib-sharding {
           leaf rib-sharding {
             description "Name of rib shard";
             type string {
             }
           }
         }
         case logical-system {
           leaf logical-system {
             description "Name of logical system, or 'all'";
             type string {
             }
           }
         }
       }
       leaf label {
         description "Top label of label stack";
         type union {
           type uint32;
           type string {
             pattern "<.*>|$.*";
           }
         }
       }
     }
     output {
       choice output-tags {
         case actual-tag {
           container bgp-traffic-stats-ingress-labeled-info {
             uses bgp-traffic-stats-ingress-labeled-info-block;
           }
         }
         case multichassis-tag {
           container multi-routing-engine-results {
             list multi-routing-engine-item {
               leaf re-name {
                 type string;
               }
               choice output-tags {
                 case actual-tag {
                   container bgp-traffic-stats-ingress-labeled-info {
                     uses bgp-traffic-stats-ingress-labeled-info-block;
                   }
                 }
               }
             }
           }
         }
       }
     }
   }
   rpc get-bgp-neighbor-information {
     description "Show the BGP neighbor database";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf exact-instance {
         description "Show peer information for a particular instance";
         type string;
       }
       leaf instance {
         description "Show peer information for instances with this prefix";
         type string;
       }
       leaf neighbor-address {
         description "Show the neighbor database for a particular neighbor";
         type string;
       }
       leaf auto-discovered {
         description "Show Auto-discovered peers";
         type empty;
       }
       leaf allowed-neighbors {
         description "Show neighbors brought up via allow";
         type empty;
       }
       leaf fabric-color {
         description "Show neighbors with the specified fabric color";
         type string;
       }
       leaf dynamic-neighbor-template {
         description "Show neighbors brought up via dynamic-neighbor allow";
         type string;
       }
     }
     output {
       choice output-tags {
         case actual-tag {
           container bgp-information {
             uses bgp-information-block;
           }
         }
         case multichassis-tag {
           container multi-routing-engine-results {
             list multi-routing-engine-item {
               leaf re-name {
                 type string;
               }
               choice output-tags {
                 case actual-tag {
                   container bgp-information {
                     uses bgp-information-block;
                   }
                 }
               }
             }
           }
         }
       }
     }
   }
   rpc get-bgp-orf-information {
     description "Show outbound route filtering information";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf verbosity_level {
         default "brief";
         type enumeration {
           enum "brief" {
             description "Display brief output (default)";
           }
           enum "detail" {
             description "Display detailed output";
           }
         }
       }
       leaf instance {
         description "Show ORF information for instances with this prefix";
         type string;
       }
       leaf neighbor-address {
         description "Show ORF information for a particular neighbor";
         type string;
       }
     }
     output {
       choice output-tags {
         case actual-tag {
           container bgp-orf-information {
             uses bgp-orf-information-block;
           }
         }
         case multichassis-tag {
           container multi-routing-engine-results {
             list multi-routing-engine-item {
               leaf re-name {
                 type string;
               }
               choice output-tags {
                 case actual-tag {
                   container bgp-orf-information {
                     uses bgp-orf-information-block;
                   }
                 }
               }
             }
           }
         }
       }
     }
   }
   rpc get-bgp-output-queue-information {
     description "Show outbound routes queue depths by priority";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf instance {
         description "Show route queue depths for instances with this prefix";
         type string;
       }
       leaf neighbor-address {
         description "Show route queue depths for a particular neighbor";
         type string;
       }
     }
     output {
       choice output-tags {
         case actual-tag {
           container bgp-information {
             uses bgp-information-block;
           }
         }
         case multichassis-tag {
           container multi-routing-engine-results {
             list multi-routing-engine-item {
               leaf re-name {
                 type string;
               }
               choice output-tags {
                 case actual-tag {
                   container bgp-information {
                     uses bgp-information-block;
                   }
                 }
               }
             }
           }
         }
       }
     }
   }
   rpc get-origin-validation-statistics {
     description "Show peer validation state statistics";
     input {
       leaf tenant {
         description "Name of tenant, or 'all'";
         type string {
         }
       }
       choice daemon-select {
         case rib-sharding {
           leaf rib-sharding {
             description "Name of rib shard";
             type string {
             }
           }
         }
       }
       leaf neighbor-address {
         description "Show Origin-validation-state statistics for a particular neighbor";
         type string;
       }
     }
     output {
       choice output-tags {
         case actual-tag {
           container bgp-information {
             uses bgp-information-block;
           }
         }
         case multichassis-tag {
           container multi-routing-engine-results {
             list multi-routing-engine-item {
               leaf re-name {
                 type string;
               }
               choice output-tags {
                 case actual-tag {
                   container bgp-information {
                     uses bgp-information-block;
                   }
                 }
               }
             }
           }
         }
       }
     }
   }
   rpc get-bgp-monitoring-protocol-statistics {
     description "Show BGP Monitoring Protocol information";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bgp-information {
             uses bgp-information-block;
           }
         }
         case multichassis-tag {
           container multi-routing-engine-results {
             list multi-routing-engine-item {
               leaf re-name {
                 type string;
               }
               choice output-tags {
                 case actual-tag {
                   container bgp-information {
                     uses bgp-information-block;
                   }
                 }
               }
             }
           }
         }
       }
     }
   }
   rpc get-bmp-insights-time-series-information {
     description "Show BMP insights time-series";
     input {
       choice daemon-select {
         case rib-sharding {
           leaf rib-sharding {
             description "Name of rib shard";
             type string {
             }
           }
         }
       }
       leaf category {
         description "Show information per category";
         type enumeration {
           enum "socket-blocked" {
             description "BMP socket blocked information";
           }
           enum "write-back-pressure" {
             description "BMP write back pressure information";
           }
         }
       }
       leaf last-n-entries {
         description "Show information for last n entries";
         type union {
           type string {
             pattern "<.*>|$.*";
           }
           type uint32 {
             range "1 .. 24";
           }
         }
       }
       leaf station-name {
         description "Show information for a particular station";
         type string;
       }
     }
     output {
       choice output-tags {
         case actual-tag {
           container bmp-insights-time-series-information {
             uses bmp-insights-time-series-information-block;
           }
         }
         case multichassis-tag {
           container multi-routing-engine-results {
             list multi-routing-engine-item {
               leaf re-name {
                 type string;
               }
               choice output-tags {
                 case actual-tag {
                   container bmp-insights-time-series-information {
                     uses bmp-insights-time-series-information-block;
                   }
                 }
               }
             }
           }
         }
       }
     }
   }
   rpc get-bmp-socket-write-stats-information {
     description "Show BMP socket write statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-socket-write-stats-information {
             uses bmp-socket-write-stats-information-block;
           }
         }
         case multichassis-tag {
           container multi-routing-engine-results {
             list multi-routing-engine-item {
               leaf re-name {
                 type string;
               }
               choice output-tags {
                 case actual-tag {
                   container bmp-socket-write-stats-information {
                     uses bmp-socket-write-stats-information-block;
                   }
                 }
               }
             }
           }
         }
       }
     }
   }
   rpc get-bmp-route-monitoring-statistics-information {
     description "Show BMP route monitoring statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-route-monitoring-statistics-information {
             uses bmp-route-monitoring-statistics-information-block;
           }
         }
         case multichassis-tag {
           container multi-routing-engine-results {
             list multi-routing-engine-item {
               leaf re-name {
                 type string;
               }
               choice output-tags {
                 case actual-tag {
                   container bmp-route-monitoring-statistics-information {
                     uses bmp-route-monitoring-statistics-information-block;
                   }
                 }
               }
             }
           }
         }
       }
     }
   }
   rpc get-bmp-eor-stats-information {
     description "Show BMP end-of-rib statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-eor-stats-information {
             uses bmp-eor-stats-information-block;
           }
         }
         case multichassis-tag {
           container multi-routing-engine-results {
             list multi-routing-engine-item {
               leaf re-name {
                 type string;
               }
               choice output-tags {
                 case actual-tag {
                   container bmp-eor-stats-information {
                     uses bmp-eor-stats-information-block;
                   }
                 }
               }
             }
           }
         }
       }
     }
   }
   rpc get-bmp-peer-statistics-information {
     description "Show BMP peer statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-peer-statistics-information {
             uses bmp-peer-statistics-information-block;
           }
         }
         case multichassis-tag {
           container multi-routing-engine-results {
             list multi-routing-engine-item {
               leaf re-name {
                 type string;
               }
               choice output-tags {
                 case actual-tag {
                   container bmp-peer-statistics-information {
                     uses bmp-peer-statistics-information-block;
                   }
                 }
               }
             }
           }
         }
       }
     }
   }
   rpc get-bmp-term-statistics-information {
     description "Show BMP termination statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-term-statistics-information {
             uses bmp-term-statistics-information-block;
           }
         }
         case multichassis-tag {
           container multi-routing-engine-results {
             list multi-routing-engine-item {
               leaf re-name {
                 type string;
               }
               choice output-tags {
                 case actual-tag {
                   container bmp-term-statistics-information {
                     uses bmp-term-statistics-information-block;
                   }
                 }
               }
             }
           }
         }
       }
     }
   }
   rpc get-bmp-report-statistics-information {
     description "Show BMP statistics-report statistics";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output-tags {
         case actual-tag {
           container bmp-report-statistics-information {
             uses bmp-report-statistics-information-block;
           }
         }
         case multichassis-tag {
           container multi-routing-engine-results {
             list multi-routing-engine-item {
               leaf re-name {
                 type string;
               }
               choice output-tags {
                 case actual-tag {
                   container bmp-report-statistics-information {
                     uses bmp-report-statistics-information-block;
                   }
                 }
               }
             }
           }
         }
       }
     }
   }
   rpc get-bgp-output-queue-scheduler {
     description "Show BGP output queue scheduler configuration";
     input {
       choice daemon-select {
         case logical-system {
           leaf logical-system {
             description "Name of logical system, or 'all'";
             type string {
             }
           }
         }
         case rib-sharding {
           leaf rib-sharding {
             description "Name of rib shard";
             type string {
             }
           }
         }
       }
       leaf tenant {
         description "Name of tenant, or 'all'";
         type string {
         }
       }
       leaf exact-instance {
         description "Show scheduler for a particular instance";
         type string;
       }
       leaf instance {
         description "Show scheduler for instances with this prefix";
         type string;
       }
     }
     output {
       choice output-tags {
         case actual-tag {
           container bgp-output-queue-scheduler {
             uses bgp-output-queue-scheduler-block;
           }
         }
         case multichassis-tag {
           container multi-routing-engine-results {
             list multi-routing-engine-item {
               leaf re-name {
                 type string;
               }
               choice output-tags {
                 case actual-tag {
                   container bgp-output-queue-scheduler {
                     uses bgp-output-queue-scheduler-block;
                   }
                 }
               }
             }
           }
         }
       }
     }
   }
   rpc get-bgp-replication-information {
     description "BGP NSR replication state between master and backup";
     input {
       choice daemon-select {
         case rib-sharding {
           leaf rib-sharding {
             description "Name of rib shard";
             type string {
             }
           }
         }
         case logical-system {
           leaf logical-system {
             description "Name of logical system, or 'all'";
             type string {
             }
           }
         }
       }
     }
     output {
       choice output-tags {
         case actual-tag {
           container bgp-sync-information {
             uses bgp-sync-information-block;
           }
         }
         case multichassis-tag {
           container multi-routing-engine-results {
             list multi-routing-engine-item {
               leaf re-name {
                 type string;
               }
               choice output-tags {
                 case actual-tag {
                   container bgp-sync-information {
                     uses bgp-sync-information-block;
                   }
                 }
               }
             }
           }
         }
       }
     }
   }
   rpc get-bgp-tunnel-atribute-information {
     description "Show Tunnel attributes advertised/received";
     input {
       choice daemon-select {
         case logical-system {
           leaf logical-system {
             description "Name of logical system, or 'all'";
             type string {
             }
           }
         }
       }
       leaf verbosity_level {
         default "brief";
         type enumeration {
           enum "summary" {
             description "Display summary output";
           }
           enum "brief" {
             description "Display brief output (default)";
           }
           enum "detail" {
             description "Display detailed output";
           }
         }
       }
     }
     output {
       choice output-tags {
         case actual-tag {
           container bgp-tunnel-atribute-information {
             uses bgp-tunnel-atribute-information-block;
           }
         }
         case multichassis-tag {
           container multi-routing-engine-results {
             list multi-routing-engine-item {
               leaf re-name {
                 type string;
               }
               choice output-tags {
                 case actual-tag {
                   container bgp-tunnel-atribute-information {
                     uses bgp-tunnel-atribute-information-block;
                   }
                 }
               }
             }
           }
         }
       }
     }
   }
   rpc get-bgp-glb {
     description "Show bgp GLB data";
     input {
       choice daemon-select {
         case logical-system {
           leaf logical-system {
             description "Name of logical system, or 'all'";
             type string {
             }
           }
         }
       }
     }
     output {
       choice output-tags {
         case actual-tag {
           container bgp-glb {
             uses bgp-glb-block;
           }
         }
         case multichassis-tag {
           container multi-routing-engine-results {
             list multi-routing-engine-item {
               leaf re-name {
                 type string;
               }
               choice output-tags {
                 case actual-tag {
                   container bgp-glb {
                     uses bgp-glb-block;
                   }
                 }
               }
             }
           }
         }
       }
     }
   }
   rpc get-bgp-glb-path {
     description "Show GLB Paths";
     input {
       choice daemon-select {
         case logical-system {
           leaf logical-system {
             description "Name of logical system, or 'all'";
             type string {
             }
           }
         }
       }
       leaf path-id {
         description "Show Path with a particular identifier";
         type union {
           type uint32;
           type string {
             pattern "<.*>|$.*";
           }
         }
       }
     }
     output {
       choice output-tags {
         case actual-tag {
           container bgp-glb {
             uses bgp-glb-block;
           }
         }
         case multichassis-tag {
           container multi-routing-engine-results {
             list multi-routing-engine-item {
               leaf re-name {
                 type string;
               }
               choice output-tags {
                 case actual-tag {
                   container bgp-glb {
                     uses bgp-glb-block;
                   }
                 }
               }
             }
           }
         }
       }
     }
   }
   rpc get-bgp-glb-path-monitor {
     description "Show GLB Path Monitors";
     input {
       choice daemon-select {
         case logical-system {
           leaf logical-system {
             description "Name of logical system, or 'all'";
             type string {
             }
           }
         }
       }
     }
     output {
       choice output-tags {
         case actual-tag {
           container bgp-glb {
             uses bgp-glb-block;
           }
         }
         case multichassis-tag {
           container multi-routing-engine-results {
             list multi-routing-engine-item {
               leaf re-name {
                 type string;
               }
               choice output-tags {
                 case actual-tag {
                   container bgp-glb {
                     uses bgp-glb-block;
                   }
                 }
               }
             }
           }
         }
       }
     }
   }
   rpc get-bgp-glb-profile {
     description "Show GLB Path Quality Profiles";
     input {
       choice daemon-select {
         case logical-system {
           leaf logical-system {
             description "Name of logical system, or 'all'";
             type string {
             }
           }
         }
       }
       leaf profile-id {
         description "Show Path Quality Profile with a particular identifier";
         type union {
           type uint32;
           type string {
             pattern "<.*>|$.*";
           }
         }
       }
     }
     output {
       choice output-tags {
         case actual-tag {
           container bgp-glb {
             uses bgp-glb-block;
           }
         }
         case multichassis-tag {
           container multi-routing-engine-results {
             list multi-routing-engine-item {
               leaf re-name {
                 type string;
               }
               choice output-tags {
                 case actual-tag {
                   container bgp-glb {
                     uses bgp-glb-block;
                   }
                 }
               }
             }
           }
         }
       }
     }
   }
   rpc get-bgp-glb-profile-space {
     description "Show GLB profile spaces";
     input {
       choice daemon-select {
         case logical-system {
           leaf logical-system {
             description "Name of logical system, or 'all'";
             type string {
             }
           }
         }
       }
     }
     output {
       choice output-tags {
         case actual-tag {
           container bgp-glb {
             uses bgp-glb-block;
           }
         }
         case multichassis-tag {
           container multi-routing-engine-results {
             list multi-routing-engine-item {
               leaf re-name {
                 type string;
               }
               choice output-tags {
                 case actual-tag {
                   container bgp-glb {
                     uses bgp-glb-block;
                   }
                 }
               }
             }
           }
         }
       }
     }
   }
   rpc get-bgp-fabric-advertise {
     description "Show bgp fabric advertise routes";
     input {
       choice daemon-select {
         case logical-system {
           leaf logical-system {
             description "Name of logical system, or 'all'";
             type string {
             }
           }
         }
         case rib-sharding {
           leaf rib-sharding {
             description "Name of rib shard";
             type string {
             }
           }
         }
       }
     }
     output {
       choice output-tags {
         case actual-tag {
           container bgp-fabric-advertise {
             uses bgp-fabric-advertise-block;
           }
         }
         case multichassis-tag {
           container multi-routing-engine-results {
             list multi-routing-engine-item {
               leaf re-name {
                 type string;
               }
               choice output-tags {
                 case actual-tag {
                   container bgp-fabric-advertise {
                     uses bgp-fabric-advertise-block;
                   }
                 }
               }
             }
           }
         }
       }
     }
   }
   rpc get-bgp-diagnostics-overview {
     description "Show BGP diagnostics overview";
     input {
       choice daemon-select {
         case rib-sharding {
           leaf rib-sharding {
             description "Name of rib shard";
             type string {
             }
           }
         }
         case logical-system {
           leaf logical-system {
             description "Name of logical system, or 'all'";
             type string {
             }
           }
         }
       }
     }
     output {
       choice output-tags {
         case actual-tag {
           container bgp-diagnostics-overview {
             uses bgp-diagnostics-overview-block;
           }
         }
         case multichassis-tag {
           container multi-routing-engine-results {
             list multi-routing-engine-item {
               leaf re-name {
                 type string;
               }
               choice output-tags {
                 case actual-tag {
                   container bgp-diagnostics-overview {
                     uses bgp-diagnostics-overview-block;
                   }
                 }
               }
             }
           }
         }
       }
     }
   }
   rpc get-bgp-diagnostics-warnings {
     description "Show BGP related warnings";
     input {
       choice daemon-select {
         case rib-sharding {
           leaf rib-sharding {
             description "Name of rib shard";
             type string {
             }
           }
         }
         case logical-system {
           leaf logical-system {
             description "Name of logical system, or 'all'";
             type string {
             }
           }
         }
       }
     }
     output {
       choice output-tags {
         case actual-tag {
           container bgp-diagnostics-warnings {
             uses bgp-diagnostics-warnings-block;
           }
         }
         case multichassis-tag {
           container multi-routing-engine-results {
             list multi-routing-engine-item {
               leaf re-name {
                 type string;
               }
               choice output-tags {
                 case actual-tag {
                   container bgp-diagnostics-warnings {
                     uses bgp-diagnostics-warnings-block;
                   }
                 }
               }
             }
           }
         }
       }
     }
   }
   rpc get-bgp-diagnostics-import-eval {
     description "Show events which lead to the current BGP import evaluation";
     input {
       choice daemon-select {
         case rib-sharding {
           leaf rib-sharding {
             description "Name of rib shard";
             type string {
             }
           }
         }
         case logical-system {
           leaf logical-system {
             description "Name of logical system, or 'all'";
             type string {
             }
           }
         }
       }
       leaf neighbor-address {
         description "Show last import evaluation trigger for a particular neighbor";
         type string;
       }
     }
     output {
       choice output-tags {
         case actual-tag {
           container bgp-diagnostics-import-eval {
             uses bgp-diagnostics-import-eval-block;
           }
         }
         case multichassis-tag {
           container multi-routing-engine-results {
             list multi-routing-engine-item {
               leaf re-name {
                 type string;
               }
               choice output-tags {
                 case actual-tag {
                   container bgp-diagnostics-import-eval {
                     uses bgp-diagnostics-import-eval-block;
                   }
                 }
               }
             }
           }
         }
       }
     }
   }
   rpc get-bgp-diagnostics-export-eval {
     description "Show events which lead to the current BGP export evaluation";
     input {
       choice daemon-select {
         case rib-sharding {
           leaf rib-sharding {
             description "Name of rib shard";
             type string {
             }
           }
         }
         case logical-system {
           leaf logical-system {
             description "Name of logical system, or 'all'";
             type string {
             }
           }
         }
       }
       leaf group-name {
         description "Show last export evaluation trigger for a particular group";
         type string;
       }
     }
     output {
       choice output-tags {
         case actual-tag {
           container bgp-diagnostics-export-eval {
             uses bgp-diagnostics-export-eval-block;
           }
         }
         case multichassis-tag {
           container multi-routing-engine-results {
             list multi-routing-engine-item {
               leaf re-name {
                 type string;
               }
               choice output-tags {
                 case actual-tag {
                   container bgp-diagnostics-export-eval {
                     uses bgp-diagnostics-export-eval-block;
                   }
                 }
               }
             }
           }
         }
       }
     }
   }
   rpc get-bgp-diagnostics-local-rib-eval {
     description "Show events which lead to the current BGP local rib evaluation";
     input {
       choice daemon-select {
         case rib-sharding {
           leaf rib-sharding {
             description "Name of rib shard";
             type string {
             }
           }
         }
         case logical-system {
           leaf logical-system {
             description "Name of logical system, or 'all'";
             type string {
             }
           }
         }
       }
       leaf rib-name {
         description "Show last local-rib evaluation trigger for a particular rib";
         type string;
       }
     }
     output {
       choice output-tags {
         case actual-tag {
           container bgp-diagnostics-local-rib-eval {
             uses bgp-diagnostics-local-rib-eval-block;
           }
         }
         case multichassis-tag {
           container multi-routing-engine-results {
             list multi-routing-engine-item {
               leaf re-name {
                 type string;
               }
               choice output-tags {
                 case actual-tag {
                   container bgp-diagnostics-local-rib-eval {
                     uses bgp-diagnostics-local-rib-eval-block;
                   }
                 }
               }
             }
           }
         }
       }
     }
   }
   rpc get-bgp-diagnostics-neighbor {
     description "Show BGP neighbor diagnostics";
     input {
       choice daemon-select {
         case rib-sharding {
           leaf rib-sharding {
             description "Name of rib shard";
             type string {
             }
           }
         }
         case logical-system {
           leaf logical-system {
             description "Name of logical system, or 'all'";
             type string {
             }
           }
         }
       }
       leaf neighbor-address {
         description "Address of the the neighbor for diagnostics";
         type string;
         mandatory true;
       }
     }
     output {
       choice output-tags {
         case actual-tag {
           container bgp-diagnostics-neighbor {
             uses bgp-diagnostics-neighbor-block;
           }
         }
         case multichassis-tag {
           container multi-routing-engine-results {
             list multi-routing-engine-item {
               leaf re-name {
                 type string;
               }
               choice output-tags {
                 case actual-tag {
                   container bgp-diagnostics-neighbor {
                     uses bgp-diagnostics-neighbor-block;
                   }
                 }
               }
             }
           }
         }
       }
     }
   }
   rpc get-bgp-diagnostics-route {
     description "Show BGP route diagnostics";
     input {
       choice daemon-select {
         case rib-sharding {
           leaf rib-sharding {
             description "Name of rib shard";
             type string {
             }
           }
         }
         case logical-system {
           leaf logical-system {
             description "Name of logical system, or 'all'";
             type string {
             }
           }
         }
       }
       leaf destination {
         description "BGP route to be diagnosed, use rd:prefix/len format for VPN routes";
         type string;
         mandatory true;
       }
       leaf instance {
         description "Routing instance where BGP neighbor is configured";
         type string;
       }
       leaf table {
         description "Route table name";
         type string;
         mandatory true;
       }
       choice neighbor-choice {
         case from {
           leaf from {
             description "BGP neighbor the route is received from";
             type string;
           }
         }
         case to {
           leaf to {
             description "BGP neighbor the route is advertised to";
             type string;
           }
         }
       }
     }
     output {
       choice output-tags {
         case actual-tag {
           container bgp-diagnostics-route {
             uses bgp-diagnostics-route-block;
           }
         }
         case multichassis-tag {
           container multi-routing-engine-results {
             list multi-routing-engine-item {
               leaf re-name {
                 type string;
               }
               choice output-tags {
                 case actual-tag {
                   container bgp-diagnostics-route {
                     uses bgp-diagnostics-route-block;
                   }
                 }
               }
             }
           }
         }
       }
     }
   }
   rpc get-bgp-diagnostics-dropped-route-cache {
     description "Show all cached dropped routes for a given peer rib";
     input {
       choice daemon-select {
         case rib-sharding {
           leaf rib-sharding {
             description "Name of rib shard";
             type string {
             }
           }
         }
         case logical-system {
           leaf logical-system {
             description "Name of logical system, or 'all'";
             type string {
             }
           }
         }
       }
       leaf instance {
         description "Routing instance where BGP neighbor is configured";
         type string;
       }
       leaf table {
         description "Route table name";
         type string;
         mandatory true;
       }
       leaf from {
         description "BGP neighbor the dropped routes are received from";
         type string;
         mandatory true;
       }
     }
     output {
       choice output-tags {
         case actual-tag {
           container bgp-diagnostics-dropped-route-cache {
             uses bgp-diagnostics-dropped-route-cache-block;
           }
         }
         case multichassis-tag {
           container multi-routing-engine-results {
             list multi-routing-engine-item {
               leaf re-name {
                 type string;
               }
               choice output-tags {
                 case actual-tag {
                   container bgp-diagnostics-dropped-route-cache {
                     uses bgp-diagnostics-dropped-route-cache-block;
                   }
                 }
               }
             }
           }
         }
       }
     }
   }
   rpc get-bgp-spring-information {
     description "Show BGP source-packet-routing";
     input {
       choice daemon-select {
         case rib-sharding {
           leaf rib-sharding {
             description "Name of rib shard";
             type string {
             }
           }
         }
       }
     }
     output {
       choice output-tags {
         case actual-tag {
           container bgp-spring-information {
             uses bgp-spring-information-block;
           }
         }
         case multichassis-tag {
           container multi-routing-engine-results {
             list multi-routing-engine-item {
               leaf re-name {
                 type string;
               }
               choice output-tags {
                 case actual-tag {
                   container bgp-spring-information {
                     uses bgp-spring-information-block;
                   }
                 }
               }
             }
           }
         }
       }
     }
   }
   rpc get-bgp-srgb-information {
     description "Show BGP source-packet-routing srgb";
     input {
       choice daemon-select {
         case logical-system {
           leaf logical-system {
             description "Name of logical system, or 'all'";
             type string {
             }
           }
         }
       }
     }
     output {
       choice output-tags {
         case output-tag {
           leaf output {
             type string;
           }
         }
         case actual-tag {
           anyxml bgp-srgb-information;
         }
         case multichassis-tag {
           anyxml multi-routing-engine-results;
         }
       }
     }
   }
   rpc get-bgp-rv-statistics-information {
     description "Show BGP route validation statistics";
     input {
       choice daemon-select {
         case rib-sharding {
           leaf rib-sharding {
             description "Name of rib shard";
             type string {
             }
           }
         }
       }
       leaf instance {
         description "Show BGP route validation statistics belonging to instances";
         type string;
       }
     }
     output {
       choice output-tags {
         case actual-tag {
           container bgp-rv-statistics-information {
             uses bgp-rv-statistics-information-block;
           }
         }
         case multichassis-tag {
           container multi-routing-engine-results {
             list multi-routing-engine-item {
               leaf re-name {
                 type string;
               }
               choice output-tags {
                 case actual-tag {
                   container bgp-rv-statistics-information {
                     uses bgp-rv-statistics-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping bgp-information-block {
     leaf bgp-thread-mode {
       type string;
     }
     leaf thread-state {
       type string;
     }
     leaf thread-updio-count {
       type int32;
       description
         "Update io thread count";
     }
     leaf thread-shard-count {
       type int32;
       description
         "Shards thread count";
     }
     leaf tcp-listen-port {
       type uint32;
       description
         "TCP port BGP is accepting connections on";
     }
     leaf default-ebgp-advertise-mode {
       type string;
       description
         "Default eBGP advertisement mode";
     }
     leaf default-ebgp-receive-mode {
       type string;
       description
         "Default eBGP receive mode";
     }
     leaf default-ibgp-loopcheck-state {
       type string;
       description
         "Default iBGP loop check state";
     }
     leaf group-count {
       type int32;
     }
     leaf peer-count {
       type int32;
       description
         "Total number of peers";
     }
     leaf down-peer-count {
       type int32;
     }
     leaf unconfigured-peer-count {
       type int32;
     }
     leaf half-open-peer-count {
       type int32;
     }
     leaf auto-discovered-peer-count {
       type int32;
     }
     container peer-inb-conv-info {
       leaf inb-conv-status {
         type string;
         description
           "State of inbound convergence";
       }
       leaf inb-conv-time {
         type string;
         description
           "Time taken for inbound convergence";
       }
       leaf inb-conv-wait-period {
         type uint32;
         description
           "Maximum wait time for inbound convergence";
       }
       leaf inb-conv-reason {
         type string;
         description
           "Reason of inbound convergence";
       }
       leaf nlri-waiting-eor {
         type string;
         description
           "NLRI that end-of-rib is expected but not received";
       }
       leaf inb-conv-abort-time {
         type string;
         description
           "Time pending for inbound convergence";
       }
     }
     list bgp-family-stat {
       key "nlri-type";
       leaf nlri-type {
         type string;
         description
           "Type of NLRI being limited";
       }
       leaf bgp-nlri-send-time {
         type int32;
         description
           "Time for initial send by peer";
       }
       leaf bgp-nlri-recv-time {
         type int32;
         description
           "Time for initial receive by peer";
       }
     }
     container bgp-updio-globals {
       leaf bgp-updio-cfg-seq {
         type int32;
       }
       leaf bgp-updio-shutting-down {
         type int32;
       }
       leaf bgp-updio-shutdown-rcvd {
         type string;
       }
       leaf bgp-updio-shutdown-sent {
         type int32;
       }
       leaf bgp-updio-gc-timer {
         type int32;
       }
       leaf bgp-updio-gc-count {
         type int32;
       }
       leaf bgp-updio-gc-job {
         type string;
       }
     }
     list bgp-rib {
       key "name";
       leaf name {
         type string;
       }
       leaf total-prefix-count {
         type int32;
         description
           "Total number of prefixes in this RIB";
       }
       leaf active-prefix-count {
         type int32;
         description
           "Number of active prefixes";
       }
       leaf suppressed-prefix-count {
         type int32;
         description
           "Number of prefixes suppressed due to damping";
       }
       leaf history-prefix-count {
         type int32;
         description
           "Number of prefixes with damping history maintained";
       }
       leaf damped-prefix-count {
         type int32;
         description
           "Number of prefixes in any damped state";
       }
       leaf pending-prefix-count {
         type int32;
         description
           "Number of prefixes with pending changes";
       }
       leaf received-prefix-count {
         type int32;
         description
           "For a peer RIB, number of prefixes received from this peer";
       }
       leaf accepted-prefix-count {
         type int32;
         description
           "For a peer RIB, number of prefixes from this peer accepted by 
           policy";
       }
       leaf active-external-prefix-count {
         type int32;
         description
           "Number of active prefixes received from external peers";
       }
       leaf total-external-prefix-count {
         type int32;
         description
           "Total number of prefixes received from external peers";
       }
       leaf accepted-external-prefix-count {
         type int32;
         description
           "Number of accepted prefixes received from external peers";
       }
       leaf suppressed-external-prefix-count {
         type int32;
         description
           "Number of external prefixes suppressed due to damping";
       }
       leaf active-internal-prefix-count {
         type int32;
         description
           "Number of active prefixes received from internal peers";
       }
       leaf total-internal-prefix-count {
         type int32;
         description
           "Total number of prefixes received from internal peers";
       }
       leaf accepted-internal-prefix-count {
         type int32;
         description
           "Number of accepted prefixes received from internal peers";
       }
       leaf suppressed-internal-prefix-count {
         type int32;
         description
           "Number of internal prefixes suppressed due to damping";
       }
       leaf rib-bit {
         type string;
       }
       leaf bgp-rib-state {
         type string;
       }
       leaf vpn-rib-state {
         type string;
       }
       leaf send-state {
         type string;
       }
       leaf stale-prefix-count {
         type int32;
         description
           "Number of prefixes marked as stale";
       }
       leaf llgr-stale-prefix-count {
         type int32;
         description
           "Number of prefixes marked as LLGR stale";
       }
       leaf advertised-prefix-count {
         type int32;
         description
           "Number of prefixes present in the RIB-OUT";
       }
     }
     list bgp-peer {
       key "peer-address";
       description
         "Operational and configuration information for a BGP peer";
       leaf-list bgp-peer.heading {
         type string;
         description
           "Operational and configuration information for a BGP peer";
       }
       leaf peer-address {
         type jt:ipaddr;
       }
       leaf peer-as {
         type int32;
         description
           "Peer AS number";
       }
       leaf input-messages {
         type int32;
       }
       leaf output-messages {
         type int32;
       }
       leaf route-queue-count {
         type int32;
         description
           "Total number of routes queued for output to this peer";
       }
       leaf flap-count {
         type int32;
         description
           "Number of times BGP sessions have gone down";
       }
       leaf elapsed-time {
         type string;
         description
           "Time this adjacency or session has been up or down";
       }
       leaf peer-state {
         type string;
       }
       leaf local-interface-index {
         type int32;
         description
           "SNMP ifIndex of local interface";
       }
       leaf peer-end-of-rib-scheduled {
         type string;
       }
       leaf extended-information {
         type string;
       }
       container bgp-option-information {
         leaf bgp-nlri-send-time {
           type int32;
           description
             "Time for initial send by peer";
         }
         list nlri-policy {
           key "nlri-type";
           leaf nlri-type {
             type string;
             description
               "Type of NLRI being limited";
           }
           leaf nlri-export-policy {
             type string;
           }
           leaf nlri-import-policy {
             type string;
           }
         }
         container nlri-send-community {
           leaf nlri-type {
             type string;
             description
               "Type of NLRI being limited";
           }
           leaf nlri-send-community-type {
             type string;
           }
         }
         container addpath-send {
           leaf nlri-type {
             type string;
             description
               "Type of NLRI being limited";
           }
           leaf addpath-send-type {
             type string;
           }
           leaf addpath-send-count {
             type int32;
           }
           leaf addpath-send-policy {
             type string;
           }
         }
         container addpath-receive {
           leaf nlri-type {
             type string;
             description
               "Type of NLRI being limited";
           }
           leaf addpath-receive-type {
             type string;
           }
         }
         container nlri-information {
           leaf nlri-type {
             type string;
             description
               "Type of NLRI being limited";
           }
           leaf nlri-flow-novalidate {
             type string;
             description
               "Policy to accept flow routes without validation";
           }
           leaf nlri-output-queue-priority {
             type string;
             description
               "Default address family output queue priority";
           }
           leaf nlri-route-refresh-priority {
             type string;
             description
               "Default address family route-refresh priority";
           }
           leaf nlri-withdraw-priority {
             type string;
             description
               "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-rtage-refl-upd-msgs {
               type empty;
             }
             leaf bgp-nlri-flag-no-resolution {
               type empty;
             }
             leaf bgp-nlri-flag-resolve-preserve-hier {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-accept-local-addr-pnh {
               type empty;
             }
             leaf bgp-nlri-flag-accept-own {
               type empty;
             }
             leaf bgp-nlri-flag-strip-nexthop {
               type empty;
             }
             leaf bgp-nlri-flag-allow-po-add-nexthop {
               type empty;
             }
             leaf bgp-nlri-flag-per-nexthop-label {
               type empty;
             }
           }
           container nlri-traffic-stats {
             leaf traffic-stats-interval {
               type int32;
             }
             container tracing-information {
               leaf flags {
                 type string;
                 description
                   "Enabled trace flags";
               }
               leaf filename {
                 type string;
                 description
                   "Name of the trace file";
               }
               leaf filesize {
                 type int32;
                 description
                   "Maximum size of the trace file";
               }
               leaf filelimit {
                 type int32;
                 description
                   "Maximum number of retained trace files";
               }
             }
           }
           container output-queues {
             description
               "BGP output queues statistics";
             leaf time-series {
               type string;
             }
             list class {
               description
                 "An instance of BGP output queue statistics";
               leaf priority-type {
                 type string;
                 description
                   "BGP output queue priority type";
               }
               leaf rank {
                 type int32;
                 description
                   "BGP output queue rank for priority type";
               }
               leaf token-count {
                 type int32;
                 description
                   "BGP output queue token count for priority";
               }
               leaf output-queue-route-count {
                 type int32;
                 description
                   "BGP output queue route count for priority";
               }
             }
           }
         }
         leaf export-policy {
           type string;
         }
         leaf import-policy {
           type string;
         }
         leaf send-community-type {
           type string;
         }
         leaf advertise-bgp-static-policy {
           type string;
         }
         leaf bgp-options {
           type string;
         }
         leaf bgp-options2 {
           type string;
         }
         leaf bgp-options-extended {
           type string;
         }
         leaf bgp-options-extended2 {
           type string;
         }
         leaf remove-private-options {
           type string;
         }
         leaf authentication-key {
           type string;
         }
         leaf authentication-key-chain {
           type string;
           description
             "Name of authentication key chain";
         }
         leaf authentication-algorithm {
           type string;
           description
             "Name of authentication algorithm";
         }
         leaf authentication-configured {
           type empty;
         }
         leaf gshut-recv-local-preference {
           type uint32;
         }
         leaf gshut-send-local-preference {
           type uint32;
         }
         leaf address-families {
           type string;
         }
         leaf ignore-path-attributes {
           type string;
         }
         leaf local-address {
           type jt:ipaddr;
         }
         leaf holdtime {
           type int32;
           description
             "Delay before timing out the adjacency (default is 180 seconds)";
         }
         leaf metric-out {
           type int32;
         }
         leaf preference {
           type int32;
           description
             "Preference for the route";
         }
         leaf local-preference {
           type int32;
         }
         leaf local-as {
           type int32;
           description
             "Local AS number";
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         leaf bgp-bmp-route-monitoring-ribout-prepolicy {
           type empty;
         }
         leaf bgp-bmp-route-monitoring-ribout-postpolicy {
           type empty;
         }
         container drop-path-attr-info {
           leaf drop-path-attributes {
             type string;
           }
           leaf drop-path-attributes-uot {
             type string;
           }
         }
         container wdraw-path-attr-info {
           leaf wdraw-path-attributes {
             type string;
           }
           leaf wdraw-path-attributes-uot {
             type string;
           }
         }
         container prefix-limit {
           leaf nlri-type {
             type string;
             description
               "Type of NLRI being limited";
           }
           leaf prefix-count {
             type int32;
             description
               "Number of prefixes accepted before action is taken";
           }
           leaf limit-action {
             type string;
             description
               "Action taken upon reaching limit";
           }
           leaf warning-percentage {
             type int32;
             description
               "Percentage of limit at which to log a warning";
           }
         }
         container accepted-prefix-limit {
           description
             "Limit number of prefixes accepted by policy";
           leaf nlri-type {
             type string;
             description
               "Type of NLRI being limited";
           }
           leaf prefix-count {
             type int32;
             description
               "Number of prefixes accepted before action is taken";
           }
           leaf limit-action {
             type string;
             description
               "Action taken upon reaching limit";
           }
           leaf warning-percentage {
             type int32;
             description
               "Percentage of limit at which to log a warning";
           }
         }
         container aigp-mode {
           leaf nlri-type {
             type string;
             description
               "Type of NLRI being limited";
           }
         }
         container family-damping-info {
           leaf nlri-type {
             type string;
             description
               "Type of NLRI being limited";
           }
         }
         container protection {
           leaf nlri-type {
             type string;
             description
               "Type of NLRI being limited";
           }
         }
       }
       container egress-protection {
         container nlri-egress-protection {
           leaf nlri-type {
             type string;
             description
               "Type of NLRI being limited";
           }
           leaf bgp-context-id {
             type jt:ipaddr;
           }
           leaf bgp-import-policy {
             type string;
           }
         }
         list ep-backup-table {
           leaf-list ep-backup-rib-name {
             type string;
             description
               "Instance backup RIB";
           }
           leaf ep-backup-link {
             type string;
             description
               "Vt interface";
           }
           leaf ep-backup-rib-id {
             type int32;
             description
               "RIB Identifier";
           }
           leaf ep-backup-kern-id {
             type int32;
             description
               "FIB Identifier";
           }
           leaf ep-backup-table-nh {
             type string;
             description
               "Enhanced table nexthop";
           }
           leaf-list ep-instance-route-targets {
             type string;
             description
               "Instance route targets";
           }
           leaf ep-backup-instance {
             type string;
           }
           leaf ep-backup-context {
             type string;
             description
               "Instance backup context";
           }
         }
         list ep-instance-table {
           leaf ep-instance-name {
             type string;
           }
           leaf ep-instance-type {
             type string;
             description
               "Instance type";
           }
           leaf ep-instance-protection-type {
             type string;
             description
               "Instance request protected";
           }
           leaf ep-instance-context-id {
             type jt:ipaddr;
             description
               "Context-id";
           }
           leaf-list ep-backup-rib-name {
             type string;
             description
               "Instance backup RIB";
           }
         }
         leaf nlri-type {
           type string;
           description
             "Type of NLRI being limited";
         }
       }
       list bgp-output-queue {
         key "number";
         leaf number {
           type int32;
         }
         leaf count {
           type int32;
         }
         leaf table-name {
           type string;
           description
             "Unicast routing table";
         }
         leaf rib-adv-nlri {
           type string;
         }
         leaf time-series {
           type string;
         }
         list class {
           description
             "An instance of BGP output queue statistics";
           leaf priority-type {
             type string;
             description
               "BGP output queue priority type";
           }
           leaf rank {
             type int32;
             description
               "BGP output queue rank for priority type";
           }
           leaf token-count {
             type int32;
             description
               "BGP output queue token count for priority";
           }
         }
       }
       list bgp-rib {
         key "name";
         leaf name {
           type string;
         }
         leaf total-prefix-count {
           type int32;
           description
             "Total number of prefixes in this RIB";
         }
         leaf active-prefix-count {
           type int32;
           description
             "Number of active prefixes";
         }
         leaf suppressed-prefix-count {
           type int32;
           description
             "Number of prefixes suppressed due to damping";
         }
         leaf history-prefix-count {
           type int32;
           description
             "Number of prefixes with damping history maintained";
         }
         leaf damped-prefix-count {
           type int32;
           description
             "Number of prefixes in any damped state";
         }
         leaf pending-prefix-count {
           type int32;
           description
             "Number of prefixes with pending changes";
         }
         leaf received-prefix-count {
           type int32;
           description
             "For a peer RIB, number of prefixes received from this peer";
         }
         leaf accepted-prefix-count {
           type int32;
           description
             "For a peer RIB, number of prefixes from this peer accepted by 
             policy";
         }
         leaf active-external-prefix-count {
           type int32;
           description
             "Number of active prefixes received from external peers";
         }
         leaf total-external-prefix-count {
           type int32;
           description
             "Total number of prefixes received from external peers";
         }
         leaf accepted-external-prefix-count {
           type int32;
           description
             "Number of accepted prefixes received from external peers";
         }
         leaf suppressed-external-prefix-count {
           type int32;
           description
             "Number of external prefixes suppressed due to damping";
         }
         leaf active-internal-prefix-count {
           type int32;
           description
             "Number of active prefixes received from internal peers";
         }
         leaf total-internal-prefix-count {
           type int32;
           description
             "Total number of prefixes received from internal peers";
         }
         leaf accepted-internal-prefix-count {
           type int32;
           description
             "Number of accepted prefixes received from internal peers";
         }
         leaf suppressed-internal-prefix-count {
           type int32;
           description
             "Number of internal prefixes suppressed due to damping";
         }
         leaf rib-bit {
           type string;
         }
         leaf bgp-rib-state {
           type string;
         }
         leaf vpn-rib-state {
           type string;
         }
         leaf send-state {
           type string;
         }
         leaf stale-prefix-count {
           type int32;
           description
             "Number of prefixes marked as stale";
         }
         leaf llgr-stale-prefix-count {
           type int32;
           description
             "Number of prefixes marked as LLGR stale";
         }
         leaf advertised-prefix-count {
           type int32;
           description
             "Number of prefixes present in the RIB-OUT";
         }
       }
       container peer-inb-conv-info {
         leaf inb-conv-status {
           type string;
           description
             "State of inbound convergence";
         }
         leaf inb-conv-time {
           type string;
           description
             "Time taken for inbound convergence";
         }
         leaf inb-conv-wait-period {
           type uint32;
           description
             "Maximum wait time for inbound convergence";
         }
         leaf inb-conv-reason {
           type string;
           description
             "Reason of inbound convergence";
         }
         leaf nlri-waiting-eor {
           type string;
           description
             "NLRI that end-of-rib is expected but not received";
         }
         leaf inb-conv-abort-time {
           type string;
           description
             "Time pending for inbound convergence";
         }
       }
       list bgp-family-stat {
         key "nlri-type";
         leaf nlri-type {
           type string;
           description
             "Type of NLRI being limited";
         }
         leaf bgp-nlri-send-time {
           type int32;
           description
             "Time for initial send by peer";
         }
         leaf bgp-nlri-recv-time {
           type int32;
           description
             "Time for initial receive by peer";
         }
       }
       list entropy-label-info {
         key "nlri-type";
         leaf nlri-type {
           type string;
           description
             "Type of NLRI being limited";
         }
         leaf entropy-label {
           type string;
           description
             "Entropy label";
         }
         leaf entropy-label-import-policy {
           type string;
         }
         leaf entropy-label-no-next-hop-validation {
           type string;
           description
             "Entropy label no next hop validation";
         }
         leaf entropy-label-elc-v2-compatible {
           type string;
           description
             "Entropy label ELCv2 compatible";
         }
         leaf entropy-label-capability {
           type string;
           description
             "Local entropy label capability";
         }
         leaf entropy-label-stitching-capability {
           type string;
           description
             "Entropy label stitching capability";
         }
       }
       container bgp-malformed-attributes {
         container malformed-information {
           leaf log-interval {
             type int32;
           }
           leaf route-limit {
             type int32;
           }
         }
         container path-attribute {
           leaf name {
             type string;
           }
           leaf code {
             type int32;
           }
           leaf last-recv {
             type int32;
           }
           leaf total-recv {
             type int32;
           }
         }
       }
       leaf local-address {
         type jt:ipaddr;
       }
       leaf local-as {
         type int32;
         description
           "Local AS number";
       }
       leaf tcp-connect-port {
         type uint32;
         description
           "TCP port to connect to BGP peer";
       }
       leaf description {
         type string;
       }
       leaf notify-message {
         type string;
       }
       leaf notify-message-recv {
         type string;
       }
       leaf peer-group {
         type string;
         description
           "BGP peer-group peer belongs to";
       }
       leaf peer-cfg-rti {
         type string;
         description
           "Routing-instance peer is configured in";
       }
       leaf peer-fwd-rti {
         type string;
         description
           "Peer's forwarding-context routing-instance";
       }
       leaf dynamic-neighbor-template {
         type string;
         description
           "Dynamic-neighbor template peer brought up in";
       }
       leaf peer-type {
         type string;
       }
       leaf route-reflector-client {
         type empty;
       }
       leaf peer-flags {
         type string;
       }
       leaf rsync-flags {
         type string;
       }
       leaf peer-auto-discovery-type {
         type string;
       }
       leaf last-state {
         type string;
       }
       leaf last-event {
         type string;
       }
       leaf recv-ebgp-origin-validation-state {
         type string;
       }
       leaf last-error {
         type string;
       }
       leaf last-flap-event {
         type string;
       }
       leaf last-unreplicate-event {
         type string;
       }
       leaf peer-id {
         type jt:ipaddr;
       }
       leaf local-id {
         type jt:ipaddr;
       }
       leaf active-holdtime {
         type int32;
       }
       leaf keepalive-interval {
         type int32;
       }
       leaf group-index {
         type int32;
       }
       leaf peer-index {
         type int32;
       }
       leaf snmp-index {
         type uint32;
       }
       leaf bgp-alert {
         type string;
       }
       leaf bgp-link-bandwidth-autosense-holdtime {
         type uint32;
       }
       leaf bgp-link-bandwidth-autosense-timer {
         type string;
       }
       leaf local-interface-name {
         type string;
         description
           "Logical interface name";
       }
       leaf glb-path-monitor-ifindex {
         type uint32;
         description
           "GLB Path Monitor ifIndex";
       }
       leaf glb-path-monitor-local-node-id {
         type jt:ipaddr;
         description
           "GLB Path Monitor local node ID";
       }
       leaf glb-path-monitor-remote-node-id {
         type jt:ipaddr;
         description
           "GLB Path Monitor remote node ID";
       }
       leaf glb-profile-space {
         type string;
       }
       leaf peer-color {
         type string;
       }
       leaf-list extended-community {
         type string;
         description
           "Extended community";
       }
       leaf nlri-type-peer {
         type string;
       }
       leaf nlri-type-session {
         type string;
       }
       leaf loop-check-display {
         type string;
       }
       leaf peer-no-refresh {
         type empty;
         description
           "Present if this peer does not support refresh";
       }
       leaf peer-refresh-capability {
         type int32;
         description
           "Version of refresh capability supported by this peer";
       }
       leaf peer-4byte-as-capability-not-supported {
         type empty;
         description
           "This peer does not support 4 byte AS extension";
       }
       leaf peer-4byte-as-capability-advertised {
         type int32;
         description
           "4 byte Autonomous System capability advertised by this peer";
       }
       leaf peer-addpath-not-supported {
         type empty;
         description
           "This peer does not support addpath";
       }
       leaf peer-addpath-ronly-nlri {
         type string;
         description
           "Types of NLRI for which peer advertised recv capability";
       }
       leaf peer-addpath-sonly-nlri {
         type string;
         description
           "Types of NLRI for which peer advertised send capability";
       }
       leaf peer-addpath-rs-nlri {
         type string;
         description
           "Types of NLRI for which peer advertised send/recv cap";
       }
       leaf peer-addpath-send-negotiated-nlri {
         type string;
         description
           "NLRI for which Addpath 'send' is negotiated with peer";
       }
       leaf peer-addpath-send-not-negotiated-nlri {
         type string;
         description
           "NLRI for which Addpath 'send' is not negotiated with peer";
       }
       leaf peer-addpath-recv-negotiated-nlri {
         type string;
         description
           "NLRI for which Addpath 'receive' is negotiated with peer";
       }
       leaf peer-addpath-recv-not-negotiated-nlri {
         type string;
         description
           "NLRI for which Addpath 'receive' is not negotiated with peer";
       }
       leaf local-role-advertised {
         type string;
         description
           "BGP role configured locally";
       }
       leaf local-role-mode {
         type string;
         description
           "BGP local role mode";
       }
       leaf peer-remote-role-advertised {
         type string;
         description
           "BGP role is advertised from this peer";
       }
       leaf peer-delay-route-advertisements {
         type string;
       }
       leaf local-ext-nh-nlri {
         type string;
         description
           "Types of NLRI for which we advertised extend nh cap";
       }
       leaf peer-ext-nh-nlri {
         type string;
         description
           "Types of NLRI for which peer advertised extend nh cap";
       }
       leaf peer-dont-wait-eor {
         type string;
       }
       leaf peer-dont-send-eor {
         type string;
       }
       leaf peer-restart-nlri-configured {
         type string;
       }
       leaf peer-restart-time-configured {
         type string;
       }
       leaf peer-stale-route-time-configured {
         type string;
       }
       leaf peer-down-time-configured {
         type string;
       }
       leaf peer-no-restart {
         type empty;
         description
           "Present if this peer does not support graceful restart restarter
           mode";
       }
       leaf peer-restart-nlri-received {
         type string;
       }
       leaf peer-restart-time-received {
         type int32;
       }
       leaf peer-restart-flags-received {
         type string;
       }
       leaf peer-restart-nlri-can-save-state {
         type string;
       }
       leaf peer-restart-nlri-state-saved {
         type string;
       }
       leaf peer-restart-nlri-negotiated {
         type string;
       }
       leaf peer-end-of-rib-received {
         type string;
       }
       leaf peer-end-of-rib-sent {
         type string;
       }
       leaf peer-delay-end-of-rib {
         type string;
       }
       leaf peer-no-helper {
         type empty;
         description
           "Present if this peer does not support graceful restart receiver 
           mode";
       }
       leaf peer-restart-nlri-held {
         type string;
       }
       leaf peer-restart-remaining-time {
         type string;
       }
       leaf peer-stale-remaining-time {
         type string;
       }
       leaf peer-llgr-nlri-configured {
         type string;
       }
       leaf peer-no-llgr-restarter {
         type empty;
         description
           "Present if this peer does not support long-lived graceful 
           restart restarter mode";
       }
       leaf peer-llgr-nlri-restarter {
         type string;
       }
       leaf peer-llgr-nlri-state-saved {
         type string;
       }
       leaf peer-no-llgr-helper {
         type empty;
         description
           "Present if this peer does not support long-lived graceful 
           restart receiver mode";
       }
       leaf peer-llgr-ext-nlri-times-set {
         type string;
         description
           "NLRIs and extended-route-retention times set for this peer";
       }
       leaf peer-llgr-nlri-times {
         type string;
         description
           "NLRIs and times before long-lived stale routes are deleted";
       }
       leaf local-ext-nh-color-nlri {
         type string;
         description
           "Types of NLRI for which we enabled extended color nexthop 
           resolution";
       }
       leaf last-received {
         type int32;
       }
       leaf last-sent {
         type int32;
       }
       leaf last-checked {
         type int32;
       }
       leaf input-updates {
         type int32;
       }
       leaf input-refreshes {
         type int32;
       }
       leaf input-octets {
         type int32;
       }
       leaf output-updates {
         type int32;
       }
       leaf output-refreshes {
         type int32;
       }
       leaf output-octets {
         type int32;
       }
       leaf input-checksum {
         type int32;
       }
       leaf output-checksum {
         type int32;
       }
       leaf input-checksum-err {
         type int32;
       }
       leaf input-drop-path-attributes {
         type string;
       }
       leaf input-ignore-path-attributes {
         type string;
       }
       leaf input-wdraw-path-attributes {
         type string;
       }
       leaf buffered-octets-rx {
         type int32;
         description
           "Number of octets that have been received and are still buffered";
       }
       leaf buffered-octets-tx {
         type int32;
         description
           "Number of octets in the transmit buffer";
       }
       leaf gather-buffered-octets-tx {
         type int32;
         description
           "Number of octets in the gather transmit buffer";
       }
       leaf input-updates-dropped {
         type int32;
         description
           "Number of received update messages dropped";
       }
       container bgp-peer-iosession {
         leaf iosession-thread-name {
           type string;
         }
         leaf iosession-state {
           type string;
         }
       }
       container bgp-bfd {
         leaf bfd-configuration-state {
           type string;
           description
             "BFD configuration state";
         }
         leaf bfd-operational-state {
           type string;
           description
             "BFD operational state";
         }
         leaf strict-bfd-configured {
           type empty;
         }
         leaf peer-strict-bfd-received {
           type empty;
         }
         leaf bfd-up-wait-timer-due {
           type string;
           description
             "Time until bgp session is reset if bfd does not come up";
         }
       }
       container prefix-limit-dropped-count {
         leaf nlri-type {
           type string;
           description
             "Type of NLRI being limited";
         }
         leaf dropped-count {
           type int32;
           description
             "Per NLRI monotonously increasing count.";
         }
       }
       container prefix-limit-hidden-count {
         leaf nlri-type {
           type string;
           description
             "Type of NLRI being limited";
         }
         leaf hidden-count {
           type int32;
           description
             "Per NLRI monotonously increasing count.";
         }
       }
       list bgp-shard-output-queue {
         key "shard-rib-number";
         leaf shard-rib-number {
           type int32;
         }
         leaf shard-outq-count {
           type int32;
         }
         leaf shard-table-name {
           type string;
         }
         leaf shard-rib-adv-nlri {
           type string;
         }
         leaf thread-name {
           type string;
         }
       }
       container update-io-info {
         leaf uio-info {
           type string;
         }
         leaf peer-internal-state {
           type string;
         }
         leaf peer-up-ack-pending-shards {
           type string;
         }
         leaf uio-peer-up-ack {
           type string;
         }
         leaf uio-peer-close-sent {
           type string;
         }
         leaf uio-peer-close-done {
           type string;
         }
       }
       container uio-peer-bits {
         leaf uio-peer-bits-header {
           type string;
         }
         leaf uio-up-rcvd {
           type string;
         }
         leaf uio-down-rcvd {
           type string;
         }
         leaf uio-write-act-rcvd {
           type string;
         }
         leaf uio-write-deact-rcvd {
           type string;
         }
         leaf uio-nlri-type {
           type string;
         }
         leaf uio-eor-rcvd {
           type string;
         }
         leaf uio-cfg-seq {
           type int32;
         }
         leaf uio-peer-create-thr-id {
           type int32;
         }
       }
       container bgp-error {
         leaf name {
           type string;
         }
         leaf send-count {
           type int32;
         }
         leaf receive-count {
           type int32;
         }
       }
       container route-queue {
         leaf timer {
           type string;
         }
         leaf state {
           type string;
           description
             "HFRR profile Current state";
         }
         leaf element {
           type string;
         }
       }
       container tracing-information {
         leaf flags {
           type string;
           description
             "Enabled trace flags";
         }
         leaf filename {
           type string;
           description
             "Name of the trace file";
         }
         leaf filesize {
           type int32;
           description
             "Maximum size of the trace file";
         }
         leaf filelimit {
           type int32;
           description
             "Maximum number of retained trace files";
         }
       }
       container bgp-uio-traffic {
         leaf uio-last-sent {
           type int32;
         }
         leaf uio-input-messages {
           type int32;
         }
         leaf uio-input-octets {
           type int32;
         }
       }
     }
     container bgp-bmp-information {
       list bmp-station {
         key "bmp-station-name";
         leaf bmp-station-name {
           type string;
         }
         leaf bmp-station-state {
           type string;
         }
         leaf bmp-myaddr {
           type string;
         }
         leaf bmp-remoteaddr {
           type string;
         }
         leaf bmp-connect-time {
           type string;
         }
         leaf bmp-holddown-time {
           type string;
         }
         leaf bmp-state-more-info {
           type string;
         }
         leaf elapsed-time {
           type string;
           description
             "Time this adjacency or session has been up or down";
         }
         leaf in-memory-profiling {
           type string;
         }
         leaf bmp-skip-write-time {
           type string;
         }
         leaf bmp-skip-read-time {
           type string;
         }
         leaf bmp-version {
           type string;
         }
         leaf bmp-route-instance {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         leaf bgp-bmp-route-monitoring-ribout-prepolicy {
           type empty;
         }
         leaf bgp-bmp-route-monitoring-ribout-postpolicy {
           type empty;
         }
         leaf bgp-bmp-route-monitoring-loc-rib {
           type empty;
         }
         leaf bmp-treat-input-as-bmp {
           type string;
         }
         leaf bmp-server {
           type string;
         }
         leaf bmp-server-clients-cnt {
           type string;
         }
         leaf bmp-initiation-message {
           type string;
         }
         leaf bmp-memory-connect-timeout {
           type string;
         }
         leaf bmp-priority {
           type string;
         }
         leaf bmp-statistics-timeout {
           type string;
         }
         container bmp-addresses-ports {
           leaf bmp-local-address {
             type string;
           }
           leaf bmp-local-port {
             type string;
           }
           leaf bmp-station-address {
             type string;
           }
           leaf bmp-station-port {
             type string;
           }
           leaf bmp-connection-mode {
             type string;
           }
         }
         container bmp-authentication-with-key {
           leaf bmp-auth-key {
             type string;
           }
         }
         container bmp-authentication-with-key-chain {
           leaf bmp-auth-chain {
             type string;
           }
           leaf bmp-auth-alg {
             type string;
           }
         }
         container bmp-holddown {
           leaf bmp-holdtime {
             type string;
           }
           leaf bmp-holdtimeflaps {
             type string;
           }
           leaf bmp-holdtimeperiod {
             type string;
           }
         }
         container bmp-tcp-ka {
           leaf bmp-tcp-ka-idle-time {
             type string;
           }
           leaf bmp-tcp-ka-probe-count {
             type string;
           }
           leaf bmp-tcp-ka-probe-interval {
             type string;
           }
         }
         container tracing-information {
           leaf flags {
             type string;
             description
               "Enabled trace flags";
           }
           leaf filename {
             type string;
             description
               "Name of the trace file";
           }
           leaf filesize {
             type int32;
             description
               "Maximum size of the trace file";
           }
           leaf filelimit {
             type int32;
             description
               "Maximum number of retained trace files";
           }
         }
         container bmp-counter-info {
           leaf bmp-ctr-init-sent {
             type int32;
           }
           leaf bmp-ctr-term-sent {
             type int32;
           }
           leaf bmp-ctr-rm-sent {
             type int32;
           }
           leaf bmp-ctr-rm-add-sent {
             type int32;
           }
           leaf bmp-ctr-rm-del-sent {
             type int32;
           }
           leaf bmp-ctr-routes-sent {
             type int32;
           }
           leaf bmp-ctr-routes-add-sent {
             type int32;
           }
           leaf bmp-ctr-routes-del-sent {
             type int32;
           }
           leaf bmp-ctr-peer-down-sent {
             type int32;
           }
           leaf bmp-ctr-peer-up-sent {
             type int32;
           }
           leaf bmp-ctr-writes-done {
             type int32;
           }
           leaf bmp-ctr-writes-blocked {
             type int32;
           }
           leaf bmp-ctr-writes-full {
             type int32;
           }
           leaf bmp-ctr-writes-partial {
             type int32;
           }
           leaf bmp-ctr-writes-error {
             type int32;
           }
         }
         container bmp-kafka-info {
           leaf bmp-kafka-broker-address {
             type string;
           }
           leaf bmp-kafka-broker-status {
             type string;
           }
           leaf bmp-kafka-broker-elapsed-time {
             type string;
           }
         }
         container bmp-server-clients-info {
           leaf client-sys-name {
             type string;
           }
           leaf client-remote-address {
             type string;
           }
           leaf client-up-time {
             type string;
           }
         }
         container bmp-station-rib-in-pre-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-in-post-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         list bmp-station-rib-local-statistics {
           key "bmp-monitor-name";
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-out-pre-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
         container bmp-station-rib-out-post-statistics {
           leaf bmp-monitor-name {
             type string;
             description
               "BGP Monitoring type name";
           }
           leaf bmp-advertised-prefix-count {
             type int32;
             description
               "Total advertised prefix count";
           }
           leaf bmp-withdrawn-prefix-count {
             type int32;
             description
               "Total withdraw prefix count";
           }
         }
       }
     }
     leaf simple-int {
       type int32;
     }
   }
   grouping bgp-group-information-block {
     list bgp-group {
       key "name";
       description
         "Operational and configuration information for a BGP group";
       leaf type {
         type string;
       }
       leaf peer-as {
         type int32;
         description
           "Peer AS number";
       }
       leaf local-as {
         type int32;
         description
           "Local AS number";
       }
       leaf group-state {
         type string;
       }
       leaf name {
         type string;
       }
       leaf group-index {
         type int32;
       }
       leaf group-flags {
         type string;
       }
       leaf group-uio-count {
         type int32;
       }
       leaf group-uio-name {
         type string;
       }
       leaf orr {
         type string;
       }
       leaf orr-igp-primary {
         type string;
       }
       leaf orr-igp-backup {
         type string;
       }
       leaf orr-export {
         type string;
       }
       leaf peer-count {
         type int32;
         description
           "Total number of peers";
       }
       leaf established-count {
         type int32;
         description
           "Number of peers within the group that are in the established 
           state";
       }
       leaf-list peer-address {
         type jt:ipaddr;
       }
       leaf igp-protocol {
         type string;
       }
       leaf uio-group-info {
         type string;
       }
       leaf uio-tuple-dequeued {
         type int32;
       }
       leaf uio-last-sec-rtos-rcvd {
         type int32;
       }
       leaf uio-rto-churn-count {
         type int32;
       }
       leaf uio-cfg-seq {
         type int32;
       }
       leaf uio-dom-id {
         type int32;
       }
       leaf uio-inst-dynid {
         type int32;
       }
       leaf uio-fwd-inst-name {
         type string;
       }
       leaf uio-peer-close-count {
         type int32;
       }
       leaf uio-rtinfo-write-suspend-count {
         type int32;
       }
       leaf-list bgp-group.heading {
         type string;
         description
           "Operational and configuration information for a BGP group";
       }
       leaf bgp-options {
         type string;
       }
       leaf bgp-options2 {
         type string;
       }
       leaf bgp-options-extended {
         type string;
       }
       leaf bgp-options-extended2 {
         type string;
       }
       leaf remove-private-options {
         type string;
       }
       leaf flap-count {
         type int32;
         description
           "Number of times BGP sessions have gone down";
       }
       container unconfigured-peers {
         description
           "Set of address prefixes from which this group allows peering";
         list route-filter {
           key "address";
           description
             "Entries in martian table";
           leaf address {
             type jt:ipaddr;
           }
           leaf flags {
             type string;
             description
               "Enabled trace flags";
           }
           leaf extended-information {
             type string;
           }
           leaf match-count {
             type uint64;
           }
           container policy-extended-information {
             leaf account {
               type empty;
               description
                 "Account";
             }
             leaf accept {
               type empty;
               description
                 "Accept a route";
             }
             leaf advertise-locator {
               type empty;
               description
                 "Advertise SRv6 locator";
             }
             leaf advertise-locator-internal {
               type empty;
               description
                 "Advertise SRv6 locator internal";
             }
             leaf aggregate-bandwidth {
               type int32;
               description
                 "Aggregate bandwidth";
             }
             leaf auto-link-bandwidth {
               type empty;
               description
                 "Auto link bandwidth";
             }
             leaf push-label {
               type empty;
               description
                 "Push label";
             }
             leaf analyze {
               type empty;
               description
                 "Send to registered controllers for analysis";
             }
             leaf as-path-prepend {
               type uint32;
               description
                 "Prepend AS numbers to an AS path (BGP only)";
             }
             leaf as-path-replace {
               type string;
               description
                 "Replace AS numbers, or 'private' for an AS path (BGP only)";
             }
             leaf cos-next-hop-map {
               type string;
               description
                 "The CoS-based next-hop map in forwarding table";
             }
             leaf damping {
               type string;
               description
                 "Define BGP route flap damping parameters";
             }
             leaf default-action {
               type string;
               description
                 "The default policy action";
             }
             leaf destination-class {
               type string;
               description
                 "The destination class in forwarding table";
             }
             leaf dynamic-tunnel-attributes {
               type string;
               description
                 "The dynamic tunnel attributes used for forwarding";
             }
             leaf fib-install-priority {
               type string;
               description
                 "FIB install priority";
             }
             leaf filter {
               type string;
               description
                 "Next-hop firewall filter";
             }
             leaf get-route-range {
               type empty;
               description
                 "Get route range";
             }
             leaf ignore-service-label {
               type string;
               description
                 "Ignore service labels";
             }
             leaf install-to-fib {
               type string;
               description
                 "Install to FIB";
             }
             leaf ipv4-source-router-id {
               type empty;
             }
             leaf ipv4-source-router-id-address {
               type string;
               description
                 "IPV4 source router id address";
             }
             leaf ipv6-source-router-id {
               type empty;
             }
             leaf ipv6-source-router-id-address {
               type string;
               description
                 "IPV6 source router id address";
             }
             leaf label-allocation {
               type string;
               description
                 "Label allocation mode";
             }
             leaf label-allocation-fallback-reject {
               type string;
               description
                 "Suppress prefix export when label allocation fails";
             }
             leaf limit-bandwidth {
               type uint64;
               description
                 "Limit advertised aggregate outbound link bandwidth";
             }
             leaf load-balance {
               type string;
               description
                 "Load-balancing algorithm chosen";
             }
             leaf mhop-bfd-port {
               type uint32;
               description
                 "Use port number 4784 for MPLS-BFD as per RFC5884";
             }
             leaf multipath-resolve {
               type string;
               description
                 "Use all paths for resolution over this prefix";
             }
             leaf next {
               type string;
               description
                 "Skip to next policy or term";
             }
             leaf no-backup {
               type empty;
               description
                 "This prefix should not have backup";
             }
             leaf no-entropy-label-capability {
               type empty;
               description
                 "Don't advertise entropy label capability";
             }
             leaf no-route-localize {
               type empty;
               description
                 "No route localize";
             }
             leaf origin {
               type string;
               description
                 "BGP origin attribute";
             }
             leaf p2mp-lsp-root {
               type jt:ipaddr;
               description
                 "P2mp lsp root address";
             }
             leaf policy-priority {
               type string;
             }
             leaf reject {
               type empty;
               description
                 "Reject a route";
             }
             leaf request-long-lived-ack {
               type empty;
               description
                 "Advertise route after forwarding is programmed";
             }
             leaf resolution-map {
               type string;
               description
                 "Resolution map";
             }
             leaf resolution-map-mode {
               type string;
               description
                 "Resolution map modes";
             }
             leaf selected-mldp-egress {
               type string;
               description
                 "This node should act as egress node for MLDP inband 
                 signalling";
             }
             leaf send-withdrawal-on-route-change {
               type empty;
               description
                 "Withdrawn route as change is not ack'd from forwarding";
             }
             leaf set-down-bit {
               type empty;
               description
                 "Set down bit";
             }
             leaf slice {
               type string;
               description
                 "Slice name";
             }
             leaf source-class {
               type string;
               description
                 "The source class in forwarding table";
             }
             leaf sr-te-template {
               type string;
               description
                 "SR TE template to apply";
             }
             leaf ssm-source {
               type jt:ipaddr;
               description
                 "List of Sources for SSM mapping";
             }
             leaf trace {
               type empty;
               description
                 "Log matches to a trace file";
             }
             leaf tunnel-end-point-address {
               type string;
               description
                 "Set tunnel end-point address of tunnel";
             }
             leaf tunnel-termination-profile {
               type string;
               description
                 "Tunnel termination profile name";
             }
             leaf validation-state {
               type string;
               description
                 "Validation-state of a route";
             }
             container install-nexthop {
               description
                 "The next hop to be used for forwarding";
               container except {
                 leaf lsp {
                   type string;
                   description
                     "Label switched path name";
                 }
                 leaf lsp-regex {
                   type string;
                   description
                     "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf overlay-vxlan-interfaces {
                   type empty;
                 }
                 leaf macsec-interfaces {
                   type empty;
                 }
               }
               container fallback {
                 leaf lsp {
                   type string;
                   description
                     "Label switched path name";
                 }
                 leaf lsp-regex {
                   type string;
                   description
                     "Label switched path name regular expression";
                 }
                 leaf non-labelled-nexthop {
                   type empty;
                 }
                 leaf non-lsp-nexthop {
                   type empty;
                 }
                 leaf static-lsp {
                   type string;
                 }
                 leaf static-lsp-regex {
                   type string;
                 }
                 leaf overlay-vxlan-interfaces {
                   type empty;
                 }
                 leaf macsec-interfaces {
                   type empty;
                 }
               }
             }
             container map-to-interface {
               description
                 "Set output logical interface";
               list interface {
                 key "interface-name";
                 description
                   "Interface name or address";
                 leaf interface-name {
                   type string;
                   description
                     "Name of interface";
                 }
                 leaf interface-flags {
                   type string;
                 }
               }
             }
             container then-metric {
             }
             container prefix-segment {
               description
                 "The prefix segment attributes";
               container algorithm {
                 leaf prefix-segment-index-value {
                   type uint32;
                 }
                 leaf algorithm-name {
                   type uint32;
                 }
                 leaf node-segment {
                   type empty;
                 }
               }
             }
             list tunnel-attribute {
               description
                 "Tunnel attribute information";
               leaf tunnel-type {
                 type string;
                 description
                   "Tunnel type";
               }
               leaf reference-count {
                 type int32;
                 description
                   "Reference count";
               }
               leaf tunnel-data {
                 type string;
                 description
                   "Tunnel Data";
               }
             }
             container source-based-forwarding {
               container sbf-attributes {
                 leaf sbf-next-table {
                   type string;
                 }
               }
             }
             container policy-label {
             }
           }
         }
       }
       container route-queue {
         leaf timer {
           type string;
         }
         leaf state {
           type string;
           description
             "HFRR profile Current state";
         }
         leaf element {
           type string;
         }
       }
       list bgp-peer {
         key "peer-address";
         description
           "Operational and configuration information for a BGP peer";
         leaf-list bgp-peer.heading {
           type string;
           description
             "Operational and configuration information for a BGP peer";
         }
         leaf peer-address {
           type jt:ipaddr;
         }
         leaf peer-as {
           type int32;
           description
             "Peer AS number";
         }
         leaf input-messages {
           type int32;
         }
         leaf output-messages {
           type int32;
         }
         leaf route-queue-count {
           type int32;
           description
             "Total number of routes queued for output to this peer";
         }
         leaf flap-count {
           type int32;
           description
             "Number of times BGP sessions have gone down";
         }
         leaf elapsed-time {
           type string;
           description
             "Time this adjacency or session has been up or down";
         }
         leaf peer-state {
           type string;
         }
         leaf local-interface-index {
           type int32;
           description
             "SNMP ifIndex of local interface";
         }
         leaf peer-end-of-rib-scheduled {
           type string;
         }
         leaf extended-information {
           type string;
         }
         container bgp-option-information {
           leaf bgp-nlri-send-time {
             type int32;
             description
               "Time for initial send by peer";
           }
           list nlri-policy {
             key "nlri-type";
             leaf nlri-type {
               type string;
               description
                 "Type of NLRI being limited";
             }
             leaf nlri-export-policy {
               type string;
             }
             leaf nlri-import-policy {
               type string;
             }
           }
           container nlri-send-community {
             leaf nlri-type {
               type string;
               description
                 "Type of NLRI being limited";
             }
             leaf nlri-send-community-type {
               type string;
             }
           }
           container addpath-send {
             leaf nlri-type {
               type string;
               description
                 "Type of NLRI being limited";
             }
             leaf addpath-send-type {
               type string;
             }
             leaf addpath-send-count {
               type int32;
             }
             leaf addpath-send-policy {
               type string;
             }
           }
           container addpath-receive {
             leaf nlri-type {
               type string;
               description
                 "Type of NLRI being limited";
             }
             leaf addpath-receive-type {
               type string;
             }
           }
           container nlri-information {
             leaf nlri-type {
               type string;
               description
                 "Type of NLRI being limited";
             }
             leaf nlri-flow-novalidate {
               type string;
               description
                 "Policy to accept flow routes without validation";
             }
             leaf nlri-output-queue-priority {
               type string;
               description
                 "Default address family output queue priority";
             }
             leaf nlri-route-refresh-priority {
               type string;
               description
                 "Default address family route-refresh priority";
             }
             leaf nlri-withdraw-priority {
               type string;
               description
                 "Default address family withdraw priority";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-rtage-refl-upd-msgs {
                 type empty;
               }
               leaf bgp-nlri-flag-no-resolution {
                 type empty;
               }
               leaf bgp-nlri-flag-resolve-preserve-hier {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-accept-local-addr-pnh {
                 type empty;
               }
               leaf bgp-nlri-flag-accept-own {
                 type empty;
               }
               leaf bgp-nlri-flag-strip-nexthop {
                 type empty;
               }
               leaf bgp-nlri-flag-allow-po-add-nexthop {
                 type empty;
               }
               leaf bgp-nlri-flag-per-nexthop-label {
                 type empty;
               }
             }
             container nlri-traffic-stats {
               leaf traffic-stats-interval {
                 type int32;
               }
               container tracing-information {
                 leaf flags {
                   type string;
                   description
                     "Enabled trace flags";
                 }
                 leaf filename {
                   type string;
                   description
                     "Name of the trace file";
                 }
                 leaf filesize {
                   type int32;
                   description
                     "Maximum size of the trace file";
                 }
                 leaf filelimit {
                   type int32;
                   description
                     "Maximum number of retained trace files";
                 }
               }
             }
             container output-queues {
               description
                 "BGP output queues statistics";
               leaf time-series {
                 type string;
               }
               list class {
                 description
                   "An instance of BGP output queue statistics";
                 leaf priority-type {
                   type string;
                   description
                     "BGP output queue priority type";
                 }
                 leaf rank {
                   type int32;
                   description
                     "BGP output queue rank for priority type";
                 }
                 leaf token-count {
                   type int32;
                   description
                     "BGP output queue token count for priority";
                 }
                 leaf output-queue-route-count {
                   type int32;
                   description
                     "BGP output queue route count for priority";
                 }
               }
             }
           }
           leaf export-policy {
             type string;
           }
           leaf import-policy {
             type string;
           }
           leaf send-community-type {
             type string;
           }
           leaf advertise-bgp-static-policy {
             type string;
           }
           leaf bgp-options {
             type string;
           }
           leaf bgp-options2 {
             type string;
           }
           leaf bgp-options-extended {
             type string;
           }
           leaf bgp-options-extended2 {
             type string;
           }
           leaf remove-private-options {
             type string;
           }
           leaf authentication-key {
             type string;
           }
           leaf authentication-key-chain {
             type string;
             description
               "Name of authentication key chain";
           }
           leaf authentication-algorithm {
             type string;
             description
               "Name of authentication algorithm";
           }
           leaf authentication-configured {
             type empty;
           }
           leaf gshut-recv-local-preference {
             type uint32;
           }
           leaf gshut-send-local-preference {
             type uint32;
           }
           leaf address-families {
             type string;
           }
           leaf ignore-path-attributes {
             type string;
           }
           leaf local-address {
             type jt:ipaddr;
           }
           leaf holdtime {
             type int32;
             description
               "Delay before timing out the adjacency (default is 180 
               seconds)";
           }
           leaf metric-out {
             type int32;
           }
           leaf preference {
             type int32;
             description
               "Preference for the route";
           }
           leaf local-preference {
             type int32;
           }
           leaf local-as {
             type int32;
             description
               "Local AS number";
           }
           leaf local-as-private {
             type empty;
           }
           leaf local-system-as {
             type int32;
           }
           leaf receive-buffer-size {
             type int32;
           }
           leaf send-buffer-size {
             type int32;
           }
           leaf outbound-timer {
             type int32;
           }
           leaf med-action {
             type string;
           }
           leaf ipsec-sa {
             type string;
           }
           leaf bgp-bmp-monitor-peers {
             type string;
           }
           leaf bgp-bmp-route-monitoring-none {
             type empty;
           }
           leaf bgp-bmp-route-monitoring-prepolicy {
             type empty;
           }
           leaf bgp-bmp-prepolicy-exclude-non-feasible {
             type empty;
           }
           leaf bgp-bmp-route-monitoring-postpolicy {
             type empty;
           }
           leaf bgp-bmp-postpolicy-exclude-non-eligible {
             type empty;
           }
           leaf bgp-bmp-route-monitoring-ribout-prepolicy {
             type empty;
           }
           leaf bgp-bmp-route-monitoring-ribout-postpolicy {
             type empty;
           }
           container drop-path-attr-info {
             leaf drop-path-attributes {
               type string;
             }
             leaf drop-path-attributes-uot {
               type string;
             }
           }
           container wdraw-path-attr-info {
             leaf wdraw-path-attributes {
               type string;
             }
             leaf wdraw-path-attributes-uot {
               type string;
             }
           }
           container prefix-limit {
             leaf nlri-type {
               type string;
               description
                 "Type of NLRI being limited";
             }
             leaf prefix-count {
               type int32;
               description
                 "Number of prefixes accepted before action is taken";
             }
             leaf limit-action {
               type string;
               description
                 "Action taken upon reaching limit";
             }
             leaf warning-percentage {
               type int32;
               description
                 "Percentage of limit at which to log a warning";
             }
           }
           container accepted-prefix-limit {
             description
               "Limit number of prefixes accepted by policy";
             leaf nlri-type {
               type string;
               description
                 "Type of NLRI being limited";
             }
             leaf prefix-count {
               type int32;
               description
                 "Number of prefixes accepted before action is taken";
             }
             leaf limit-action {
               type string;
               description
                 "Action taken upon reaching limit";
             }
             leaf warning-percentage {
               type int32;
               description
                 "Percentage of limit at which to log a warning";
             }
           }
           container aigp-mode {
             leaf nlri-type {
               type string;
               description
                 "Type of NLRI being limited";
             }
           }
           container family-damping-info {
             leaf nlri-type {
               type string;
               description
                 "Type of NLRI being limited";
             }
           }
           container protection {
             leaf nlri-type {
               type string;
               description
                 "Type of NLRI being limited";
             }
           }
         }
         container egress-protection {
           container nlri-egress-protection {
             leaf nlri-type {
               type string;
               description
                 "Type of NLRI being limited";
             }
             leaf bgp-context-id {
               type jt:ipaddr;
             }
             leaf bgp-import-policy {
               type string;
             }
           }
           list ep-backup-table {
             leaf-list ep-backup-rib-name {
               type string;
               description
                 "Instance backup RIB";
             }
             leaf ep-backup-link {
               type string;
               description
                 "Vt interface";
             }
             leaf ep-backup-rib-id {
               type int32;
               description
                 "RIB Identifier";
             }
             leaf ep-backup-kern-id {
               type int32;
               description
                 "FIB Identifier";
             }
             leaf ep-backup-table-nh {
               type string;
               description
                 "Enhanced table nexthop";
             }
             leaf-list ep-instance-route-targets {
               type string;
               description
                 "Instance route targets";
             }
             leaf ep-backup-instance {
               type string;
             }
             leaf ep-backup-context {
               type string;
               description
                 "Instance backup context";
             }
           }
           list ep-instance-table {
             leaf ep-instance-name {
               type string;
             }
             leaf ep-instance-type {
               type string;
               description
                 "Instance type";
             }
             leaf ep-instance-protection-type {
               type string;
               description
                 "Instance request protected";
             }
             leaf ep-instance-context-id {
               type jt:ipaddr;
               description
                 "Context-id";
             }
             leaf-list ep-backup-rib-name {
               type string;
               description
                 "Instance backup RIB";
             }
           }
           leaf nlri-type {
             type string;
             description
               "Type of NLRI being limited";
           }
         }
         list bgp-output-queue {
           key "number";
           leaf number {
             type int32;
           }
           leaf count {
             type int32;
           }
           leaf table-name {
             type string;
             description
               "Unicast routing table";
           }
           leaf rib-adv-nlri {
             type string;
           }
           leaf time-series {
             type string;
           }
           list class {
             description
               "An instance of BGP output queue statistics";
             leaf priority-type {
               type string;
               description
                 "BGP output queue priority type";
             }
             leaf rank {
               type int32;
               description
                 "BGP output queue rank for priority type";
             }
             leaf token-count {
               type int32;
               description
                 "BGP output queue token count for priority";
             }
           }
         }
         list bgp-rib {
           key "name";
           leaf name {
             type string;
           }
           leaf total-prefix-count {
             type int32;
             description
               "Total number of prefixes in this RIB";
           }
           leaf active-prefix-count {
             type int32;
             description
               "Number of active prefixes";
           }
           leaf suppressed-prefix-count {
             type int32;
             description
               "Number of prefixes suppressed due to damping";
           }
           leaf history-prefix-count {
             type int32;
             description
               "Number of prefixes with damping history maintained";
           }
           leaf damped-prefix-count {
             type int32;
             description
               "Number of prefixes in any damped state";
           }
           leaf pending-prefix-count {
             type int32;
             description
               "Number of prefixes with pending changes";
           }
           leaf received-prefix-count {
             type int32;
             description
               "For a peer RIB, number of prefixes received from this peer";
           }
           leaf accepted-prefix-count {
             type int32;
             description
               "For a peer RIB, number of prefixes from this peer accepted 
               by policy";
           }
           leaf active-external-prefix-count {
             type int32;
             description
               "Number of active prefixes received from external peers";
           }
           leaf total-external-prefix-count {
             type int32;
             description
               "Total number of prefixes received from external peers";
           }
           leaf accepted-external-prefix-count {
             type int32;
             description
               "Number of accepted prefixes received from external peers";
           }
           leaf suppressed-external-prefix-count {
             type int32;
             description
               "Number of external prefixes suppressed due to damping";
           }
           leaf active-internal-prefix-count {
             type int32;
             description
               "Number of active prefixes received from internal peers";
           }
           leaf total-internal-prefix-count {
             type int32;
             description
               "Total number of prefixes received from internal peers";
           }
           leaf accepted-internal-prefix-count {
             type int32;
             description
               "Number of accepted prefixes received from internal peers";
           }
           leaf suppressed-internal-prefix-count {
             type int32;
             description
               "Number of internal prefixes suppressed due to damping";
           }
           leaf rib-bit {
             type string;
           }
           leaf bgp-rib-state {
             type string;
           }
           leaf vpn-rib-state {
             type string;
           }
           leaf send-state {
             type string;
           }
           leaf stale-prefix-count {
             type int32;
             description
               "Number of prefixes marked as stale";
           }
           leaf llgr-stale-prefix-count {
             type int32;
             description
               "Number of prefixes marked as LLGR stale";
           }
           leaf advertised-prefix-count {
             type int32;
             description
               "Number of prefixes present in the RIB-OUT";
           }
         }
         container peer-inb-conv-info {
           leaf inb-conv-status {
             type string;
             description
               "State of inbound convergence";
           }
           leaf inb-conv-time {
             type string;
             description
               "Time taken for inbound convergence";
           }
           leaf inb-conv-wait-period {
             type uint32;
             description
               "Maximum wait time for inbound convergence";
           }
           leaf inb-conv-reason {
             type string;
             description
               "Reason of inbound convergence";
           }
           leaf nlri-waiting-eor {
             type string;
             description
               "NLRI that end-of-rib is expected but not received";
           }
           leaf inb-conv-abort-time {
             type string;
             description
               "Time pending for inbound convergence";
           }
         }
         list bgp-family-stat {
           key "nlri-type";
           leaf nlri-type {
             type string;
             description
               "Type of NLRI being limited";
           }
           leaf bgp-nlri-send-time {
             type int32;
             description
               "Time for initial send by peer";
           }
           leaf bgp-nlri-recv-time {
             type int32;
             description
               "Time for initial receive by peer";
           }
         }
         list entropy-label-info {
           key "nlri-type";
           leaf nlri-type {
             type string;
             description
               "Type of NLRI being limited";
           }
           leaf entropy-label {
             type string;
             description
               "Entropy label";
           }
           leaf entropy-label-import-policy {
             type string;
           }
           leaf entropy-label-no-next-hop-validation {
             type string;
             description
               "Entropy label no next hop validation";
           }
           leaf entropy-label-elc-v2-compatible {
             type string;
             description
               "Entropy label ELCv2 compatible";
           }
           leaf entropy-label-capability {
             type string;
             description
               "Local entropy label capability";
           }
           leaf entropy-label-stitching-capability {
             type string;
             description
               "Entropy label stitching capability";
           }
         }
         container bgp-malformed-attributes {
           container malformed-information {
             leaf log-interval {
               type int32;
             }
             leaf route-limit {
               type int32;
             }
           }
           container path-attribute {
             leaf name {
               type string;
             }
             leaf code {
               type int32;
             }
             leaf last-recv {
               type int32;
             }
             leaf total-recv {
               type int32;
             }
           }
         }
         leaf local-address {
           type jt:ipaddr;
         }
         leaf local-as {
           type int32;
           description
             "Local AS number";
         }
         leaf tcp-connect-port {
           type uint32;
           description
             "TCP port to connect to BGP peer";
         }
         leaf description {
           type string;
         }
         leaf notify-message {
           type string;
         }
         leaf notify-message-recv {
           type string;
         }
         leaf peer-group {
           type string;
           description
             "BGP peer-group peer belongs to";
         }
         leaf peer-cfg-rti {
           type string;
           description
             "Routing-instance peer is configured in";
         }
         leaf peer-fwd-rti {
           type string;
           description
             "Peer's forwarding-context routing-instance";
         }
         leaf dynamic-neighbor-template {
           type string;
           description
             "Dynamic-neighbor template peer brought up in";
         }
         leaf peer-type {
           type string;
         }
         leaf route-reflector-client {
           type empty;
         }
         leaf peer-flags {
           type string;
         }
         leaf rsync-flags {
           type string;
         }
         leaf peer-auto-discovery-type {
           type string;
         }
         leaf last-state {
           type string;
         }
         leaf last-event {
           type string;
         }
         leaf recv-ebgp-origin-validation-state {
           type string;
         }
         leaf last-error {
           type string;
         }
         leaf last-flap-event {
           type string;
         }
         leaf last-unreplicate-event {
           type string;
         }
         leaf peer-id {
           type jt:ipaddr;
         }
         leaf local-id {
           type jt:ipaddr;
         }
         leaf active-holdtime {
           type int32;
         }
         leaf keepalive-interval {
           type int32;
         }
         leaf group-index {
           type int32;
         }
         leaf peer-index {
           type int32;
         }
         leaf snmp-index {
           type uint32;
         }
         leaf bgp-alert {
           type string;
         }
         leaf bgp-link-bandwidth-autosense-holdtime {
           type uint32;
         }
         leaf bgp-link-bandwidth-autosense-timer {
           type string;
         }
         leaf local-interface-name {
           type string;
           description
             "Logical interface name";
         }
         leaf glb-path-monitor-ifindex {
           type uint32;
           description
             "GLB Path Monitor ifIndex";
         }
         leaf glb-path-monitor-local-node-id {
           type jt:ipaddr;
           description
             "GLB Path Monitor local node ID";
         }
         leaf glb-path-monitor-remote-node-id {
           type jt:ipaddr;
           description
             "GLB Path Monitor remote node ID";
         }
         leaf glb-profile-space {
           type string;
         }
         leaf peer-color {
           type string;
         }
         leaf-list extended-community {
           type string;
           description
             "Extended community";
         }
         leaf nlri-type-peer {
           type string;
         }
         leaf nlri-type-session {
           type string;
         }
         leaf loop-check-display {
           type string;
         }
         leaf peer-no-refresh {
           type empty;
           description
             "Present if this peer does not support refresh";
         }
         leaf peer-refresh-capability {
           type int32;
           description
             "Version of refresh capability supported by this peer";
         }
         leaf peer-4byte-as-capability-not-supported {
           type empty;
           description
             "This peer does not support 4 byte AS extension";
         }
         leaf peer-4byte-as-capability-advertised {
           type int32;
           description
             "4 byte Autonomous System capability advertised by this peer";
         }
         leaf peer-addpath-not-supported {
           type empty;
           description
             "This peer does not support addpath";
         }
         leaf peer-addpath-ronly-nlri {
           type string;
           description
             "Types of NLRI for which peer advertised recv capability";
         }
         leaf peer-addpath-sonly-nlri {
           type string;
           description
             "Types of NLRI for which peer advertised send capability";
         }
         leaf peer-addpath-rs-nlri {
           type string;
           description
             "Types of NLRI for which peer advertised send/recv cap";
         }
         leaf peer-addpath-send-negotiated-nlri {
           type string;
           description
             "NLRI for which Addpath 'send' is negotiated with peer";
         }
         leaf peer-addpath-send-not-negotiated-nlri {
           type string;
           description
             "NLRI for which Addpath 'send' is not negotiated with peer";
         }
         leaf peer-addpath-recv-negotiated-nlri {
           type string;
           description
             "NLRI for which Addpath 'receive' is negotiated with peer";
         }
         leaf peer-addpath-recv-not-negotiated-nlri {
           type string;
           description
             "NLRI for which Addpath 'receive' is not negotiated with peer";
         }
         leaf local-role-advertised {
           type string;
           description
             "BGP role configured locally";
         }
         leaf local-role-mode {
           type string;
           description
             "BGP local role mode";
         }
         leaf peer-remote-role-advertised {
           type string;
           description
             "BGP role is advertised from this peer";
         }
         leaf peer-delay-route-advertisements {
           type string;
         }
         leaf local-ext-nh-nlri {
           type string;
           description
             "Types of NLRI for which we advertised extend nh cap";
         }
         leaf peer-ext-nh-nlri {
           type string;
           description
             "Types of NLRI for which peer advertised extend nh cap";
         }
         leaf peer-dont-wait-eor {
           type string;
         }
         leaf peer-dont-send-eor {
           type string;
         }
         leaf peer-restart-nlri-configured {
           type string;
         }
         leaf peer-restart-time-configured {
           type string;
         }
         leaf peer-stale-route-time-configured {
           type string;
         }
         leaf peer-down-time-configured {
           type string;
         }
         leaf peer-no-restart {
           type empty;
           description
             "Present if this peer does not support graceful restart 
             restarter mode";
         }
         leaf peer-restart-nlri-received {
           type string;
         }
         leaf peer-restart-time-received {
           type int32;
         }
         leaf peer-restart-flags-received {
           type string;
         }
         leaf peer-restart-nlri-can-save-state {
           type string;
         }
         leaf peer-restart-nlri-state-saved {
           type string;
         }
         leaf peer-restart-nlri-negotiated {
           type string;
         }
         leaf peer-end-of-rib-received {
           type string;
         }
         leaf peer-end-of-rib-sent {
           type string;
         }
         leaf peer-delay-end-of-rib {
           type string;
         }
         leaf peer-no-helper {
           type empty;
           description
             "Present if this peer does not support graceful restart 
             receiver mode";
         }
         leaf peer-restart-nlri-held {
           type string;
         }
         leaf peer-restart-remaining-time {
           type string;
         }
         leaf peer-stale-remaining-time {
           type string;
         }
         leaf peer-llgr-nlri-configured {
           type string;
         }
         leaf peer-no-llgr-restarter {
           type empty;
           description
             "Present if this peer does not support long-lived graceful 
             restart restarter mode";
         }
         leaf peer-llgr-nlri-restarter {
           type string;
         }
         leaf peer-llgr-nlri-state-saved {
           type string;
         }
         leaf peer-no-llgr-helper {
           type empty;
           description
             "Present if this peer does not support long-lived graceful 
             restart receiver mode";
         }
         leaf peer-llgr-ext-nlri-times-set {
           type string;
           description
             "NLRIs and extended-route-retention times set for this peer";
         }
         leaf peer-llgr-nlri-times {
           type string;
           description
             "NLRIs and times before long-lived stale routes are deleted";
         }
         leaf local-ext-nh-color-nlri {
           type string;
           description
             "Types of NLRI for which we enabled extended color nexthop 
             resolution";
         }
         leaf last-received {
           type int32;
         }
         leaf last-sent {
           type int32;
         }
         leaf last-checked {
           type int32;
         }
         leaf input-updates {
           type int32;
         }
         leaf input-refreshes {
           type int32;
         }
         leaf input-octets {
           type int32;
         }
         leaf output-updates {
           type int32;
         }
         leaf output-refreshes {
           type int32;
         }
         leaf output-octets {
           type int32;
         }
         leaf input-checksum {
           type int32;
         }
         leaf output-checksum {
           type int32;
         }
         leaf input-checksum-err {
           type int32;
         }
         leaf input-drop-path-attributes {
           type string;
         }
         leaf input-ignore-path-attributes {
           type string;
         }
         leaf input-wdraw-path-attributes {
           type string;
         }
         leaf buffered-octets-rx {
           type int32;
           description
             "Number of octets that have been received and are still 
             buffered";
         }
         leaf buffered-octets-tx {
           type int32;
           description
             "Number of octets in the transmit buffer";
         }
         leaf gather-buffered-octets-tx {
           type int32;
           description
             "Number of octets in the gather transmit buffer";
         }
         leaf input-updates-dropped {
           type int32;
           description
             "Number of received update messages dropped";
         }
         container bgp-peer-iosession {
           leaf iosession-thread-name {
             type string;
           }
           leaf iosession-state {
             type string;
           }
         }
         container bgp-bfd {
           leaf bfd-configuration-state {
             type string;
             description
               "BFD configuration state";
           }
           leaf bfd-operational-state {
             type string;
             description
               "BFD operational state";
           }
           leaf strict-bfd-configured {
             type empty;
           }
           leaf peer-strict-bfd-received {
             type empty;
           }
           leaf bfd-up-wait-timer-due {
             type string;
             description
               "Time until bgp session is reset if bfd does not come up";
           }
         }
         container prefix-limit-dropped-count {
           leaf nlri-type {
             type string;
             description
               "Type of NLRI being limited";
           }
           leaf dropped-count {
             type int32;
             description
               "Per NLRI monotonously increasing count.";
           }
         }
         container prefix-limit-hidden-count {
           leaf nlri-type {
             type string;
             description
               "Type of NLRI being limited";
           }
           leaf hidden-count {
             type int32;
             description
               "Per NLRI monotonously increasing count.";
           }
         }
         list bgp-shard-output-queue {
           key "shard-rib-number";
           leaf shard-rib-number {
             type int32;
           }
           leaf shard-outq-count {
             type int32;
           }
           leaf shard-table-name {
             type string;
           }
           leaf shard-rib-adv-nlri {
             type string;
           }
           leaf thread-name {
             type string;
           }
         }
         container update-io-info {
           leaf uio-info {
             type string;
           }
           leaf peer-internal-state {
             type string;
           }
           leaf peer-up-ack-pending-shards {
             type string;
           }
           leaf uio-peer-up-ack {
             type string;
           }
           leaf uio-peer-close-sent {
             type string;
           }
           leaf uio-peer-close-done {
             type string;
           }
         }
         container uio-peer-bits {
           leaf uio-peer-bits-header {
             type string;
           }
           leaf uio-up-rcvd {
             type string;
           }
           leaf uio-down-rcvd {
             type string;
           }
           leaf uio-write-act-rcvd {
             type string;
           }
           leaf uio-write-deact-rcvd {
             type string;
           }
           leaf uio-nlri-type {
             type string;
           }
           leaf uio-eor-rcvd {
             type string;
           }
           leaf uio-cfg-seq {
             type int32;
           }
           leaf uio-peer-create-thr-id {
             type int32;
           }
         }
         container bgp-error {
           leaf name {
             type string;
           }
           leaf send-count {
             type int32;
           }
           leaf receive-count {
             type int32;
           }
         }
         container route-queue {
           leaf timer {
             type string;
           }
           leaf state {
             type string;
             description
               "HFRR profile Current state";
           }
           leaf element {
             type string;
           }
         }
         container tracing-information {
           leaf flags {
             type string;
             description
               "Enabled trace flags";
           }
           leaf filename {
             type string;
             description
               "Name of the trace file";
           }
           leaf filesize {
             type int32;
             description
               "Maximum size of the trace file";
           }
           leaf filelimit {
             type int32;
             description
               "Maximum number of retained trace files";
           }
         }
         container bgp-uio-traffic {
           leaf uio-last-sent {
             type int32;
           }
           leaf uio-input-messages {
             type int32;
           }
           leaf uio-input-octets {
             type int32;
           }
         }
       }
       container bgp-option-information {
         leaf export-policy {
           type string;
         }
         leaf import-policy {
           type string;
         }
         leaf send-community-type {
           type string;
         }
         leaf advertise-bgp-static-policy {
           type string;
         }
         leaf bgp-options {
           type string;
         }
         leaf bgp-options2 {
           type string;
         }
         leaf bgp-options-extended {
           type string;
         }
         leaf bgp-options-extended2 {
           type string;
         }
         leaf remove-private-options {
           type string;
         }
         leaf authentication-key {
           type string;
         }
         leaf authentication-key-chain {
           type string;
           description
             "Name of authentication key chain";
         }
         leaf authentication-algorithm {
           type string;
           description
             "Name of authentication algorithm";
         }
         leaf authentication-configured {
           type empty;
         }
         leaf gshut-recv-local-preference {
           type uint32;
         }
         leaf gshut-send-local-preference {
           type uint32;
         }
         leaf address-families {
           type string;
         }
         leaf ignore-path-attributes {
           type string;
         }
         leaf local-address {
           type jt:ipaddr;
         }
         leaf holdtime {
           type int32;
           description
             "Delay before timing out the adjacency (default is 180 seconds)";
         }
         leaf metric-out {
           type int32;
         }
         leaf preference {
           type int32;
           description
             "Preference for the route";
         }
         leaf local-preference {
           type int32;
         }
         leaf local-as {
           type int32;
           description
             "Local AS number";
         }
         leaf local-as-private {
           type empty;
         }
         leaf local-system-as {
           type int32;
         }
         leaf receive-buffer-size {
           type int32;
         }
         leaf send-buffer-size {
           type int32;
         }
         leaf outbound-timer {
           type int32;
         }
         leaf med-action {
           type string;
         }
         leaf ipsec-sa {
           type string;
         }
         leaf bgp-bmp-monitor-peers {
           type string;
         }
         leaf bgp-bmp-route-monitoring-none {
           type empty;
         }
         leaf bgp-bmp-route-monitoring-prepolicy {
           type empty;
         }
         leaf bgp-bmp-prepolicy-exclude-non-feasible {
           type empty;
         }
         leaf bgp-bmp-route-monitoring-postpolicy {
           type empty;
         }
         leaf bgp-bmp-postpolicy-exclude-non-eligible {
           type empty;
         }
         leaf bgp-bmp-route-monitoring-ribout-prepolicy {
           type empty;
         }
         leaf bgp-bmp-route-monitoring-ribout-postpolicy {
           type empty;
         }
         leaf bgp-nlri-send-time {
           type int32;
           description
             "Time for initial send by peer";
         }
         list nlri-policy {
           key "nlri-type";
           leaf nlri-type {
             type string;
             description
               "Type of NLRI being limited";
           }
           leaf nlri-export-policy {
             type string;
           }
           leaf nlri-import-policy {
             type string;
           }
         }
         container nlri-send-community {
           leaf nlri-type {
             type string;
             description
               "Type of NLRI being limited";
           }
           leaf nlri-send-community-type {
             type string;
           }
         }
         container drop-path-attr-info {
           leaf drop-path-attributes {
             type string;
           }
           leaf drop-path-attributes-uot {
             type string;
           }
         }
         container wdraw-path-attr-info {
           leaf wdraw-path-attributes {
             type string;
           }
           leaf wdraw-path-attributes-uot {
             type string;
           }
         }
         container addpath-send {
           leaf nlri-type {
             type string;
             description
               "Type of NLRI being limited";
           }
           leaf addpath-send-type {
             type string;
           }
           leaf addpath-send-count {
             type int32;
           }
           leaf addpath-send-policy {
             type string;
           }
         }
         container addpath-receive {
           leaf nlri-type {
             type string;
             description
               "Type of NLRI being limited";
           }
           leaf addpath-receive-type {
             type string;
           }
         }
         container nlri-information {
           leaf nlri-type {
             type string;
             description
               "Type of NLRI being limited";
           }
           leaf nlri-flow-novalidate {
             type string;
             description
               "Policy to accept flow routes without validation";
           }
           leaf nlri-output-queue-priority {
             type string;
             description
               "Default address family output queue priority";
           }
           leaf nlri-route-refresh-priority {
             type string;
             description
               "Default address family route-refresh priority";
           }
           leaf nlri-withdraw-priority {
             type string;
             description
               "Default address family withdraw priority";
           }
           container nlri-flags {
             leaf bgp-nlri-flag-explicit-null-for-all-routes {
               type empty;
             }
             leaf bgp-nlri-flag-explicit-null-for-connected-routes {
               type empty;
             }
             leaf bgp-nlri-flag-aggregate-label {
               type empty;
             }
             leaf bgp-nlri-flag-per-prefix-label {
               type empty;
             }
             leaf bgp-nlri-flag-per-group-label {
               type empty;
             }
             leaf bgp-nlri-flag-no-install-forwarding {
               type empty;
             }
             leaf bgp-nlri-flag-rtage-refl-upd-msgs {
               type empty;
             }
             leaf bgp-nlri-flag-no-resolution {
               type empty;
             }
             leaf bgp-nlri-flag-resolve-preserve-hier {
               type empty;
             }
             leaf bgp-nlri-flag-delay-route-advt {
               type empty;
             }
             leaf bgp-nlri-flag-traffic-stats {
               type empty;
             }
             leaf bgp-nlri-flag-l2vpn-status-vector {
               type empty;
             }
             leaf bgp-nlri-flag-no-l2vpn-status-vector {
               type empty;
             }
             leaf bgp-nlri-flag-accept-local-addr-pnh {
               type empty;
             }
             leaf bgp-nlri-flag-accept-own {
               type empty;
             }
             leaf bgp-nlri-flag-strip-nexthop {
               type empty;
             }
             leaf bgp-nlri-flag-allow-po-add-nexthop {
               type empty;
             }
             leaf bgp-nlri-flag-per-nexthop-label {
               type empty;
             }
           }
           container nlri-traffic-stats {
             leaf traffic-stats-interval {
               type int32;
             }
             container tracing-information {
               leaf flags {
                 type string;
                 description
                   "Enabled trace flags";
               }
               leaf filename {
                 type string;
                 description
                   "Name of the trace file";
               }
               leaf filesize {
                 type int32;
                 description
                   "Maximum size of the trace file";
               }
               leaf filelimit {
                 type int32;
                 description
                   "Maximum number of retained trace files";
               }
             }
           }
           container output-queues {
             description
               "BGP output queues statistics";
             leaf time-series {
               type string;
             }
             list class {
               description
                 "An instance of BGP output queue statistics";
               leaf priority-type {
                 type string;
                 description
                   "BGP output queue priority type";
               }
               leaf rank {
                 type int32;
                 description
                   "BGP output queue rank for priority type";
               }
               leaf token-count {
                 type int32;
                 description
                   "BGP output queue token count for priority";
               }
               leaf output-queue-route-count {
                 type int32;
                 description
                   "BGP output queue route count for priority";
               }
             }
           }
         }
       }
       container tracing-information {
         leaf flags {
           type string;
           description
             "Enabled trace flags";
         }
         leaf filename {
           type string;
           description
             "Name of the trace file";
         }
         leaf filesize {
           type int32;
           description
             "Maximum size of the trace file";
         }
         leaf filelimit {
           type int32;
           description
             "Maximum number of retained trace files";
         }
       }
       list bgp-rib {
         key "name";
         leaf name {
           type string;
         }
         leaf total-prefix-count {
           type int32;
           description
             "Total number of prefixes in this RIB";
         }
         leaf active-prefix-count {
           type int32;
           description
             "Number of active prefixes";
         }
         leaf suppressed-prefix-count {
           type int32;
           description
             "Number of prefixes suppressed due to damping";
         }
         leaf history-prefix-count {
           type int32;
           description
             "Number of prefixes with damping history maintained";
         }
         leaf damped-prefix-count {
           type int32;
           description
             "Number of prefixes in any damped state";
         }
         leaf pending-prefix-count {
           type int32;
           description
             "Number of prefixes with pending changes";
         }
         leaf received-prefix-count {
           type int32;
           description
             "For a peer RIB, number of prefixes received from this peer";
         }
         leaf accepted-prefix-count {
           type int32;
           description
             "For a peer RIB, number of prefixes from this peer accepted by 
             policy";
         }
         leaf active-external-prefix-count {
           type int32;
           description
             "Number of active prefixes received from external peers";
         }
         leaf total-external-prefix-count {
           type int32;
           description
             "Total number of prefixes received from external peers";
         }
         leaf accepted-external-prefix-count {
           type int32;
           description
             "Number of accepted prefixes received from external peers";
         }
         leaf suppressed-external-prefix-count {
           type int32;
           description
             "Number of external prefixes suppressed due to damping";
         }
         leaf active-internal-prefix-count {
           type int32;
           description
             "Number of active prefixes received from internal peers";
         }
         leaf total-internal-prefix-count {
           type int32;
           description
             "Total number of prefixes received from internal peers";
         }
         leaf accepted-internal-prefix-count {
           type int32;
           description
             "Number of accepted prefixes received from internal peers";
         }
         leaf suppressed-internal-prefix-count {
           type int32;
           description
             "Number of internal prefixes suppressed due to damping";
         }
         leaf rib-bit {
           type string;
         }
         leaf bgp-rib-state {
           type string;
         }
         leaf vpn-rib-state {
           type string;
         }
         leaf send-state {
           type string;
         }
         leaf stale-prefix-count {
           type int32;
           description
             "Number of prefixes marked as stale";
         }
         leaf llgr-stale-prefix-count {
           type int32;
           description
             "Number of prefixes marked as LLGR stale";
         }
         leaf advertised-prefix-count {
           type int32;
           description
             "Number of prefixes present in the RIB-OUT";
         }
       }
     }
     container bgp-information {
       description
         "Operational and configuration information for BGP";
       leaf group-count {
         type int32;
       }
       leaf peer-count {
         type int32;
         description
           "Total number of peers";
       }
       leaf external-peer-count {
         type int32;
       }
       leaf internal-peer-count {
         type int32;
       }
       leaf down-peer-count {
         type int32;
       }
       leaf flap-count {
         type int32;
         description
           "Number of times BGP sessions have gone down";
       }
       leaf default-ebgp-advertise-mode {
         type string;
         description
           "Default eBGP advertisement mode";
       }
       leaf default-ebgp-receive-mode {
         type string;
         description
           "Default eBGP receive mode";
       }
       container peer-inb-conv-info {
         leaf inb-conv-status {
           type string;
           description
             "State of inbound convergence";
         }
         leaf inb-conv-time {
           type string;
           description
             "Time taken for inbound convergence";
         }
         leaf inb-conv-wait-period {
           type uint32;
           description
             "Maximum wait time for inbound convergence";
         }
         leaf inb-conv-reason {
           type string;
           description
             "Reason of inbound convergence";
         }
         leaf nlri-waiting-eor {
           type string;
           description
             "NLRI that end-of-rib is expected but not received";
         }
         leaf inb-conv-abort-time {
           type string;
           description
             "Time pending for inbound convergence";
         }
       }
       list bgp-family-stat {
         key "nlri-type";
         leaf nlri-type {
           type string;
           description
             "Type of NLRI being limited";
         }
         leaf bgp-nlri-send-time {
           type int32;
           description
             "Time for initial send by peer";
         }
         leaf bgp-nlri-recv-time {
           type int32;
           description
             "Time for initial receive by peer";
         }
       }
       container bgp-updio-globals {
         leaf bgp-updio-cfg-seq {
           type int32;
         }
         leaf bgp-updio-shutting-down {
           type int32;
         }
         leaf bgp-updio-shutdown-rcvd {
           type string;
         }
         leaf bgp-updio-shutdown-sent {
           type int32;
         }
         leaf bgp-updio-gc-timer {
           type int32;
         }
         leaf bgp-updio-gc-count {
           type int32;
         }
         leaf bgp-updio-gc-job {
           type string;
         }
       }
       list bgp-rib {
         key "name";
         leaf name {
           type string;
         }
         leaf total-prefix-count {
           type int32;
           description
             "Total number of prefixes in this RIB";
         }
         leaf active-prefix-count {
           type int32;
           description
             "Number of active prefixes";
         }
         leaf suppressed-prefix-count {
           type int32;
           description
             "Number of prefixes suppressed due to damping";
         }
         leaf history-prefix-count {
           type int32;
           description
             "Number of prefixes with damping history maintained";
         }
         leaf damped-prefix-count {
           type int32;
           description
             "Number of prefixes in any damped state";
         }
         leaf pending-prefix-count {
           type int32;
           description
             "Number of prefixes with pending changes";
         }
         leaf received-prefix-count {
           type int32;
           description
             "For a peer RIB, number of prefixes received from this peer";
         }
         leaf accepted-prefix-count {
           type int32;
           description
             "For a peer RIB, number of prefixes from this peer accepted by 
             policy";
         }
         leaf active-external-prefix-count {
           type int32;
           description
             "Number of active prefixes received from external peers";
         }
         leaf total-external-prefix-count {
           type int32;
           description
             "Total number of prefixes received from external peers";
         }
         leaf accepted-external-prefix-count {
           type int32;
           description
             "Number of accepted prefixes received from external peers";
         }
         leaf suppressed-external-prefix-count {
           type int32;
           description
             "Number of external prefixes suppressed due to damping";
         }
         leaf active-internal-prefix-count {
           type int32;
           description
             "Number of active prefixes received from internal peers";
         }
         leaf total-internal-prefix-count {
           type int32;
           description
             "Total number of prefixes received from internal peers";
         }
         leaf accepted-internal-prefix-count {
           type int32;
           description
             "Number of accepted prefixes received from internal peers";
         }
         leaf suppressed-internal-prefix-count {
           type int32;
           description
             "Number of internal prefixes suppressed due to damping";
         }
         leaf rib-bit {
           type string;
         }
         leaf bgp-rib-state {
           type string;
         }
         leaf vpn-rib-state {
           type string;
         }
         leaf send-state {
           type string;
         }
         leaf stale-prefix-count {
           type int32;
           description
             "Number of prefixes marked as stale";
         }
         leaf llgr-stale-prefix-count {
           type int32;
           description
             "Number of prefixes marked as LLGR stale";
         }
         leaf advertised-prefix-count {
           type int32;
           description
             "Number of prefixes present in the RIB-OUT";
         }
       }
       list bgp-peer {
         key "peer-address";
         description
           "Operational and configuration information for a BGP peer";
         leaf-list bgp-peer.heading {
           type string;
           description
             "Operational and configuration information for a BGP peer";
         }
         leaf peer-address {
           type jt:ipaddr;
         }
         leaf peer-as {
           type int32;
           description
             "Peer AS number";
         }
         leaf input-messages {
           type int32;
         }
         leaf output-messages {
           type int32;
         }
         leaf route-queue-count {
           type int32;
           description
             "Total number of routes queued for output to this peer";
         }
         leaf flap-count {
           type int32;
           description
             "Number of times BGP sessions have gone down";
         }
         leaf elapsed-time {
           type string;
           description
             "Time this adjacency or session has been up or down";
         }
         leaf peer-state {
           type string;
         }
         leaf local-interface-index {
           type int32;
           description
             "SNMP ifIndex of local interface";
         }
         leaf peer-end-of-rib-scheduled {
           type string;
         }
         leaf extended-information {
           type string;
         }
         container bgp-option-information {
           leaf bgp-nlri-send-time {
             type int32;
             description
               "Time for initial send by peer";
           }
           list nlri-policy {
             key "nlri-type";
             leaf nlri-type {
               type string;
               description
                 "Type of NLRI being limited";
             }
             leaf nlri-export-policy {
               type string;
             }
             leaf nlri-import-policy {
               type string;
             }
           }
           container nlri-send-community {
             leaf nlri-type {
               type string;
               description
                 "Type of NLRI being limited";
             }
             leaf nlri-send-community-type {
               type string;
             }
           }
           container addpath-send {
             leaf nlri-type {
               type string;
               description
                 "Type of NLRI being limited";
             }
             leaf addpath-send-type {
               type string;
             }
             leaf addpath-send-count {
               type int32;
             }
             leaf addpath-send-policy {
               type string;
             }
           }
           container addpath-receive {
             leaf nlri-type {
               type string;
               description
                 "Type of NLRI being limited";
             }
             leaf addpath-receive-type {
               type string;
             }
           }
           container nlri-information {
             leaf nlri-type {
               type string;
               description
                 "Type of NLRI being limited";
             }
             leaf nlri-flow-novalidate {
               type string;
               description
                 "Policy to accept flow routes without validation";
             }
             leaf nlri-output-queue-priority {
               type string;
               description
                 "Default address family output queue priority";
             }
             leaf nlri-route-refresh-priority {
               type string;
               description
                 "Default address family route-refresh priority";
             }
             leaf nlri-withdraw-priority {
               type string;
               description
                 "Default address family withdraw priority";
             }
             container nlri-flags {
               leaf bgp-nlri-flag-explicit-null-for-all-routes {
                 type empty;
               }
               leaf bgp-nlri-flag-explicit-null-for-connected-routes {
                 type empty;
               }
               leaf bgp-nlri-flag-aggregate-label {
                 type empty;
               }
               leaf bgp-nlri-flag-per-prefix-label {
                 type empty;
               }
               leaf bgp-nlri-flag-per-group-label {
                 type empty;
               }
               leaf bgp-nlri-flag-no-install-forwarding {
                 type empty;
               }
               leaf bgp-nlri-flag-rtage-refl-upd-msgs {
                 type empty;
               }
               leaf bgp-nlri-flag-no-resolution {
                 type empty;
               }
               leaf bgp-nlri-flag-resolve-preserve-hier {
                 type empty;
               }
               leaf bgp-nlri-flag-delay-route-advt {
                 type empty;
               }
               leaf bgp-nlri-flag-traffic-stats {
                 type empty;
               }
               leaf bgp-nlri-flag-l2vpn-status-vector {
                 type empty;
               }
               leaf bgp-nlri-flag-no-l2vpn-status-vector {
                 type empty;
               }
               leaf bgp-nlri-flag-accept-local-addr-pnh {
                 type empty;
               }
               leaf bgp-nlri-flag-accept-own {
                 type empty;
               }
               leaf bgp-nlri-flag-strip-nexthop {
                 type empty;
               }
               leaf bgp-nlri-flag-allow-po-add-nexthop {
                 type empty;
               }
               leaf bgp-nlri-flag-per-nexthop-label {
                 type empty;
               }
             }
             container nlri-traffic-stats {
               leaf traffic-stats-interval {
                 type int32;
               }
               container tracing-information {
                 leaf flags {
                   type string;
                   description
                     "Enabled trace flags";
                 }
                 leaf filename {
                   type string;
                   description
                     "Name of the trace file";
                 }
                 leaf filesize {
                   type int32;
                   description
                     "Maximum size of the trace file";
                 }
                 leaf filelimit {
                   type int32;
                   description
                     "Maximum number of retained trace files";
                 }
               }
             }
             container output-queues {
               description
                 "BGP output queues statistics";
               leaf time-series {
                 type string;
               }
               list class {
                 description
                   "An instance of BGP output queue statistics";
                 leaf priority-type {
                   type string;
                   description
                     "BGP output queue priority type";
                 }
                 leaf rank {
                   type int32;
                   description
                     "BGP output queue rank for priority type";
                 }
                 leaf token-count {
                   type int32;
                   description
                     "BGP output queue token count for priority";
                 }
                 leaf output-queue-route-count {
                   type int32;
                   description
                     "BGP output queue route count for priority";
                 }
               }
             }
           }
           leaf export-policy {
             type string;
           }
           leaf import-policy {
             type string;
           }
           leaf send-community-type {
             type string;
           }
           leaf advertise-bgp-static-policy {
             type string;
           }
           leaf bgp-options {
             type string;
           }
           leaf bgp-options2 {
             type string;
           }
           leaf bgp-options-extended {
             type string;
           }
           leaf bgp-options-extended2 {
             type string;
           }
           leaf remove-private-options {
             type string;
           }
           leaf authentication-key {
             type string;
           }
           leaf authentication-key-chain {
             type string;
             description
               "Name of authentication key chain";
           }
           leaf authentication-algorithm {
             type string;
             description
               "Name of authentication algorithm";
           }
           leaf authentication-configured {
             type empty;
           }
           leaf gshut-recv-local-preference {
             type uint32;
           }
           leaf gshut-send-local-preference {
             type uint32;
           }
           leaf address-families {
             type string;
           }
           leaf ignore-path-attributes {
             type string;
           }
           leaf local-address {
             type jt:ipaddr;
           }
           leaf holdtime {
             type int32;
             description
               "Delay before timing out the adjacency (default is 180 
               seconds)";
           }
           leaf metric-out {
             type int32;
           }
           leaf preference {
             type int32;
             description
               "Preference for the route";
           }
           leaf local-preference {
             type int32;
           }
           leaf local-as {
             type int32;
             description
               "Local AS number";
           }
           leaf local-as-private {
             type empty;
           }
           leaf local-system-as {
             type int32;
           }
           leaf receive-buffer-size {
             type int32;
           }
           leaf send-buffer-size {
             type int32;
           }
           leaf outbound-timer {
             type int32;
           }
           leaf med-action {
             type string;
           }
           leaf ipsec-sa {
             type string;
           }
           leaf bgp-bmp-monitor-peers {
             type string;
           }
           leaf bgp-bmp-route-monitoring-none {
             type empty;
           }
           leaf bgp-bmp-route-monitoring-prepolicy {
             type empty;
           }
           leaf bgp-bmp-prepolicy-exclude-non-feasible {
             type empty;
           }
           leaf bgp-bmp-route-monitoring-postpolicy {
             type empty;
           }
           leaf bgp-bmp-postpolicy-exclude-non-eligible {
             type empty;
           }
           leaf bgp-bmp-route-monitoring-ribout-prepolicy {
             type empty;
           }
           leaf bgp-bmp-route-monitoring-ribout-postpolicy {
             type empty;
           }
           container drop-path-attr-info {
             leaf drop-path-attributes {
               type string;
             }
             leaf drop-path-attributes-uot {
               type string;
             }
           }
           container wdraw-path-attr-info {
             leaf wdraw-path-attributes {
               type string;
             }
             leaf wdraw-path-attributes-uot {
               type string;
             }
           }
           container prefix-limit {
             leaf nlri-type {
               type string;
               description
                 "Type of NLRI being limited";
             }
             leaf prefix-count {
               type int32;
               description
                 "Number of prefixes accepted before action is taken";
             }
             leaf limit-action {
               type string;
               description
                 "Action taken upon reaching limit";
             }
             leaf warning-percentage {
               type int32;
               description
                 "Percentage of limit at which to log a warning";
             }
           }
           container accepted-prefix-limit {
             description
               "Limit number of prefixes accepted by policy";
             leaf nlri-type {
               type string;
               description
                 "Type of NLRI being limited";
             }
             leaf prefix-count {
               type int32;
               description
                 "Number of prefixes accepted before action is taken";
             }
             leaf limit-action {
               type string;
               description
                 "Action taken upon reaching limit";
             }
             leaf warning-percentage {
               type int32;
               description
                 "Percentage of limit at which to log a warning";
             }
           }
           container aigp-mode {
             leaf nlri-type {
               type string;
               description
                 "Type of NLRI being limited";
             }
           }
           container family-damping-info {
             leaf nlri-type {
               type string;
               description
                 "Type of NLRI being limited";
             }
           }
           container protection {
             leaf nlri-type {
               type string;
               description
                 "Type of NLRI being limited";
             }
           }
         }
         container egress-protection {
           container nlri-egress-protection {
             leaf nlri-type {
               type string;
               description
                 "Type of NLRI being limited";
             }
             leaf bgp-context-id {
               type jt:ipaddr;
             }
             leaf bgp-import-policy {
               type string;
             }
           }
           list ep-backup-table {
             leaf-list ep-backup-rib-name {
               type string;
               description
                 "Instance backup RIB";
             }
             leaf ep-backup-link {
               type string;
               description
                 "Vt interface";
             }
             leaf ep-backup-rib-id {
               type int32;
               description
                 "RIB Identifier";
             }
             leaf ep-backup-kern-id {
               type int32;
               description
                 "FIB Identifier";
             }
             leaf ep-backup-table-nh {
               type string;
               description
                 "Enhanced table nexthop";
             }
             leaf-list ep-instance-route-targets {
               type string;
               description
                 "Instance route targets";
             }
             leaf ep-backup-instance {
               type string;
             }
             leaf ep-backup-context {
               type string;
               description
                 "Instance backup context";
             }
           }
           list ep-instance-table {
             leaf ep-instance-name {
               type string;
             }
             leaf ep-instance-type {
               type string;
               description
                 "Instance type";
             }
             leaf ep-instance-protection-type {
               type string;
               description
                 "Instance request protected";
             }
             leaf ep-instance-context-id {
               type jt:ipaddr;
               description
                 "Context-id";
             }
             leaf-list ep-backup-rib-name {
               type string;
               description
                 "Instance backup RIB";
             }
           }
           leaf nlri-type {
             type string;
             description
               "Type of NLRI being limited";
           }
         }
         list bgp-output-queue {
           key "number";
           leaf number {
             type int32;
           }
           leaf count {
             type int32;
           }
           leaf table-name {
             type string;
             description
               "Unicast routing table";
           }
           leaf rib-adv-nlri {
             type string;
           }
           leaf time-series {
             type string;
           }
           list class {
             description
               "An instance of BGP output queue statistics";
             leaf priority-type {
               type string;
               description
                 "BGP output queue priority type";
             }
             leaf rank {
               type int32;
               description
                 "BGP output queue rank for priority type";
             }
             leaf token-count {
               type int32;
               description
                 "BGP output queue token count for priority";
             }
           }
         }
         list bgp-rib {
           key "name";
           leaf name {
             type string;
           }
           leaf total-prefix-count {
             type int32;
             description
               "Total number of prefixes in this RIB";
           }
           leaf active-prefix-count {
             type int32;
             description
               "Number of active prefixes";
           }
           leaf suppressed-prefix-count {
             type int32;
             description
               "Number of prefixes suppressed due to damping";
           }
           leaf history-prefix-count {
             type int32;
             description
               "Number of prefixes with damping history maintained";
           }
           leaf damped-prefix-count {
             type int32;
             description
               "Number of prefixes in any damped state";
           }
           leaf pending-prefix-count {
             type int32;
             description
               "Number of prefixes with pending changes";
           }
           leaf received-prefix-count {
             type int32;
             description
               "For a peer RIB, number of prefixes received from this peer";
           }
           leaf accepted-prefix-count {
             type int32;
             description
               "For a peer RIB, number of prefixes from this peer accepted 
               by policy";
           }
           leaf active-external-prefix-count {
             type int32;
             description
               "Number of active prefixes received from external peers";
           }
           leaf total-external-prefix-count {
             type int32;
             description
               "Total number of prefixes received from external peers";
           }
           leaf accepted-external-prefix-count {
             type int32;
             description
               "Number of accepted prefixes received from external peers";
           }
           leaf suppressed-external-prefix-count {
             type int32;
             description
               "Number of external prefixes suppressed due to damping";
           }
           leaf active-internal-prefix-count {
             type int32;
             description
               "Number of active prefixes received from internal peers";
           }
           leaf total-internal-prefix-count {
             type int32;
             description
               "Total number of prefixes received from internal peers";
           }
           leaf accepted-internal-prefix-count {
             type int32;
             description
               "Number of accepted prefixes received from internal peers";
           }
           leaf suppressed-internal-prefix-count {
             type int32;
             description
               "Number of internal prefixes suppressed due to damping";
           }
           leaf rib-bit {
             type string;
           }
           leaf bgp-rib-state {
             type string;
           }
           leaf vpn-rib-state {
             type string;
           }
           leaf send-state {
             type string;
           }
           leaf stale-prefix-count {
             type int32;
             description
               "Number of prefixes marked as stale";
           }
           leaf llgr-stale-prefix-count {
             type int32;
             description
               "Number of prefixes marked as LLGR stale";
           }
           leaf advertised-prefix-count {
             type int32;
             description
               "Number of prefixes present in the RIB-OUT";
           }
         }
         container peer-inb-conv-info {
           leaf inb-conv-status {
             type string;
             description
               "State of inbound convergence";
           }
           leaf inb-conv-time {
             type string;
             description
               "Time taken for inbound convergence";
           }
           leaf inb-conv-wait-period {
             type uint32;
             description
               "Maximum wait time for inbound convergence";
           }
           leaf inb-conv-reason {
             type string;
             description
               "Reason of inbound convergence";
           }
           leaf nlri-waiting-eor {
             type string;
             description
               "NLRI that end-of-rib is expected but not received";
           }
           leaf inb-conv-abort-time {
             type string;
             description
               "Time pending for inbound convergence";
           }
         }
         list bgp-family-stat {
           key "nlri-type";
           leaf nlri-type {
             type string;
             description
               "Type of NLRI being limited";
           }
           leaf bgp-nlri-send-time {
             type int32;
             description
               "Time for initial send by peer";
           }
           leaf bgp-nlri-recv-time {
             type int32;
             description
               "Time for initial receive by peer";
           }
         }
         list entropy-label-info {
           key "nlri-type";
           leaf nlri-type {
             type string;
             description
               "Type of NLRI being limited";
           }
           leaf entropy-label {
             type string;
             description
               "Entropy label";
           }
           leaf entropy-label-import-policy {
             type string;
           }
           leaf entropy-label-no-next-hop-validation {
             type string;
             description
               "Entropy label no next hop validation";
           }
           leaf entropy-label-elc-v2-compatible {
             type string;
             description
               "Entropy label ELCv2 compatible";
           }
           leaf entropy-label-capability {
             type string;
             description
               "Local entropy label capability";
           }
           leaf entropy-label-stitching-capability {
             type string;
             description
               "Entropy label stitching capability";
           }
         }
         container bgp-malformed-attributes {
           container malformed-information {
             leaf log-interval {
               type int32;
             }
             leaf route-limit {
               type int32;
             }
           }
           container path-attribute {
             leaf name {
               type string;
             }
             leaf code {
               type int32;
             }
             leaf last-recv {
               type int32;
             }
             leaf total-recv {
               type int32;
             }
           }
         }
         leaf local-address {
           type jt:ipaddr;
         }
         leaf local-as {
           type int32;
           description
             "Local AS number";
         }
         leaf tcp-connect-port {
           type uint32;
           description
             "TCP port to connect to BGP peer";
         }
         leaf description {
           type string;
         }
         leaf notify-message {
           type string;
         }
         leaf notify-message-recv {
           type string;
         }
         leaf peer-group {
           type string;
           description
             "BGP peer-group peer belongs to";
         }
         leaf peer-cfg-rti {
           type string;
           description
             "Routing-instance peer is configured in";
         }
         leaf peer-fwd-rti {
           type string;
           description
             "Peer's forwarding-context routing-instance";
         }
         leaf dynamic-neighbor-template {
           type string;
           description
             "Dynamic-neighbor template peer brought up in";
         }
         leaf peer-type {
           type string;
         }
         leaf route-reflector-client {
           type empty;
         }
         leaf peer-flags {
           type string;
         }
         leaf rsync-flags {
           type string;
         }
         leaf peer-auto-discovery-type {
           type string;
         }
         leaf last-state {
           type string;
         }
         leaf last-event {
           type string;
         }
         leaf recv-ebgp-origin-validation-state {
           type string;
         }
         leaf last-error {
           type string;
         }
         leaf last-flap-event {
           type string;
         }
         leaf last-unreplicate-event {
           type string;
         }
         leaf peer-id {
           type jt:ipaddr;
         }
         leaf local-id {
           type jt:ipaddr;
         }
         leaf active-holdtime {
           type int32;
         }
         leaf keepalive-interval {
           type int32;
         }
         leaf group-index {
           type int32;
         }
         leaf peer-index {
           type int32;
         }
         leaf snmp-index {
           type uint32;
         }
         leaf bgp-alert {
           type string;
         }
         leaf bgp-link-bandwidth-autosense-holdtime {
           type uint32;
         }
         leaf bgp-link-bandwidth-autosense-timer {
           type string;
         }
         leaf local-interface-name {
           type string;
           description
             "Logical interface name";
         }
         leaf glb-path-monitor-ifindex {
           type uint32;
           description
             "GLB Path Monitor ifIndex";
         }
         leaf glb-path-monitor-local-node-id {
           type jt:ipaddr;
           description
             "GLB Path Monitor local node ID";
         }
         leaf glb-path-monitor-remote-node-id {
           type jt:ipaddr;
           description
             "GLB Path Monitor remote node ID";
         }
         leaf glb-profile-space {
           type string;
         }
         leaf peer-color {
           type string;
         }
         leaf-list extended-community {
           type string;
           description
             "Extended community";
         }
         leaf nlri-type-peer {
           type string;
         }
         leaf nlri-type-session {
           type string;
         }
         leaf loop-check-display {
           type string;
         }
         leaf peer-no-refresh {
           type empty;
           description
             "Present if this peer does not support refresh";
         }
         leaf peer-refresh-capability {
           type int32;
           description
             "Version of refresh capability supported by this peer";
         }
         leaf peer-4byte-as-capability-not-supported {
           type empty;
           description
             "This peer does not support 4 byte AS extension";
         }
         leaf peer-4byte-as-capability-advertised {
           type int32;
           description
             "4 byte Autonomous System capability advertised by this peer";
         }
         leaf peer-addpath-not-supported {
           type empty;
           description
             "This peer does not support addpath";
         }
         leaf peer-addpath-ronly-nlri {
           type string;
           description
             "Types of NLRI for which peer advertised recv capability";
         }
         leaf peer-addpath-sonly-nlri {
           type string;
           description
             "Types of NLRI for which peer advertised send capability";
         }
         leaf peer-addpath-rs-nlri {
           type string;
           description
             "Types of NLRI for which peer advertised send/recv cap";
         }
         leaf peer-addpath-send-negotiated-nlri {
           type string;
           description
             "NLRI for which Addpath 'send' is negotiated with peer";
         }
         leaf peer-addpath-send-not-negotiated-nlri {
           type string;
           description
             "NLRI for which Addpath 'send' is not negotiated with peer";
         }
         leaf peer-addpath-recv-negotiated-nlri {
           type string;
           description
             "NLRI for which Addpath 'receive' is negotiated with peer";
         }
         leaf peer-addpath-recv-not-negotiated-nlri {
           type string;
           description
             "NLRI for which Addpath 'receive' is not negotiated with peer";
         }
         leaf local-role-advertised {
           type string;
           description
             "BGP role configured locally";
         }
         leaf local-role-mode {
           type string;
           description
             "BGP local role mode";
         }
         leaf peer-remote-role-advertised {
           type string;
           description
             "BGP role is advertised from this peer";
         }
         leaf peer-delay-route-advertisements {
           type string;
         }
         leaf local-ext-nh-nlri {
           type string;
           description
             "Types of NLRI for which we advertised extend nh cap";
         }
         leaf peer-ext-nh-nlri {
           type string;
           description
             "Types of NLRI for which peer advertised extend nh cap";
         }
         leaf peer-dont-wait-eor {
           type string;
         }
         leaf peer-dont-send-eor {
           type string;
         }
         leaf peer-restart-nlri-configured {
           type string;
         }
         leaf peer-restart-time-configured {
           type string;
         }
         leaf peer-stale-route-time-configured {
           type string;
         }
         leaf peer-down-time-configured {
           type string;
         }
         leaf peer-no-restart {
           type empty;
           description
             "Present if this peer does not support graceful restart 
             restarter mode";
         }
         leaf peer-restart-nlri-received {
           type string;
         }
         leaf peer-restart-time-received {
           type int32;
         }
         leaf peer-restart-flags-received {
           type string;
         }
         leaf peer-restart-nlri-can-save-state {
           type string;
         }
         leaf peer-restart-nlri-state-saved {
           type string;
         }
         leaf peer-restart-nlri-negotiated {
           type string;
         }
         leaf peer-end-of-rib-received {
           type string;
         }
         leaf peer-end-of-rib-sent {
           type string;
         }
         leaf peer-delay-end-of-rib {
           type string;
         }
         leaf peer-no-helper {
           type empty;
           description
             "Present if this peer does not support graceful restart 
             receiver mode";
         }
         leaf peer-restart-nlri-held {
           type string;
         }
         leaf peer-restart-remaining-time {
           type string;
         }
         leaf peer-stale-remaining-time {
           type string;
         }
         leaf peer-llgr-nlri-configured {
           type string;
         }
         leaf peer-no-llgr-restarter {
           type empty;
           description
             "Present if this peer does not support long-lived graceful 
             restart restarter mode";
         }
         leaf peer-llgr-nlri-restarter {
           type string;
         }
         leaf peer-llgr-nlri-state-saved {
           type string;
         }
         leaf peer-no-llgr-helper {
           type empty;
           description
             "Present if this peer does not support long-lived graceful 
             restart receiver mode";
         }
         leaf peer-llgr-ext-nlri-times-set {
           type string;
           description
             "NLRIs and extended-route-retention times set for this peer";
         }
         leaf peer-llgr-nlri-times {
           type string;
           description
             "NLRIs and times before long-lived stale routes are deleted";
         }
         leaf local-ext-nh-color-nlri {
           type string;
           description
             "Types of NLRI for which we enabled extended color nexthop 
             resolution";
         }
         leaf last-received {
           type int32;
         }
         leaf last-sent {
           type int32;
         }
         leaf last-checked {
           type int32;
         }
         leaf input-updates {
           type int32;
         }
         leaf input-refreshes {
           type int32;
         }
         leaf input-octets {
           type int32;
         }
         leaf output-updates {
           type int32;
         }
         leaf output-refreshes {
           type int32;
         }
         leaf output-octets {
           type int32;
         }
         leaf input-checksum {
           type int32;
         }
         leaf output-checksum {
           type int32;
         }
         leaf input-checksum-err {
           type int32;
         }
         leaf input-drop-path-attributes {
           type string;
         }
         leaf input-ignore-path-attributes {
           type string;
         }
         leaf input-wdraw-path-attributes {
           type string;
         }
         leaf buffered-octets-rx {
           type int32;
           description
             "Number of octets that have been received and are still 
             buffered";
         }
         leaf buffered-octets-tx {
           type int32;
           description
             "Number of octets in the transmit buffer";
         }
         leaf gather-buffered-octets-tx {
           type int32;
           description
             "Number of octets in the gather transmit buffer";
         }
         leaf input-updates-dropped {
           type int32;
           description
             "Number of received update messages dropped";
         }
         container bgp-peer-iosession {
           leaf iosession-thread-name {
             type string;
           }
           leaf iosession-state {
             type string;
           }
         }
         container bgp-bfd {
           leaf bfd-configuration-state {
             type string;
             description
               "BFD configuration state";
           }
           leaf bfd-operational-state {
             type string;
             description
               "BFD operational state";
           }
           leaf strict-bfd-configured {
             type empty;
           }
           leaf peer-strict-bfd-received {
             type empty;
           }
           leaf bfd-up-wait-timer-due {
             type string;
             description
               "Time until bgp session is reset if bfd does not come up";
           }
         }
         container prefix-limit-dropped-count {
           leaf nlri-type {
             type string;
             description
               "Type of NLRI being limited";
           }
           leaf dropped-count {
             type int32;
             description
               "Per NLRI monotonously increasing count.";
           }
         }
         container prefix-limit-hidden-count {
           leaf nlri-type {
             type string;
             description
               "Type of NLRI being limited";
           }
           leaf hidden-count {
             type int32;
             description
               "Per NLRI monotonously increasing count.";
           }
         }
         list bgp-shard-output-queue {
           key "shard-rib-number";
           leaf shard-rib-number {
             type int32;
           }
           leaf shard-outq-count {
             type int32;
           }
           leaf shard-table-name {
             type string;
           }
           leaf shard-rib-adv-nlri {
             type string;
           }
           leaf thread-name {
             type string;
           }
         }
         container update-io-info {
           leaf uio-info {
             type string;
           }
           leaf peer-internal-state {
             type string;
           }
           leaf peer-up-ack-pending-shards {
             type string;
           }
           leaf uio-peer-up-ack {
             type string;
           }
           leaf uio-peer-close-sent {
             type string;
           }
           leaf uio-peer-close-done {
             type string;
           }
         }
         container uio-peer-bits {
           leaf uio-peer-bits-header {
             type string;
           }
           leaf uio-up-rcvd {
             type string;
           }
           leaf uio-down-rcvd {
             type string;
           }
           leaf uio-write-act-rcvd {
             type string;
           }
           leaf uio-write-deact-rcvd {
             type string;
           }
           leaf uio-nlri-type {
             type string;
           }
           leaf uio-eor-rcvd {
             type string;
           }
           leaf uio-cfg-seq {
             type int32;
           }
           leaf uio-peer-create-thr-id {
             type int32;
           }
         }
         container bgp-error {
           leaf name {
             type string;
           }
           leaf send-count {
             type int32;
           }
           leaf receive-count {
             type int32;
           }
         }
         container route-queue {
           leaf timer {
             type string;
           }
           leaf state {
             type string;
             description
               "HFRR profile Current state";
           }
           leaf element {
             type string;
           }
         }
         container tracing-information {
           leaf flags {
             type string;
             description
               "Enabled trace flags";
           }
           leaf filename {
             type string;
             description
               "Name of the trace file";
           }
           leaf filesize {
             type int32;
             description
               "Maximum size of the trace file";
           }
           leaf filelimit {
             type int32;
             description
               "Maximum number of retained trace files";
           }
         }
         container bgp-uio-traffic {
           leaf uio-last-sent {
             type int32;
           }
           leaf uio-input-messages {
             type int32;
           }
           leaf uio-input-octets {
             type int32;
           }
         }
       }
       container bgp-bmp-information {
         list bmp-station {
           key "bmp-station-name";
           leaf bmp-station-name {
             type string;
           }
           leaf bmp-station-state {
             type string;
           }
           leaf bmp-myaddr {
             type string;
           }
           leaf bmp-remoteaddr {
             type string;
           }
           leaf bmp-connect-time {
             type string;
           }
           leaf bmp-holddown-time {
             type string;
           }
           leaf bmp-state-more-info {
             type string;
           }
           leaf elapsed-time {
             type string;
             description
               "Time this adjacency or session has been up or down";
           }
           leaf in-memory-profiling {
             type string;
           }
           leaf bmp-skip-write-time {
             type string;
           }
           leaf bmp-skip-read-time {
             type string;
           }
           leaf bmp-version {
             type string;
           }
           leaf bmp-route-instance {
             type string;
           }
           leaf bgp-bmp-monitor-peers {
             type string;
           }
           leaf bgp-bmp-route-monitoring-none {
             type empty;
           }
           leaf bgp-bmp-route-monitoring-prepolicy {
             type empty;
           }
           leaf bgp-bmp-prepolicy-exclude-non-feasible {
             type empty;
           }
           leaf bgp-bmp-route-monitoring-postpolicy {
             type empty;
           }
           leaf bgp-bmp-postpolicy-exclude-non-eligible {
             type empty;
           }
           leaf bgp-bmp-route-monitoring-ribout-prepolicy {
             type empty;
           }
           leaf bgp-bmp-route-monitoring-ribout-postpolicy {
             type empty;
           }
           leaf bgp-bmp-route-monitoring-loc-rib {
             type empty;
           }
           leaf bmp-treat-input-as-bmp {
             type string;
           }
           leaf bmp-server {
             type string;
           }
           leaf bmp-server-clients-cnt {
             type string;
           }
           leaf bmp-initiation-message {
             type string;
           }
           leaf bmp-memory-connect-timeout {
             type string;
           }
           leaf bmp-priority {
             type string;
           }
           leaf bmp-statistics-timeout {
             type string;
           }
           container bmp-addresses-ports {
             leaf bmp-local-address {
               type string;
             }
             leaf bmp-local-port {
               type string;
             }
             leaf bmp-station-address {
               type string;
             }
             leaf bmp-station-port {
               type string;
             }
             leaf bmp-connection-mode {
               type string;
             }
           }
           container bmp-authentication-with-key {
             leaf bmp-auth-key {
               type string;
             }
           }
           container bmp-authentication-with-key-chain {
             leaf bmp-auth-chain {
               type string;
             }
             leaf bmp-auth-alg {
               type string;
             }
           }
           container bmp-holddown {
             leaf bmp-holdtime {
               type string;
             }
             leaf bmp-holdtimeflaps {
               type string;
             }
             leaf bmp-holdtimeperiod {
               type string;
             }
           }
           container bmp-tcp-ka {
             leaf bmp-tcp-ka-idle-time {
               type string;
             }
             leaf bmp-tcp-ka-probe-count {
               type string;
             }
             leaf bmp-tcp-ka-probe-interval {
               type string;
             }
           }
           container tracing-information {
             leaf flags {
               type string;
               description
                 "Enabled trace flags";
             }
             leaf filename {
               type string;
               description
                 "Name of the trace file";
             }
             leaf filesize {
               type int32;
               description
                 "Maximum size of the trace file";
             }
             leaf filelimit {
               type int32;
               description
                 "Maximum number of retained trace files";
             }
           }
           container bmp-counter-info {
             leaf bmp-ctr-init-sent {
               type int32;
             }
             leaf bmp-ctr-term-sent {
               type int32;
             }
             leaf bmp-ctr-rm-sent {
               type int32;
             }
             leaf bmp-ctr-rm-add-sent {
               type int32;
             }
             leaf bmp-ctr-rm-del-sent {
               type int32;
             }
             leaf bmp-ctr-routes-sent {
               type int32;
             }
             leaf bmp-ctr-routes-add-sent {
               type int32;
             }
             leaf bmp-ctr-routes-del-sent {
               type int32;
             }
             leaf bmp-ctr-peer-down-sent {
               type int32;
             }
             leaf bmp-ctr-peer-up-sent {
               type int32;
             }
             leaf bmp-ctr-writes-done {
               type int32;
             }
             leaf bmp-ctr-writes-blocked {
               type int32;
             }
             leaf bmp-ctr-writes-full {
               type int32;
             }
             leaf bmp-ctr-writes-partial {
               type int32;
             }
             leaf bmp-ctr-writes-error {
               type int32;
             }
           }
           container bmp-kafka-info {
             leaf bmp-kafka-broker-address {
               type string;
             }
             leaf bmp-kafka-broker-status {
               type string;
             }
             leaf bmp-kafka-broker-elapsed-time {
               type string;
             }
           }
           container bmp-server-clients-info {
             leaf client-sys-name {
               type string;
             }
             leaf client-remote-address {
               type string;
             }
             leaf client-up-time {
               type string;
             }
           }
           container bmp-station-rib-in-pre-statistics {
             leaf bmp-monitor-name {
               type string;
               description
                 "BGP Monitoring type name";
             }
             leaf bmp-advertised-prefix-count {
               type int32;
               description
                 "Total advertised prefix count";
             }
             leaf bmp-withdrawn-prefix-count {
               type int32;
               description
                 "Total withdraw prefix count";
             }
           }
           container bmp-station-rib-in-post-statistics {
             leaf bmp-monitor-name {
               type string;
               description
                 "BGP Monitoring type name";
             }
             leaf bmp-advertised-prefix-count {
               type int32;
               description
                 "Total advertised prefix count";
             }
             leaf bmp-withdrawn-prefix-count {
               type int32;
               description
                 "Total withdraw prefix count";
             }
           }
           list bmp-station-rib-local-statistics {
             key "bmp-monitor-name";
             leaf bmp-monitor-name {
               type string;
               description
                 "BGP Monitoring type name";
             }
             leaf bmp-advertised-prefix-count {
               type int32;
               description
                 "Total advertised prefix count";
             }
             leaf bmp-withdrawn-prefix-count {
               type int32;
               description
                 "Total withdraw prefix count";
             }
           }
           container bmp-station-rib-out-pre-statistics {
             leaf bmp-monitor-name {
               type string;
               description
                 "BGP Monitoring type name";
             }
             leaf bmp-advertised-prefix-count {
               type int32;
               description
                 "Total advertised prefix count";
             }
             leaf bmp-withdrawn-prefix-count {
               type int32;
               description
                 "Total withdraw prefix count";
             }
           }
           container bmp-station-rib-out-post-statistics {
             leaf bmp-monitor-name {
               type string;
               description
                 "BGP Monitoring type name";
             }
             leaf bmp-advertised-prefix-count {
               type int32;
               description
                 "Total advertised prefix count";
             }
             leaf bmp-withdrawn-prefix-count {
               type int32;
               description
                 "Total withdraw prefix count";
             }
           }
         }
       }
       leaf bgp-thread-mode {
         type string;
       }
       leaf thread-state {
         type string;
       }
       leaf simple-int {
         type int32;
       }
     }
     leaf simple-int {
       type int32;
     }
   }
   grouping bgp-rtf-information-block {
     list bgp-rtf-brief {
       key "group-name";
       leaf group-name {
         type string;
       }
       leaf table-name {
         type string;
         description
           "Unicast routing table";
       }
       leaf bgp-rtf-state-flags {
         type string;
       }
       leaf bgp-rtf-entries {
         type int32;
       }
       leaf group-index {
         type int32;
       }
       leaf rtarget-recv-mask {
         type string;
       }
       leaf default-mask {
         type string;
       }
       list bgp-rtf-state {
         key "table-name";
         leaf table-name {
           type string;
           description
             "Unicast routing table";
         }
         leaf bgp-rtf-state-flags {
           type string;
         }
         leaf bgp-rtf-entries {
           type int32;
         }
         list bgp-rtf-entry {
           key "rtarget";
           leaf rtarget {
             type string;
             description
               "Route target community";
           }
           leaf rtarget-mask {
             type string;
           }
         }
       }
     }
     list bgp-rtf-group {
       key "group-name";
       leaf group-name {
         type string;
       }
       leaf group-index {
         type int32;
       }
       leaf rtarget-recv-mask {
         type string;
       }
       leaf default-mask {
         type string;
       }
       list bgp-rtf-state {
         key "table-name";
         leaf table-name {
           type string;
           description
             "Unicast routing table";
         }
         leaf bgp-rtf-state-flags {
           type string;
         }
         leaf bgp-rtf-entries {
           type int32;
         }
         list bgp-rtf-entry {
           key "rtarget";
           leaf rtarget {
             type string;
             description
               "Route target community";
           }
           leaf rtarget-mask {
             type string;
           }
         }
       }
     }
   }
   grouping bgp-traffic-statistics-information-block {
     container bgp-traffic-statistics-header {
       leaf group-name {
         type string;
       }
       leaf group-index {
         type int32;
       }
       leaf nlri-name {
         type string;
       }
     }
     container bgp-traffic-statistics {
       leaf bgp-prefix {
         type string;
       }
       leaf bgp-traffic-error {
         type string;
         description
           "Error encountered when querying the statistics";
       }
       leaf bgp-traffic-statistics-packet-count {
         type int32;
         description
           "Number of packets";
       }
       leaf bgp-traffic-statistics-byte-count {
         type int32;
         description
           "Number of bytes";
       }
       leaf bgp-traffic-statistics-egress-as {
         type string;
         description
           "Egress AS for traffic destined for this prefix";
       }
       leaf bgp-traffic-statistics-advertised-fec-label {
         type int32;
         description
           "Label advertised for routes in FEC";
       }
       leaf bgp-traffic-type {
         type string;
         description
           "Type of traffic: ingress or transit";
       }
     }
     container bgp-traffic-statistics-error {
       leaf bgp-traffic-error {
         type string;
         description
           "Error encountered when querying the statistics";
       }
     }
   }
   grouping bgp-traffic-stats-ingress-labeled-info-block {
     container bgp-traffic-statistics-header {
       leaf group-name {
         type string;
       }
       leaf group-index {
         type int32;
       }
       leaf nlri-name {
         type string;
       }
     }
     container bgp-traffic-statistics-ingress-labeled {
       leaf bgp-traffic-statistics-received-fec-labels {
         type int32;
         description
           "Labels received for routes in FEC";
       }
       leaf bgp-traffic-error {
         type string;
         description
           "Error encountered when querying the statistics";
       }
       leaf bgp-traffic-statistics-next-hop {
         type string;
         description
           "Next hop for labeled path";
       }
       leaf bgp-traffic-statistics-packet-count {
         type int32;
         description
           "Number of packets";
       }
       leaf bgp-traffic-statistics-byte-count {
         type int32;
         description
           "Number of bytes";
       }
       leaf bgp-traffic-type {
         type string;
         description
           "Type of traffic: ingress or transit";
       }
     }
     container bgp-traffic-statistics-error {
       leaf bgp-traffic-error {
         type string;
         description
           "Error encountered when querying the statistics";
       }
     }
   }
   grouping bgp-orf-information-block {
     container bgp-orf {
       leaf peer-address {
         type jt:ipaddr;
       }
       leaf peer-type {
         type string;
       }
       leaf group-name {
         type string;
       }
       list bgp-orf-nlri-info {
         key "nlri-name";
         leaf nlri-name {
           type string;
         }
         leaf filter-out-updates {
           type int32;
         }
         leaf filter-qcount {
           type int32;
         }
         leaf filter-in-updates {
           type int32;
         }
         leaf immediate-count {
           type int32;
         }
         list bgp-orf-filter-information {
           key "filter-type";
           leaf filter-type {
             type string;
           }
           leaf filter-mode {
             type string;
           }
           leaf filter-out-updates {
             type int32;
           }
           leaf filter-qcount {
             type int32;
           }
           leaf filter-in-updates {
             type int32;
           }
           container bgp-orf-filter-info {
             list bgp-orf-extcomm-filter {
               leaf-list extended-community {
                 type string;
                 description
                   "Extended community";
               }
             }
             list bgp-orf-prefix-filter {
               leaf prefix-orf {
                 type string;
                 description
                   "Prefix-based outbound route filter";
               }
             }
           }
         }
       }
     }
   }
   grouping bmp-insights-time-series-information-block {
     leaf time-series-header {
       type string;
     }
     container bmp-time-series {
       leaf bmp-station-name {
         type string;
       }
       container station-time-series {
         leaf station-time-series-name {
           type string;
         }
         container station-time-series-detail {
           leaf station-time-series-time-stamp {
             type string;
             description
               "Time stamp of the sample";
           }
           leaf station-time-series-value {
             type int32;
             description
               "Value of the sample";
           }
         }
       }
     }
   }
   grouping bmp-socket-write-stats-information-block {
     leaf bmp-sw-header {
       type string;
     }
     list bmp-sw {
       key "bmp-sw-name";
       leaf bmp-sw-name {
         type string;
       }
       container bmp-sw-stats {
         leaf bmp-monitor-name {
           type string;
           description
             "BGP Monitoring type name";
         }
         leaf write-count {
           type string;
           description
             "Write count";
         }
       }
       container bmp-swr-stats {
         leaf bmp-monitor-name {
           type string;
           description
             "BGP Monitoring type name";
         }
         leaf write-rate-count {
           type string;
           description
             "Write rate count";
         }
       }
     }
   }
   grouping bmp-route-monitoring-statistics-information-block {
     leaf bmp-station-statistics-header {
       type string;
     }
     list bmp-station {
       key "bmp-station-name";
       leaf bmp-station-name {
         type string;
       }
       container tracing-information {
         leaf flags {
           type string;
           description
             "Enabled trace flags";
         }
         leaf filename {
           type string;
           description
             "Name of the trace file";
         }
         leaf filesize {
           type int32;
           description
             "Maximum size of the trace file";
         }
         leaf filelimit {
           type int32;
           description
             "Maximum number of retained trace files";
         }
       }
       container bmp-counter-info {
         leaf bmp-ctr-init-sent {
           type int32;
         }
         leaf bmp-ctr-term-sent {
           type int32;
         }
         leaf bmp-ctr-rm-sent {
           type int32;
         }
         leaf bmp-ctr-rm-add-sent {
           type int32;
         }
         leaf bmp-ctr-rm-del-sent {
           type int32;
         }
         leaf bmp-ctr-routes-sent {
           type int32;
         }
         leaf bmp-ctr-routes-add-sent {
           type int32;
         }
         leaf bmp-ctr-routes-del-sent {
           type int32;
         }
         leaf bmp-ctr-peer-down-sent {
           type int32;
         }
         leaf bmp-ctr-peer-up-sent {
           type int32;
         }
         leaf bmp-ctr-writes-done {
           type int32;
         }
         leaf bmp-ctr-writes-blocked {
           type int32;
         }
         leaf bmp-ctr-writes-full {
           type int32;
         }
         leaf bmp-ctr-writes-partial {
           type int32;
         }
         leaf bmp-ctr-writes-error {
           type int32;
         }
       }
       container bmp-station-rib-in-pre-statistics {
         leaf bmp-monitor-name {
           type string;
           description
             "BGP Monitoring type name";
         }
         leaf bmp-advertised-prefix-count {
           type int32;
           description
             "Total advertised prefix count";
         }
         leaf bmp-withdrawn-prefix-count {
           type int32;
           description
             "Total withdraw prefix count";
         }
       }
       container bmp-station-rib-in-post-statistics {
         leaf bmp-monitor-name {
           type string;
           description
             "BGP Monitoring type name";
         }
         leaf bmp-advertised-prefix-count {
           type int32;
           description
             "Total advertised prefix count";
         }
         leaf bmp-withdrawn-prefix-count {
           type int32;
           description
             "Total withdraw prefix count";
         }
       }
       list bmp-station-rib-local-statistics {
         key "bmp-monitor-name";
         leaf bmp-monitor-name {
           type string;
           description
             "BGP Monitoring type name";
         }
         leaf bmp-advertised-prefix-count {
           type int32;
           description
             "Total advertised prefix count";
         }
         leaf bmp-withdrawn-prefix-count {
           type int32;
           description
             "Total withdraw prefix count";
         }
       }
       container bmp-station-rib-out-pre-statistics {
         leaf bmp-monitor-name {
           type string;
           description
             "BGP Monitoring type name";
         }
         leaf bmp-advertised-prefix-count {
           type int32;
           description
             "Total advertised prefix count";
         }
         leaf bmp-withdrawn-prefix-count {
           type int32;
           description
             "Total withdraw prefix count";
         }
       }
       container bmp-station-rib-out-post-statistics {
         leaf bmp-monitor-name {
           type string;
           description
             "BGP Monitoring type name";
         }
         leaf bmp-advertised-prefix-count {
           type int32;
           description
             "Total advertised prefix count";
         }
         leaf bmp-withdrawn-prefix-count {
           type int32;
           description
             "Total withdraw prefix count";
         }
       }
     }
   }
   grouping bmp-eor-stats-information-block {
     leaf bmp-eor-stats-header {
       type string;
     }
     list bmp-eor {
       key "bmp-station-name";
       leaf bmp-station-name {
         type string;
       }
       container bmp-eor-rib-in-pre-stats {
         leaf bmp-monitor-name {
           type string;
           description
             "BGP Monitoring type name";
         }
         leaf eor-count {
           type int32;
           description
             "Total end of rib count";
         }
         leaf eor-last-sent-time-stamp {
           type string;
           description
             "Time when last end of rib was sent";
         }
       }
       container bmp-eor-rib-in-post-stats {
         leaf bmp-monitor-name {
           type string;
           description
             "BGP Monitoring type name";
         }
         leaf eor-count {
           type int32;
           description
             "Total end of rib count";
         }
         leaf eor-last-sent-time-stamp {
           type string;
           description
             "Time when last end of rib was sent";
         }
       }
       container bmp-eor-rib-local-stats {
         leaf bmp-monitor-name {
           type string;
           description
             "BGP Monitoring type name";
         }
         leaf eor-count {
           type int32;
           description
             "Total end of rib count";
         }
         leaf eor-last-sent-time-stamp {
           type string;
           description
             "Time when last end of rib was sent";
         }
       }
       container bmp-eor-rib-out-pre-stats {
         leaf bmp-monitor-name {
           type string;
           description
             "BGP Monitoring type name";
         }
         leaf eor-count {
           type int32;
           description
             "Total end of rib count";
         }
         leaf eor-last-sent-time-stamp {
           type string;
           description
             "Time when last end of rib was sent";
         }
       }
       container bmp-eor-rib-out-post-stats {
         leaf bmp-monitor-name {
           type string;
           description
             "BGP Monitoring type name";
         }
         leaf eor-count {
           type int32;
           description
             "Total end of rib count";
         }
         leaf eor-last-sent-time-stamp {
           type string;
           description
             "Time when last end of rib was sent";
         }
       }
     }
   }
   grouping bmp-peer-statistics-information-block {
     leaf bmp-peer-statistics-header {
       type string;
     }
     list bmp-peer {
       key "bmp-station-name";
       leaf bmp-station-name {
         type string;
       }
       container bmp-peer-up-statistics {
         leaf bmp-monitor-name {
           type string;
           description
             "BGP Monitoring type name";
         }
         leaf peer-statistics-count {
           type int32;
           description
             "Total peer up/down count";
         }
         leaf peer-last-sent-time-stamp {
           type string;
           description
             "Time when last peer sent";
         }
       }
       container bmp-peer-down-statistics {
         leaf bmp-monitor-name {
           type string;
           description
             "BGP Monitoring type name";
         }
         leaf peer-statistics-count {
           type int32;
           description
             "Total peer up/down count";
         }
         leaf peer-last-sent-time-stamp {
           type string;
           description
             "Time when last peer sent";
         }
       }
     }
   }
   grouping bmp-term-statistics-information-block {
     leaf bmp-term-statistics-header {
       type string;
     }
     list bmp-term {
       key "bmp-station-name";
       leaf bmp-station-name {
         type string;
       }
       container bmp-term-statistics {
         leaf term-count {
           type int32;
           description
             "Total termination count";
         }
         leaf term-last-sent-time-stamp {
           type string;
           description
             "Time when last termination sent";
         }
       }
     }
   }
   grouping bmp-report-statistics-information-block {
     leaf bmp-report-statistics-header {
       type string;
     }
     list bmp-report {
       key "bmp-station-name";
       leaf bmp-station-name {
         type string;
       }
       container bmp-report-statistics {
         leaf report-count {
           type int32;
           description
             "Total report count";
         }
         leaf report-last-sent-time-stamp {
           type string;
           description
             "Time when last report sent";
         }
       }
     }
   }
   grouping bgp-output-queue-scheduler-block {
     leaf bgp-output-queue-scheduler-instance {
       type string;
     }
     list bgp-output-queue-scheduler-classes {
       key "output-queue-class";
       leaf output-queue-class {
         type string;
       }
       leaf output-queue-tokens {
         type int32;
       }
     }
     list bgp-output-queue-scheduler-defaults {
       key "output-queue-default-priority";
       leaf output-queue-default-priority {
         type string;
       }
       leaf output-queue-class {
         type string;
       }
     }
   }
   grouping bgp-sync-information-block {
     container bgp-rsync-master {
       leaf bgp-precision-timers {
         type string;
       }
       leaf bgp-rsync-session-state {
         type string;
         description
           "State of the BGP resynchronization session";
       }
       leaf bgp-rsync-session-time {
         type string;
         description
           "Amount of time that the BGP resynchronization session has been 
           Up or Down";
       }
       leaf bgp-rsync-session-flaps {
         type int32;
         description
           "Number of BGP resynchronization session flaps";
       }
       leaf bgp-rsync-session-last-flap-reason {
         type string;
         description
           "Reason for most recent BGP resynchronization session flap";
       }
       leaf bgp-rsync-session-last-flap-error {
         type string;
         description
           "Socket error for most recent BGP resynchronization session flap";
       }
       leaf bgp-rsync-state {
         type string;
       }
       leaf bgp-rsync-state-time {
         type string;
         description
           "Time since last protocol state change";
       }
       leaf bgp-rsync-flags {
         type string;
       }
       leaf bgp-rsync-rt-state {
         type string;
       }
       leaf bgp-rsync-ackwait {
         type int32;
         description
           "Number of peers waiting for ESTABLISH-ACK message";
       }
       leaf bgp-rsync-sowait {
         type int32;
         description
           "Number of peers waiting for socket record boundaries";
       }
       leaf bgp-rsync-sched {
         type int32;
         description
           "Number of peers being synchronized";
       }
       leaf bgp-rsync-sendbuf-count {
         type int32;
       }
       leaf bgp-rsync-walker {
         type empty;
       }
       container bgp-rsync-walk {
         leaf bgp-rsync-walk-table {
           type string;
           description
             "Current table name";
         }
         leaf bgp-rsync-walk-prefix {
           type string;
           description
             "Current Prefix";
         }
         leaf bgp-rsync-walk-prefixlen {
           type int32;
           description
             "Current Prefix length";
         }
         leaf queue-count {
           type int32;
           description
             "Number of entries enqueued";
         }
       }
       container bgp-rsync-estab-queue {
         list bgp-rsync-queue-entry {
           key "rsy-queue-instance rsy-queue-addr";
           leaf rsy-queue-instance {
             type int32;
           }
           leaf rsy-queue-addr {
             type string;
           }
           leaf rsy-queue-estab-tm {
             type int32;
           }
           leaf rsy-queue-more {
             type empty;
           }
         }
       }
       container bgp-rsync-ack-queue {
         list bgp-rsync-queue-entry {
           key "rsy-queue-instance rsy-queue-addr";
           leaf rsy-queue-instance {
             type int32;
           }
           leaf rsy-queue-addr {
             type string;
           }
           leaf rsy-queue-estab-tm {
             type int32;
           }
           leaf rsy-queue-more {
             type empty;
           }
         }
       }
       container bgp-rsync-commit-sync-queue {
         list bgp-rsync-queue-entry {
           key "rsy-queue-instance rsy-queue-addr";
           leaf rsy-queue-instance {
             type int32;
           }
           leaf rsy-queue-addr {
             type string;
           }
           leaf rsy-queue-more {
             type empty;
           }
         }
       }
       container bgp-rsync-error-queue {
         list bgp-rsync-queue-entry {
           key "rsy-queue-instance rsy-queue-addr";
           leaf rsy-queue-instance {
             type int32;
           }
           leaf rsy-queue-addr {
             type string;
           }
           leaf rsy-queue-more {
             type empty;
           }
         }
       }
       container bgp-rsync-stats {
         leaf open-send-count {
           type int32;
         }
         leaf estab-send-count {
           type int32;
         }
         leaf estab-gr-send-count {
           type int32;
         }
         leaf update-send-count {
           type int32;
         }
         leaf gr-stale-label-send-count {
           type int32;
         }
         leaf error-send-count {
           type int32;
         }
         leaf complete-send-count {
           type int32;
         }
         leaf open-receive-count {
           type int32;
         }
         leaf request-wild-receive-count {
           type int32;
         }
         leaf request-tgt-receive-count {
           type int32;
         }
         leaf estab-ack-receive-count {
           type int32;
         }
         leaf estab-gr-ack-receive-count {
           type int32;
         }
         leaf complete-ack-receive-count {
           type int32;
         }
         leaf update-send-avg-length {
           type uint32;
         }
         leaf update-send-peak-length {
           type uint32;
         }
       }
       list bgp-master-rsync-shard-ports {
         description
           "Master RPD rsync shard port information";
         leaf bgp-master-rsync-shard-id {
           type int32;
           description
             "Shard Id for rsync session on Master";
         }
         leaf bgp-master-rsync-shard-port {
           type int32;
           description
             "Shard port number for rsync session on Master";
         }
       }
       list bgp-master-swo-process-state {
         description
           "Master RPD switchover processing pending state";
         leaf bgp-master-swo-insnoop-pending {
           type uint32;
           description
             "Number of peers for which insnoop processing is pending after 
             last switchover";
         }
         leaf bgp-master-swo-insnoop-complete {
           type uint32;
           description
             "Number of peers for which insnoop processing is complete after
             last switchover";
         }
         leaf bgp-master-swo-insnoop-aggregate-bytes {
           type uint64;
           description
             "Total number of insnoop bytes drained by all peers during last
             switchover";
         }
         leaf bgp-master-swo-outsnoop-pending {
           type uint32;
           description
             "Number of peers for which outsnoop processing is pending after
             last switchover";
         }
         leaf bgp-master-swo-outsnoop-complete {
           type uint32;
           description
             "Number of peers for which outsnoop processing is complete 
             after last switchover";
         }
         leaf bgp-master-swo-outsnoop-aggregate-bytes {
           type uint64;
           description
             "Total number of outsnoop bytes drained by all peers during 
             last switchover";
         }
         leaf bgp-master-swo-lbl-pending-shards {
           type int32;
           description
             "Number of shards having label request pending after last 
             switchover";
         }
         leaf bgp-master-swo-shard-standby-lbl-pending {
           type string;
           description
             "Shard's label request pending after last switchover";
         }
         leaf bgp-master-swo-lbl-pool-seeded {
           type string;
           description
             "Initial label pool seeded after last switchover";
         }
         leaf bgp-master-swo-defer-proc-rsync-reject-count {
           type uint32;
           description
             "Count of rsync connections rejected due to deferred snoop data
             processing";
         }
       }
       container bgp-master-rsync-peer-queue {
         list bgp-master-residual-peer-entry {
           description
             "Master RPD residual information for a peer";
           leaf bgp-master-residual-peer-instance {
             type string;
             description
               "BGP peer's routing instance with residual bytes at time of 
               last switchover";
           }
           leaf bgp-master-residual-peer-addr {
             type jt:ipaddr;
             description
               "IP address of the BGP peer with residual bytes at time of 
               last switchover";
           }
           leaf bgp-master-residual-peer-inbuf {
             type int32;
             description
               "Number of unread bytes in inbuf at time of last switchover";
           }
           leaf bgp-master-residual-peer-outbuf {
             type int32;
             description
               "Number of unread bytes in outbuf at time of last switchover";
           }
           leaf bgp-master-residual-inbuf-thrio-processed-count {
             type int32;
             description
               "Number of times inbound residual buffer processed before 
               next socket read after last switchover";
           }
         }
         list bgp-master-swo-pending-peer-entry {
           description
             "Master RPD switchover pending for a peer";
           leaf bgp-master-swo-pending-peer-instance {
             type string;
             description
               "BGP peer's routing instance with switchover pending after 
               last switchover";
           }
           leaf bgp-master-swo-pending-peer-addr {
             type jt:ipaddr;
             description
               "IP address of the BGP peer with switchover pending after 
               last switchover";
           }
           leaf bgp-master-swo-pending-peer-standby-flags {
             type int32;
             description
               "BGP peer's standby flags after last switchover";
           }
           leaf bgp-master-swo-pending-peer-pending-shards {
             type int32;
             description
               "Switchover pending shards for BGP peer after last switchover";
           }
         }
         list bgp-master-peer-nsr-info-entry {
           description
             "Master RPD peer nonstop-routing info";
           leaf peer-nsr-info-instance {
             type string;
             description
               "BGP peer's routing instance";
           }
           leaf peer-nsr-info-addr {
             type jt:ipaddr;
             description
               "IP address of the BGP peer";
           }
           leaf peer-nsr-info-send-buffer {
             type uint32;
             description
               "BGP peer's socket send buffer size";
           }
           leaf peer-nsr-info-soft-limit {
             type uint32;
             description
               "BGP peer's socket send buffer soft limit that is currently 
               applied";
           }
           leaf peer-nsr-info-replication-count {
             type uint32;
             description
               "Count of times socket replication activated for the BGP peer";
           }
           leaf peer-nsr-info-last-replication-ts {
             type string;
             description
               "Timestamp when the last/most-recent socket replication 
               activated for the BGP peer";
           }
           leaf peer-nsr-info-unreplication-count {
             type uint32;
             description
               "Count of times socket replication deactivated for the BGP 
               peer";
           }
           leaf peer-nsr-info-last-unreplication-ts {
             type string;
             description
               "Timestamp when the last/most-recent socket replication 
               activated for the BGP peer";
           }
           leaf peer-nsr-info-jsr-replication-timeout {
             type uint32;
             description
               "Jsr replication timeout value set";
           }
           list peer-nsr-info-jsr-unreplicate-reasons {
             leaf-list peer-nsr-info-jsr-unreplicate-reasons.heading {
               type string;
             }
             leaf peer-nsr-info-jsr-unreplicate-reason {
               type string;
               description
                 "Reason for unreplicating peer";
             }
             leaf peer-nsr-info-jsr-unreplicate-reason-counter {
               type uint32;
               description
                 "Counter for each reason unreplicating peer";
             }
           }
         }
         list bgp-master-rsync-peer-entry {
           description
             "Master RPD rsync information for a peer";
           leaf bgp-master-peer-instance {
             type string;
             description
               "BGP peer's routing instance";
           }
           leaf bgp-master-peer-addr {
             type jt:ipaddr;
             description
               "IP address of the BGP peer";
           }
           leaf bgp-master-peer-rsync-nlri {
             type string;
             description
               "NLRI of the route prefixes sent by master over rsync channel";
           }
           leaf bgp-master-peer-rsync-ribin-sent {
             type int32;
             description
               "Number of inbound route prefixes sent over rsync channel";
           }
           leaf bgp-master-peer-rsync-ribout-sent {
             type int32;
             description
               "Number of outbound route prefixes sent over rsync channel";
           }
         }
       }
       container bgp-standby-rsync-peer-queue {
         list bgp-standby-rsync-peer-entry {
           description
             "Standby RPD rsync information for a peer";
           leaf bgp-standby-peer-instance {
             type string;
             description
               "BGP peer's routing instance";
           }
           leaf bgp-standby-peer-addr {
             type jt:ipaddr;
             description
               "IP address of the BGP peer";
           }
           leaf bgp-standby-peer-rsync-nlri {
             type string;
             description
               "NLRI of the route prefixes received by standby";
           }
           leaf bgp-standby-peer-rsync-ribin-recv {
             type int32;
             description
               "Number of inbound route prefixes received over rsync channel";
           }
           leaf bgp-standby-peer-rsync-ribout-recv {
             type int32;
             description
               "Number of outbound route prefixes received over rsync 
               channel";
           }
           leaf bgp-standby-peer-snoop-ribin-adv-recv {
             type int32;
             description
               "Number of inbound route prefixes' add/change received over 
               snooping socket";
           }
           leaf bgp-standby-peer-snoop-ribout-adv-recv {
             type int32;
             description
               "Number of outbound route prefixes' add/change received over 
               snooping socket";
           }
           leaf bgp-standby-peer-snoop-ribin-del-recv {
             type int32;
             description
               "Number of inbound route prefixes' withdraw received over 
               snooping socket";
           }
           leaf bgp-standby-peer-snoop-ribout-del-recv {
             type int32;
             description
               "Number of outbound route prefixes' withdraw received over 
               snooping socket";
           }
         }
       }
     }
     container bgp-standby {
       leaf bgp-standby-state {
         type string;
       }
       leaf bgp-standby-last-trans {
         type string;
       }
       leaf bgp-standby-sendbuf {
         type int32;
       }
       leaf bgp-unsync-timer {
         type string;
       }
       leaf bgp-unsync-pending-tm {
         type string;
       }
       container bgp-unsync-queue {
         list bgp-unsync-entry {
           key "usy-iid usy-addr";
           leaf usy-iid {
             type int32;
           }
           leaf usy-addr {
             type jt:ipaddr;
           }
           leaf usy-elapsed {
             type string;
           }
           leaf usy-flags {
             type string;
           }
           leaf usy-more {
             type empty;
           }
         }
       }
       container bgp-unsync-pending {
         list bgp-unsync-entry {
           key "usy-iid usy-addr";
           leaf usy-iid {
             type int32;
           }
           leaf usy-addr {
             type jt:ipaddr;
           }
           leaf usy-elapsed {
             type string;
           }
           leaf usy-flags {
             type string;
           }
           leaf usy-more {
             type empty;
           }
         }
       }
       container bgp-standby-sync-queue {
         list bgp-standby-sync-entry {
           key "bstandby-iid bstandby-addr";
           leaf bstandby-iid {
             type int32;
           }
           leaf bstandby-addr {
             type jt:ipaddr;
           }
         }
       }
       list bgp-standby-rsync-shard-ports {
         description
           "Master RPD rsync shard port information";
         leaf bgp-standby-rsync-shard-id {
           type int32;
           description
             "Shard Id for rsync session on Standby";
         }
         leaf bgp-standby-rsync-shard-port {
           type int32;
           description
             "Shard port number for rsync session on Standby";
         }
       }
       container bgp-standby-rsync-peer-queue {
         list bgp-standby-rsync-peer-entry {
           description
             "Standby RPD rsync information for a peer";
           leaf bgp-standby-peer-instance {
             type string;
             description
               "BGP peer's routing instance";
           }
           leaf bgp-standby-peer-addr {
             type jt:ipaddr;
             description
               "IP address of the BGP peer";
           }
           leaf bgp-standby-peer-rsync-nlri {
             type string;
             description
               "NLRI of the route prefixes received by standby";
           }
           leaf bgp-standby-peer-rsync-ribin-recv {
             type int32;
             description
               "Number of inbound route prefixes received over rsync channel";
           }
           leaf bgp-standby-peer-rsync-ribout-recv {
             type int32;
             description
               "Number of outbound route prefixes received over rsync 
               channel";
           }
           leaf bgp-standby-peer-snoop-ribin-adv-recv {
             type int32;
             description
               "Number of inbound route prefixes' add/change received over 
               snooping socket";
           }
           leaf bgp-standby-peer-snoop-ribout-adv-recv {
             type int32;
             description
               "Number of outbound route prefixes' add/change received over 
               snooping socket";
           }
           leaf bgp-standby-peer-snoop-ribin-del-recv {
             type int32;
             description
               "Number of inbound route prefixes' withdraw received over 
               snooping socket";
           }
           leaf bgp-standby-peer-snoop-ribout-del-recv {
             type int32;
             description
               "Number of outbound route prefixes' withdraw received over 
               snooping socket";
           }
         }
       }
     }
   }
   grouping bgp-tunnel-atribute-information-block {
     leaf bgp-srte-policy-count {
       type uint32;
     }
     leaf bgp-ip-in-ip-count {
       type uint32;
     }
     leaf bgp-vxlan-count {
       type uint32;
     }
     leaf bgp-list-tunnels-count {
       type uint32;
     }
     leaf bgp-unsupported-tun-count {
       type uint32;
     }
     leaf bgp-total-tun-attrib-count {
       type uint32;
     }
     list bgp-tun-attributes {
       leaf bgp-srte-tunnel-adv-name {
         type string;
       }
       leaf bgp-tunnel-attrib-id {
         type uint32;
       }
       leaf bgp-tunnel-attrib-type {
         type string;
       }
       leaf bgp-tunnel-attrib-name {
         type string;
       }
       leaf bgp-tunnel-attrib-endpoint {
         type string;
       }
       leaf bgp-tunnel-attrib-color {
         type string;
       }
     }
     container bgp-tunnel-attribute-list {
       list bgp-tun-attributes {
         leaf bgp-tunnel-attrib-id {
           type uint32;
         }
         leaf bgp-srte-tunnel-adv-name {
           type string;
         }
       }
       list bgp-tunnel-attribute {
         key "tunnel-attribute-type";
         description
           "Tunne encap attribute information";
         leaf tunnel-attribute-type {
           type string;
         }
         leaf tunnel-attribute-rpf {
           type empty;
         }
         leaf tunnel-attribute-destination {
           type jt:ipaddr;
         }
       }
     }
     container srte1-policy-information {
       container srte1-policy {
         leaf srte1-tunnel-id {
           type uint32;
         }
         leaf srte1-path-preference {
           type uint32;
         }
         leaf srte1-binding-sid {
           type string;
         }
         leaf srte1-adv-policy-name {
           type string;
         }
         leaf srte1-priority {
           type uint32;
         }
         leaf srte1-enlp {
           type uint32;
         }
         leaf srte1-tlv-recv-flags {
           type string;
         }
         leaf srte1-binding-sid-label-encoding {
           type string;
         }
         list srte1-segment-list {
           leaf srte1-segment-list-weight {
             type uint32;
           }
           list srte1-segment {
             leaf srte1-segment-label {
               type uint32;
             }
             leaf srte1-segment-label-ttl {
               type string;
               description
                 "SR Policy segment label ttl";
             }
           }
         }
       }
     }
     list bgp-tunnel-attribute {
       key "tunnel-attribute-type";
       description
         "Tunne encap attribute information";
       leaf tunnel-attribute-type {
         type string;
       }
       leaf tunnel-attribute-color {
         type uint32;
       }
       leaf tunnel-attribute-destination {
         type jt:ipaddr;
       }
     }
   }
   grouping bgp-glb-block {
     leaf bgp-glb-state {
       type string;
     }
     leaf bgp-glb-role {
       type string;
     }
     leaf bgp-glb-hw-profiles {
       type uint32;
     }
     leaf bgp-glb-shared-hw-profiles {
       type uint32;
     }
     leaf bgp-glb-unshared-hw-profiles {
       type uint32;
     }
     leaf bgp-glb-pending-eval-profiles {
       type uint32;
     }
     leaf bgp-glb-profile-limit-eval-profiles {
       type uint32;
     }
     leaf bgp-glb-profile-space-others-eval-profiles {
       type uint32;
     }
     container bgp-glb-profile-sharing {
       description
         "Profile sharing related options";
       leaf bgp-glb-profile-sharing-state {
         type string;
       }
       container bgp-glb-profile-sharing-except {
         leaf except-aspath-length {
           type uint32;
         }
         leaf except-policy {
           type string;
         }
       }
     }
     list bgp-glb-profile-space {
       key "bgp-glb-profile-space-name";
       leaf bgp-glb-profile-space-name {
         type string;
       }
       leaf bgp-glb-profile-space-id {
         type uint32;
       }
       leaf bgp-glb-profile-space-unalloc-bits {
         type string;
       }
       leaf bgp-glb-profile-space-max-hw-id {
         type string;
       }
     }
     list bgp-glb-path {
       key "bgp-glb-path-id";
       leaf bgp-glb-path-id {
         type uint32;
       }
       leaf bgp-glb-path-ifindex {
         type int32;
       }
       leaf bgp-glb-path-nh-node-id {
         type jt:ipaddr;
       }
     }
     list bgp-glb-path-monitor {
       key "bgp-glb-path-monitor-ifindex bgp-glb-path-monitor-local-node-id bgp-glb-path-monitor-remote-node-id";
       leaf bgp-glb-path-monitor-ifindex {
         type int32;
       }
       leaf bgp-glb-path-monitor-local-node-id {
         type jt:ipaddr;
       }
       leaf bgp-glb-path-monitor-remote-node-id {
         type jt:ipaddr;
       }
     }
     list bgp-glb-profile {
       key "bgp-glb-profile-id";
       leaf bgp-glb-profile-pointer {
         type string;
       }
       leaf bgp-glb-profile-id {
         type uint32;
       }
       leaf bgp-glb-profile-lookahead-count {
         type uint32;
       }
       leaf bgp-glb-profile-lookahead-list {
         type empty;
       }
       leaf bgp-glb-profile-lookahead-unalloc-list {
         type empty;
       }
       leaf bgp-glb-profile-nnh-node-id {
         type jt:ipaddr;
       }
       leaf bgp-glb-profile-space-name {
         type string;
       }
       leaf bgp-glb-profile-space-id {
         type uint32;
       }
       leaf bgp-glb-profile-hw-id {
         type uint32;
       }
       leaf bgp-glb-profile-path-count {
         type uint32;
       }
       leaf bgp-glb-profile-path-list {
         type empty;
       }
       leaf bgp-glb-profile-path-unalloc-list {
         type empty;
       }
       list bgp-glb-profile-lookahead-entry {
         key "bgp-glb-profile-lookahead-profile-id";
         leaf bgp-glb-profile-lookahead-profile-id {
           type uint32;
         }
         leaf bgp-glb-profile-lookahead-profile-nnh-node-id {
           type jt:ipaddr;
         }
         leaf bgp-glb-profile-lookahead-profile-space-id {
           type uint32;
         }
         leaf bgp-glb-profile-lookahead-profile-hw-id {
           type uint32;
         }
       }
       list bgp-glb-profile-lookahead-unalloc-entry {
         key "bgp-glb-profile-lookahead-profile-nnh-node-id";
         leaf bgp-glb-profile-lookahead-profile-nnh-node-id {
           type jt:ipaddr;
         }
         leaf bgp-glb-profile-lookahead-profile-space-id {
           type uint32;
         }
         leaf bgp-glb-profile-lookahead-profile-hw-id {
           type uint32;
         }
       }
       list bgp-glb-profile-path-entry {
         key "bgp-glb-profile-path-id";
         leaf bgp-glb-profile-path-id {
           type uint32;
         }
         leaf bgp-glb-profile-path-ifindex {
           type uint32;
         }
         leaf bgp-glb-profile-path-nh-node-id {
           type jt:ipaddr;
         }
         leaf bgp-glb-profile-path-refcnt {
           type uint32;
         }
       }
       list bgp-glb-profile-path-unalloc-entry {
         key "bgp-glb-profile-path-ifindex bgp-glb-profile-path-nh-node-id";
         leaf bgp-glb-profile-path-ifindex {
           type uint32;
         }
         leaf bgp-glb-profile-path-nh-node-id {
           type jt:ipaddr;
         }
         leaf bgp-glb-profile-path-refcnt {
           type uint32;
         }
       }
     }
   }
   grouping bgp-fabric-advertise-block {
     container fabric-advertise-route {
       description
         "One fabric advertie route";
       leaf rt-destination {
         type string;
         description
           "Route prefixes awaiting ACK";
       }
       leaf rt-prefix-length {
         type string;
       }
       leaf rt-color {
         type string;
       }
       leaf rt-color-community {
         type string;
       }
       leaf rt-backup-color {
         type string;
       }
       leaf rt-backup-color-community {
         type string;
       }
     }
   }
   grouping bgp-diagnostics-overview-block {
     leaf bgp-running {
       type string;
     }
     leaf bgp-running-master {
       type empty;
     }
     leaf bgp-running-instance {
       type empty;
     }
     leaf bgp-running-api {
       type empty;
     }
     leaf bgp-running-bmp {
       type empty;
     }
     leaf nsr-enabled {
       type string;
     }
     leaf nsr-re-mode {
       type string;
     }
     leaf multipath-on-standby {
       type empty;
     }
     leaf shard-count {
       type uint32;
     }
     leaf update-io-count {
       type uint32;
     }
     leaf global-as {
       type uint32;
     }
     leaf global-confed-as {
       type uint32;
     }
     leaf global-bgp-id {
       type jt:ipaddr;
     }
     leaf listening-port {
       type uint32;
     }
     leaf listening-port-status-ipv4 {
       type string;
     }
     leaf listening-port-status-ipv6 {
       type string;
     }
     leaf multipath-enabled {
       type empty;
     }
     leaf multipath-foreground-mode {
       type string;
     }
     leaf optimal-route-reflection {
       type empty;
     }
     leaf flash-inactive {
       type string;
     }
     leaf route-walk-full-quantum {
       type string;
     }
     leaf write-job-suspend-threshold {
       type uint32;
     }
     leaf defer-unreachable-nlris {
       type empty;
     }
     leaf advertise-vpn-main-nlri {
       type string;
     }
     leaf rr-asbr-nlri {
       type string;
     }
     leaf configured-advertise-vpn-main-nlri {
       type string;
     }
     leaf app-requested-advertise-vpn-main-nlri {
       type string;
     }
     leaf stale-label-mode {
       type string;
     }
     leaf stale-label-hold-time {
       type string;
     }
     leaf stale-label-count {
       type uint32;
     }
     leaf stale-label-cleanup-time {
       type string;
     }
     leaf sr-label-type {
       type string;
     }
     leaf sr-label-start {
       type uint32;
     }
     leaf sr-label-end {
       type uint32;
     }
     leaf interface-replay-done {
       type string;
     }
     leaf inbound-convergence-pending-peer-count {
       type string;
     }
     leaf outbound-gr-eor-pending-peer-count {
       type string;
     }
     leaf warning-trigger-thresholds {
       type empty;
     }
     leaf memory-in-use-threshold {
       type uint32;
     }
     leaf memory-max-ever-threshold {
       type uint32;
     }
     leaf match-cache-hit-ratio-threshold {
       type uint32;
     }
     leaf match-cache-lookup-threshold {
       type uint32;
     }
     leaf community-hash-average-load-threshold {
       type uint32;
     }
     leaf community-hash-max-load-threshold {
       type uint32;
     }
     leaf bgp-adv-entries-threshold {
       type uint32;
     }
     leaf bgp-groups-threshold {
       type uint32;
     }
     leaf prefix-limit-threshold {
       type uint32;
     }
     container route-refresh-threshold {
       leaf five-minute-threshold {
         type uint32;
       }
       leaf thirty-minute-threshold {
         type uint32;
       }
       leaf one-hour-threshold {
         type uint32;
       }
     }
   }
   grouping bgp-diagnostics-warnings-block {
     leaf current-memory-percentage {
       type uint32;
     }
     leaf max-memory-percentage {
       type uint32;
     }
     leaf community-match-cache-lookups {
       type uint64;
     }
     leaf community-match-cache-hit-ratio {
       type string;
     }
     leaf aspath-match-cache-lookups {
       type uint64;
     }
     leaf aspath-match-cache-hit-ratio {
       type string;
     }
     leaf lsp-regex-match-cache-lookups {
       type uint64;
     }
     leaf lsp-regex-match-cache-hit-ratio {
       type string;
     }
     leaf community-hash-buckets {
       type uint32;
     }
     leaf community-hash-used-buckets {
       type uint32;
     }
     leaf average-community-hash-bucket-size {
       type uint32;
     }
     leaf max-community-hash-bucket-size {
       type uint32;
     }
     leaf advertisement-entries {
       type uint32;
     }
     leaf bgp-groups {
       type uint32;
     }
     leaf zero-bgp-id {
       type empty;
     }
     list prefix-limit-warnings {
       key "peer-address";
       leaf peer-address {
         type jt:ipaddr;
       }
       leaf nlri-type {
         type string;
         description
           "Type of NLRI being limited";
       }
       leaf prefix-limit-count {
         type uint32;
       }
       leaf prefix-percentage {
         type uint32;
       }
       leaf accepted-prefix-limit-count {
         type uint32;
       }
       leaf accepted-prefix-percentage {
         type uint32;
       }
     }
     list excess-route-refresh-warnings {
       key "peer-address";
       leaf refresh-direction {
         type string;
       }
       leaf peer-address {
         type jt:ipaddr;
       }
       leaf peer-pointer {
         type string;
       }
       leaf peer-instance-name {
         type string;
       }
       leaf received-route-refresh-count-fivemin {
         type uint32;
       }
       leaf received-route-refresh-count-thirtymin {
         type uint32;
       }
       leaf received-route-refresh-count-hour {
         type uint32;
       }
       leaf start-hour-interval-time-rcvr {
         type uint32;
       }
       leaf end-hour-interval-time-rcvr {
         type uint32;
       }
       leaf sent-route-refresh-count-fivemin {
         type uint32;
       }
       leaf sent-route-refresh-count-thirtymin {
         type uint32;
       }
       leaf sent-route-refresh-count-hour {
         type uint32;
       }
       leaf start-hour-interval-time-sndr {
         type uint32;
       }
       leaf end-hour-interval-time-sndr {
         type uint32;
       }
       leaf total-excess-rcvd-peers {
         type uint32;
       }
       leaf total-excess-sent-peers {
         type uint32;
       }
     }
   }
   grouping bgp-diagnostics-import-eval-block {
     list bgp-diagnostics-import-eval-peer {
       key "peer-address";
       leaf peer-address {
         type jt:ipaddr;
       }
       leaf peer-pointer {
         type string;
       }
       leaf instance-name {
         type string;
       }
       leaf import-eval-nlri {
         type string;
       }
       leaf import-eval-trigger {
         type string;
       }
       leaf import-eval-trigger-time {
         type string;
       }
     }
   }
   grouping bgp-diagnostics-export-eval-block {
     list bgp-diagnostics-export-eval-group {
       key "group-name";
       leaf group-name {
         type string;
       }
       leaf group-pointer {
         type string;
       }
       leaf instance-name {
         type string;
       }
       leaf group-index {
         type int32;
       }
       leaf export-eval-nlri {
         type string;
       }
       leaf export-eval-trigger {
         type string;
       }
       leaf export-eval-trigger-time {
         type string;
       }
     }
   }
   grouping bgp-diagnostics-local-rib-eval-block {
     list bgp-diagnostics-local-rib-eval-rib {
       key "rib-name";
       leaf rib-name {
         type string;
       }
       leaf rib-pointer {
         type string;
       }
       leaf local-rib-eval-trigger {
         type string;
       }
       leaf local-rib-eval-pending-trigger {
         type string;
       }
       leaf local-rib-eval-trigger-time {
         type string;
       }
     }
   }
   grouping bgp-diagnostics-neighbor-block {
     list bgp-diagnostics-one-neighbor {
       key "peer-address";
       leaf peer-address {
         type jt:ipaddr;
       }
       leaf peer-pointer {
         type string;
       }
       leaf peer-instance-name {
         type string;
       }
       leaf peer-state {
         type string;
       }
       leaf peer-last-flap-time {
         type string;
       }
       leaf peer-last-flap-event {
         type string;
       }
       leaf peer-flap-reason {
         type string;
       }
       leaf peer-down-reason-time {
         type string;
       }
       leaf peer-down-reason {
         type string;
       }
       leaf peer-down-detailed-reason {
         type string;
       }
       leaf peer-down-suggestion {
         type string;
       }
       leaf peer-sock-state {
         type string;
       }
       leaf bgp-pdu-description {
         type string;
       }
       leaf bgp-pdu {
         type string;
       }
     }
   }
   grouping bgp-diagnostics-route-block {
     leaf route-diagnostics-table {
       type string;
     }
     leaf route-diagnostics-route {
       type string;
     }
     leaf route-diagnostics-route-pointer {
       type string;
     }
     leaf route-diagnostics-state {
       type string;
     }
     leaf peer-ifl-name {
       type string;
     }
     leaf route-diagnostics-record-time {
       type string;
     }
     leaf route-diagnostics-reason {
       type string;
     }
     leaf route-diagnostics-detailed-reason {
       type string;
     }
     leaf route-diagnostics-suggestion {
       type string;
     }
   }
   grouping bgp-diagnostics-dropped-route-cache-block {
     leaf route-cache-peer {
       type string;
     }
     leaf route-cache-table {
       type string;
     }
     leaf route-cache-size {
       type uint32;
     }
     leaf route-cache-count {
       type uint32;
     }
     list route-cache-reason {
       leaf route-cache-reason-name {
         type string;
       }
       leaf route-cache-reason-route-count {
         type uint32;
       }
       list route-cache-reason-route {
         leaf route-cache-reason-route-prefix {
           type string;
         }
         leaf route-cache-reason-route-time {
           type string;
         }
       }
     }
   }
   grouping bgp-spring-information-block {
     container bgp-srgb-information {
       description
         "BGP source-packet-routing srgb information";
       leaf bgp-srgb-allocation {
         type string;
         description
           "SRGB Block Allocation";
       }
       container bgp-srgb-config {
         description
           "SRGB block configuration related information";
         leaf bgp-srgb-config-block-header {
           type string;
           description
             "SRGB Config Block";
         }
         leaf bgp-srgb-start-label {
           type int32;
           description
             "Configuration of SRGB start label";
         }
         leaf bgp-srgb-index-range {
           type int32;
           description
             "Configuration of SRGB index range";
         }
       }
       container bgp-srgb-block {
         description
           "SRGB block related information";
         leaf bgp-srgb-first-label {
           type int32;
           description
             "First label allocated for SRGB Block";
         }
         leaf bgp-srgb-last-label {
           type int32;
           description
             "Last label allocated for SRGB Block";
         }
       }
     }
   }
   grouping bgp-rv-statistics-information-block {
     container bgp-rv-statistics {
       leaf bgp-rv-policy-origin-validation-requests {
         type uint32;
       }
       leaf bgp-rv-policy-origin-validation-results-valid {
         type uint32;
       }
       leaf bgp-rv-policy-origin-validation-results-invalid {
         type uint32;
       }
       leaf bgp-rv-policy-origin-validation-results-unknown {
         type uint32;
       }
       leaf bgp-rv-import-policy-reevaluations {
         type uint32;
       }
       leaf bgp-rv-import-policy-eval-rib-walk-triggers {
         type uint32;
       }
       list bgp-rv-import-policy-rib-statistics {
         key "bgp-rv-import-policy-rib-name";
         leaf bgp-rv-import-policy-rib-name {
           type string;
         }
         leaf bgp-rv-import-policy-rib-reevaluations {
           type uint32;
         }
       }
     }
   }
 }
