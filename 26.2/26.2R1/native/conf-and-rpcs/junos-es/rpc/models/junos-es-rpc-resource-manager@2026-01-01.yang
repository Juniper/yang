/*
 * Copyright (c) 2026 Juniper Networks, Inc.
 * All rights reserved.
 */
 module junos-es-rpc-resource-manager {
   namespace "http://yang.juniper.net/junos-es/rpc/resource-manager";

   prefix resource-manager;

   import junos-common-types {
     prefix jt;
     revision-date 2026-01-01;
   }

   organization "Juniper Networks, Inc.";

   contact "yang-support@juniper.net";

   description "Junos RPC YANG module for resource-manager command(s)";

   revision 2026-01-01 {
     description "Junos: 26.2R1.7";
   }

   rpc get-resman-cpu {
     description "Show resource manager cpu information";
     input {
       leaf statistics {
         description "Show resource manager cpu statistics";
         type union {
           type uint32;
           type string {
             pattern "<.*>|$.*";
           }
         }
       }
     }
     output {
       choice output-tags {
         case actual-tag {
           container resource-manager-cpu-information {
             uses resource-manager-cpu-information-block;
           }
         }
         case multichassis-tag {
           container multi-routing-engine-results {
             list multi-routing-engine-item {
               leaf re-name {
                 type string;
               }
               choice output-tags {
                 case actual-tag {
                   container resource-manager-cpu-information {
                     uses resource-manager-cpu-information-block;
                   }
                 }
               }
             }
           }
         }
       }
     }
   }
   rpc get-resman-memory {
     description "Show resource manager memory information";
     input {
       leaf statistics {
         description "Show resource manager cpu statistics";
         type union {
           type uint32;
           type string {
             pattern "<.*>|$.*";
           }
         }
       }
     }
     output {
       choice output-tags {
         case actual-tag {
           container resource-manager-memory-information {
             uses resource-manager-memory-information-block;
           }
         }
         case multichassis-tag {
           container multi-routing-engine-results {
             list multi-routing-engine-item {
               leaf re-name {
                 type string;
               }
               choice output-tags {
                 case actual-tag {
                   container resource-manager-memory-information {
                     uses resource-manager-memory-information-block;
                   }
                 }
               }
             }
           }
         }
       }
     }
   }
   rpc get-resman-summary {
     description "Show resource manager summary";
     output {
       choice output-tags {
         case actual-tag {
           container resman-summary {
             uses resman-summary-block;
           }
         }
         case multichassis-tag {
           container multi-routing-engine-results {
             list multi-routing-engine-item {
               leaf re-name {
                 type string;
               }
               choice output-tags {
                 case actual-tag {
                   container resman-summary {
                     uses resman-summary-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping resource-manager-cpu-information-block {
     leaf fpc-number {
       type uint32;
       description
         "FPC number";
     }
     leaf pic-number {
       type uint32;
       description
         "PIC number";
     }
     leaf cpu-threshold-exceeded {
       type uint32;
       description
         "CPU Threshold exceeded";
     }
     leaf cpu-threshold-cleared {
       type uint32;
       description
         "CPU Threshold cleared";
     }
     leaf drop-flows {
       type uint32;
       description
         "Drop flows";
     }
     leaf throttled-session {
       type uint32;
       description
         "Trottled Sessions";
     }
     leaf packets-dropped {
       type uint32;
       description
         "Dropped Packets";
     }
     leaf alarm-sent {
       type uint32;
       description
         "Alarm Sent";
     }
     leaf messages-logged {
       type uint32;
       description
         "Messages Logged";
     }
   }
   grouping resource-manager-memory-information-block {
     leaf fpc-number {
       type uint32;
       description
         "FPC number";
     }
     leaf pic-number {
       type uint32;
       description
         "PIC number";
     }
     leaf session-low-watermark-hit {
       type uint32;
       description
         "Session low watermark hit";
     }
     leaf session-high-watermark-hit {
       type uint32;
       description
         "Session low watermark hit";
     }
     leaf memory-threshold-exceeded {
       type uint32;
       description
         "Memory Threshold exceeded";
     }
     leaf memory-threshold-cleared {
       type uint32;
       description
         "Memory Threshold cleared";
     }
     leaf early-session-ageout {
       type uint32;
       description
         "Early Session Ageout";
     }
     leaf drop-flows {
       type uint32;
       description
         "Drop flows";
     }
     leaf fail-open {
       type uint32;
       description
         "Fail Open";
     }
     leaf fail-close {
       type uint32;
       description
         "Fail Close";
     }
     leaf alarm-sent {
       type uint32;
       description
         "Alarm Sent";
     }
     leaf messages-logged {
       type uint32;
       description
         "Messages Logged";
     }
   }
   grouping resman-summary-block {
     leaf fpc-number {
       type uint32;
       description
         "FPC number";
     }
     leaf pic-number {
       type uint32;
       description
         "PIC number";
     }
     leaf services-memory {
       type uint64;
       description
         "Services Memory usage";
     }
     leaf packets-memory {
       type uint64;
       description
         "Packets Memory usage";
     }
     leaf session-created {
       type uint64;
       description
         "Sessions created";
     }
     list resman-summary-cpu {
       leaf cpu-number {
         type uint32;
         description
           "CPU number";
       }
       leaf cpu-last-min-usage {
         type uint32;
         description
           "Last minute average CPU usage";
       }
     }
   }
 }
