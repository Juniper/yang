/*
 * Copyright (c) 2026 Juniper Networks, Inc.
 * All rights reserved.
 */
 module junos-es-rpc-multi-chassis {
   namespace "http://yang.juniper.net/junos-es/rpc/multi-chassis";

   prefix multi-chassis;

   import junos-common-types {
     prefix jt;
     revision-date 2026-01-01;
   }

   organization "Juniper Networks, Inc.";

   contact "yang-support@juniper.net";

   description "Junos RPC YANG module for multi-chassis command(s)";

   revision 2026-01-01 {
     description "Junos: 26.2R1.7";
   }

   rpc get-mclag-config-consistency-information {
     description "Show all configuration consistency information";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   rpc get-mclag-global-config-consistency-information {
     description "Configuration related to system-wide operations";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   rpc get-mclag-icl-config-consistency-information {
     description "Configuration related to ICL";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   rpc get-mclag-config-consistency-information-mcae {
     description "Configuration related to MCAE interfaces";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   rpc get-mclag-vrrp-config-consistency-information {
     description "Configuration related to MCAE interfaces";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   rpc get-mclag-config-consistency-information-params {
     description "Show list of configuration items checked for consistency";
     output {
       choice output-tags {
         case actual-tag {
           container multichassis-consistency-params-list {
             uses multichassis-consistency-params-list-block;
           }
         }
         case multichassis-tag {
           container multi-routing-engine-results {
             list multi-routing-engine-item {
               leaf re-name {
                 type string;
               }
               choice output-tags {
                 case actual-tag {
                   container multichassis-consistency-params-list {
                     uses multichassis-consistency-params-list-block;
                   }
                 }
               }
             }
           }
         }
       }
     }
   }
   rpc get-mclag-vlan-config-consistency-information {
     description "Configuration related to VLAN";
     output {
       choice output-tags {
         case actual-tag {
           container multichassis-consistency-check-list {
             uses multichassis-consistency-check-list-block;
           }
         }
         case multichassis-tag {
           container multi-routing-engine-results {
             list multi-routing-engine-item {
               leaf re-name {
                 type string;
               }
               choice output-tags {
                 case actual-tag {
                   container multichassis-consistency-check-list {
                     uses multichassis-consistency-check-list-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping multichassis-consistency-check-list-block {
     leaf multichassis-global {
       type string;
     }
     list multichassis-ifd-name {
       leaf local-ifd-name {
         type string;
         description
           "Name of the Local Physical Interface";
       }
       leaf peer-ifd-name {
         type string;
         description
           "Name of the Peer Physical Interface";
       }
     }
     list multichassis-ifl-name {
       leaf local-ifl-name {
         type string;
         description
           "Name of the Local Logical Interface";
       }
       leaf peer-ifl-name {
         type string;
         description
           "Name of the Peer Logical Interface";
       }
     }
     list multichassis-vlan-name {
       leaf local-vlan-name {
         type string;
         description
           "Name of the Local VLAN";
       }
       leaf peer-vlan-name {
         type string;
         description
           "Name of the peer VLAN";
       }
     }
     list multichassis-irb-name {
       leaf local-irb-name {
         type string;
         description
           "Name of the Local IRB";
       }
       leaf peer-irb-name {
         type string;
         description
           "Name of the peer IRB";
       }
     }
     list multichassis-vrrp-grp-id {
       leaf local-vrrp-grp-id {
         type string;
         description
           "ID of the Local VRRP Group";
       }
       leaf peer-vrrp-grp-id {
         type string;
         description
           "ID of the peer VRRP Group";
       }
     }
     list multichassis-consistency-check-entry {
       leaf config-item {
         type string;
         description
           "Name of the Configuration Item";
       }
       leaf consistency-check {
         type string;
         description
           "Type of Consistency Check performed";
       }
       leaf local-value {
         type string;
         description
           "Configured value on the local MC-LAG node";
       }
       leaf peer-value {
         type string;
         description
           "Configured value on the peer MC-LAG node";
       }
       leaf result {
         type string;
         description
           "Result of Configuration Consistency Check";
       }
     }
   }
   grouping multichassis-consistency-params-list-block {
     list multichassis-consistency-param-entry {
       leaf param-config-item {
         type string;
         description
           "Identifier of the Configuration Item";
       }
       leaf param-config-name {
         type string;
         description
           "Name of the Configuration Item";
       }
       leaf param-config-level {
         type string;
         description
           "Configuration Level of the Config Item";
       }
       leaf param-consistency-requirement {
         type string;
         description
           "Requirement to be Consistent";
       }
       leaf param-consistency-check {
         type string;
         description
           "Consistency Check Type for this Config";
       }
     }
   }
 }
