/*
 * Copyright (c) 2026 Juniper Networks, Inc.
 * All rights reserved.
 */
 module junos-es-rpc-services {
   namespace "http://yang.juniper.net/junos-es/rpc/services";

   prefix services;

   import junos-common-types {
     prefix jt;
     revision-date 2026-01-01;
   }

   organization "Juniper Networks, Inc.";

   contact "yang-support@juniper.net";

   description "Junos RPC YANG module for services command(s)";

   revision 2026-01-01 {
     description "Junos: 26.2R1.7";
   }

   rpc get-pcef-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output-tags {
         case output-tag {
           leaf output {
             type string;
           }
         }
         case actual-tag {
           anyxml pcef-subscriber;
         }
         case multichassis-tag {
           anyxml multi-routing-engine-results;
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
     output {
       choice output-tags {
         case output-tag {
           leaf output {
             type string;
           }
         }
         case actual-tag {
           anyxml pcef-subscriber;
         }
         case multichassis-tag {
           anyxml multi-routing-engine-results;
         }
       }
     }
   }
   rpc get-pcef-pic {
     description "Show physical interface card information";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         default "terse";
         type enumeration {
           enum "terse" {
             description "Display terse output";
           }
         }
       }
     }
     output {
       choice output-tags {
         case output-tag {
           leaf output {
             type string;
           }
         }
         case actual-tag {
           anyxml pcef-pic;
         }
         case multichassis-tag {
           anyxml multi-routing-engine-results;
         }
       }
     }
   }
   rpc get-ift-global-information {
     description "Show inband telemetry information";
     output {
       choice output-tags {
         case actual-tag {
           container ift-global-information {
             uses ift-global-information-block;
           }
         }
         case multichassis-tag {
           container multi-routing-engine-results {
             list multi-routing-engine-item {
               leaf re-name {
                 type string;
               }
               choice output-tags {
                 case actual-tag {
                   container ift-global-information {
                     uses ift-global-information-block;
                   }
                 }
               }
             }
           }
         }
       }
     }
   }
   rpc get-ift-profile-information {
     description "Show inband telemetry profile details";
     input {
       leaf profile-name {
         description "Name of the profile";
         type string;
       }
     }
     output {
       choice output-tags {
         case actual-tag {
           container ift-profile-information {
             uses ift-profile-information-block;
           }
         }
         case multichassis-tag {
           container multi-routing-engine-results {
             list multi-routing-engine-item {
               leaf re-name {
                 type string;
               }
               choice output-tags {
                 case actual-tag {
                   container ift-profile-information {
                     uses ift-profile-information-block;
                   }
                 }
               }
             }
           }
         }
       }
     }
   }
   rpc get-ift-stats-information {
     description "Show inband telemetry stats information";
     output {
       choice output-tags {
         case actual-tag {
           container ift-stats-information {
             uses ift-stats-information-block;
           }
         }
         case multichassis-tag {
           container multi-routing-engine-results {
             list multi-routing-engine-item {
               leaf re-name {
                 type string;
               }
               choice output-tags {
                 case actual-tag {
                   container ift-stats-information {
                     uses ift-stats-information-block;
                   }
                 }
               }
             }
           }
         }
       }
     }
   }
   rpc get-aamw-statistics {
     description "Show advanced-anti-malware statistics";
     input {
       uses command-forwarding;
     }
     output {
       choice output-tags {
         case actual-tag {
           container aamw-statistics {
             uses aamw-statistics-block;
           }
         }
         case multichassis-tag {
           container multi-routing-engine-results {
             list multi-routing-engine-item {
               leaf re-name {
                 type string;
               }
               choice output-tags {
                 case actual-tag {
                   container aamw-statistics {
                     uses aamw-statistics-block;
                   }
                 }
               }
             }
           }
         }
       }
     }
   }
   rpc get-aamw-redirect-files {
     description "Show redirect files information";
     input {
       uses command-forwarding;
       leaf file-name {
         description "Show redirect-file content";
         type string;
       }
     }
     output {
       choice output-tags {
         case actual-tag {
           container aamw-redirect-files {
             uses aamw-redirect-files-block;
           }
         }
         case multichassis-tag {
           container multi-routing-engine-results {
             list multi-routing-engine-item {
               leaf re-name {
                 type string;
               }
               choice output-tags {
                 case actual-tag {
                   container aamw-redirect-files {
                     uses aamw-redirect-files-block;
                   }
                 }
               }
             }
           }
         }
       }
     }
   }
   rpc get-aamw-policy {
     description "Show advanced-anti-malware policy";
     input {
       uses command-forwarding;
       leaf policy-name {
         description "Policy name";
         type string;
       }
     }
     output {
       choice output-tags {
         case actual-tag {
           container aamw-policy {
             uses aamw-policy-block;
           }
         }
         case multichassis-tag {
           container multi-routing-engine-results {
             list multi-routing-engine-item {
               leaf re-name {
                 type string;
               }
               choice output-tags {
                 case actual-tag {
                   container aamw-policy {
                     uses aamw-policy-block;
                   }
                 }
               }
             }
           }
         }
       }
     }
   }
   rpc get-aamw-profile {
     description "Show advanced-anti-malware profile";
     input {
       uses command-forwarding;
       leaf profile-name {
         description "Profile name";
         type string;
       }
     }
     output {
       choice output-tags {
         case actual-tag {
           container aamw-profile {
             uses aamw-profile-block;
           }
         }
         case multichassis-tag {
           container multi-routing-engine-results {
             list multi-routing-engine-item {
               leaf re-name {
                 type string;
               }
               choice output-tags {
                 case actual-tag {
                   container aamw-profile {
                     uses aamw-profile-block;
                   }
                 }
               }
             }
           }
         }
       }
     }
   }
   rpc get-aamw-status {
     description "Show advanced-anti-malware status";
     input {
       uses command-forwarding;
     }
     output {
       choice output-tags {
         case actual-tag {
           container aamw-status {
             uses aamw-status-block;
           }
         }
         case multichassis-tag {
           container multi-routing-engine-results {
             list multi-routing-engine-item {
               leaf re-name {
                 type string;
               }
               choice output-tags {
                 case actual-tag {
                   container aamw-status {
                     uses aamw-status-block;
                   }
                 }
               }
             }
           }
         }
       }
     }
   }
   rpc get-aamw-default-policy {
     description "Show advanced-anti-malware default policy";
     input {
       uses command-forwarding;
     }
     output {
       choice output-tags {
         case actual-tag {
           container aamw-default-policy {
             uses aamw-default-policy-block;
           }
         }
         case multichassis-tag {
           container multi-routing-engine-results {
             list multi-routing-engine-item {
               leaf re-name {
                 type string;
               }
               choice output-tags {
                 case actual-tag {
                   container aamw-default-policy {
                     uses aamw-default-policy-block;
                   }
                 }
               }
             }
           }
         }
       }
     }
   }
   rpc get-aamw-version {
     description "Show advanced-anti-malware version";
     input {
       uses command-forwarding;
     }
     output {
       choice output-tags {
         case actual-tag {
           container aamw-version {
             uses aamw-version-block;
           }
         }
         case multichassis-tag {
           container multi-routing-engine-results {
             list multi-routing-engine-item {
               leaf re-name {
                 type string;
               }
               choice output-tags {
                 case actual-tag {
                   container aamw-version {
                     uses aamw-version-block;
                   }
                 }
               }
             }
           }
         }
       }
     }
   }
   rpc get-aamw-session-summary {
     description "Show advanced-anti-malware session summary";
     status deprecated;
     input {
       uses command-forwarding;
     }
     output {
       choice output-tags {
         case output-tag {
           leaf output {
             type string;
           }
         }
         case actual-tag {
           anyxml aamw-session-summary;
         }
         case multichassis-tag {
           anyxml multi-routing-engine-results;
         }
       }
     }
   }
   rpc get-aamw-db-statistics {
     description "Show advanced-anti-malware database-statistics";
     input {
       uses command-forwarding;
     }
     output {
       choice output-tags {
         case output-tag {
           leaf output {
             type string;
           }
         }
         case actual-tag {
           anyxml aamw-db-statistics;
         }
         case multichassis-tag {
           anyxml multi-routing-engine-results;
         }
       }
     }
   }
   rpc get-aamw-sig-exempt-list {
     description "Show advanced-anti-malware exempt-list";
     input {
       uses command-forwarding;
     }
     output {
       choice output-tags {
         case actual-tag {
           container aamw-sig-exempt-list {
             uses aamw-sig-exempt-list-block;
           }
         }
         case multichassis-tag {
           container multi-routing-engine-results {
             list multi-routing-engine-item {
               leaf re-name {
                 type string;
               }
               choice output-tags {
                 case actual-tag {
                   container aamw-sig-exempt-list {
                     uses aamw-sig-exempt-list-block;
                   }
                 }
               }
             }
           }
         }
       }
     }
   }
   rpc get-dynamic-filtering-statistics {
     description "Show Cloud Connection Status";
     input {
       uses command-forwarding;
     }
     output {
       choice output-tags {
         case actual-tag {
           container dynamic-filtering-connection-status {
             uses dynamic-filtering-connection-status-block;
           }
         }
         case multichassis-tag {
           container multi-routing-engine-results {
             list multi-routing-engine-item {
               leaf re-name {
                 type string;
               }
               choice output-tags {
                 case actual-tag {
                   container dynamic-filtering-connection-status {
                     uses dynamic-filtering-connection-status-block;
                   }
                 }
               }
             }
           }
         }
       }
     }
   }
   rpc get-security-metadata-dns-statistics {
     description "Show security metadata streaming DNS statistics";
     input {
       uses command-forwarding;
     }
     output {
       choice output-tags {
         case actual-tag {
           container sm-dns-statistics {
             uses sm-dns-statistics-block;
           }
         }
         case multichassis-tag {
           container multi-routing-engine-results {
             list multi-routing-engine-item {
               leaf re-name {
                 type string;
               }
               choice output-tags {
                 case actual-tag {
                   container sm-dns-statistics {
                     uses sm-dns-statistics-block;
                   }
                 }
               }
             }
           }
         }
       }
     }
   }
   rpc get-security-metadata-statistics {
     description "Show security metadata streaming HTTP statistics";
     input {
       uses command-forwarding;
     }
     output {
       choice output-tags {
         case output-tag {
           leaf output {
             type string;
           }
         }
         case actual-tag {
           anyxml security-metadata-statistics;
         }
         case multichassis-tag {
           anyxml multi-routing-engine-results;
         }
       }
     }
   }
   rpc get-security-metadata-streaming-whitelist {
     description "Show security metadata streaming HTTP whitelist";
     input {
       uses command-forwarding;
     }
     output {
       choice output-tags {
         case actual-tag {
           container security-dynamic-address {
             uses security-dynamic-address-block;
           }
         }
         case multichassis-tag {
           container multi-routing-engine-results {
             list multi-routing-engine-item {
               leaf re-name {
                 type string;
               }
               choice output-tags {
                 case actual-tag {
                   container security-dynamic-address {
                     uses security-dynamic-address-block;
                   }
                 }
               }
             }
           }
         }
       }
     }
   }
   rpc get-av-policy {
     description "Show anti-virus policy";
     input {
       uses command-forwarding;
       leaf policy-name {
         description "Policy name";
         type string;
       }
     }
     output {
       choice output-tags {
         case actual-tag {
           container av-policy {
             uses av-policy-block;
           }
         }
         case multichassis-tag {
           container multi-routing-engine-results {
             list multi-routing-engine-item {
               leaf re-name {
                 type string;
               }
               choice output-tags {
                 case actual-tag {
                   container av-policy {
                     uses av-policy-block;
                   }
                 }
               }
             }
           }
         }
       }
     }
   }
   rpc get-av-default-policy {
     description "Show anti-virus default policy";
     input {
       uses command-forwarding;
     }
     output {
       choice output-tags {
         case actual-tag {
           container av-policy {
             uses av-policy-block;
           }
         }
         case multichassis-tag {
           container multi-routing-engine-results {
             list multi-routing-engine-item {
               leaf re-name {
                 type string;
               }
               choice output-tags {
                 case actual-tag {
                   container av-policy {
                     uses av-policy-block;
                   }
                 }
               }
             }
           }
         }
       }
     }
   }
   rpc get-av-statistics {
     description "Show anti-virus statistics";
     input {
       uses command-forwarding;
     }
     output {
       choice output-tags {
         case actual-tag {
           container av-statistics {
             uses av-statistics-block;
           }
         }
         case multichassis-tag {
           container multi-routing-engine-results {
             list multi-routing-engine-item {
               leaf re-name {
                 type string;
               }
               choice output-tags {
                 case actual-tag {
                   container av-statistics {
                     uses av-statistics-block;
                   }
                 }
               }
             }
           }
         }
       }
     }
   }
   rpc get-av-ml-statistics {
     description "Show anti-virus machine learning scan statistics";
     input {
       uses command-forwarding;
     }
     output {
       choice output-tags {
         case actual-tag {
           container av-ml-statistics {
             uses av-ml-statistics-block;
           }
         }
         case multichassis-tag {
           container multi-routing-engine-results {
             list multi-routing-engine-item {
               leaf re-name {
                 type string;
               }
               choice output-tags {
                 case actual-tag {
                   container av-ml-statistics {
                     uses av-ml-statistics-block;
                   }
                 }
               }
             }
           }
         }
       }
     }
   }
   rpc get-aamw-av-sig-exempt-list {
     description "Show anti-virus exempt-list";
     input {
       uses command-forwarding;
     }
     output {
       choice output-tags {
         case actual-tag {
           container aamw-av-sig-exempt-list {
             uses aamw-av-sig-exempt-list-block;
           }
         }
         case multichassis-tag {
           container multi-routing-engine-results {
             list multi-routing-engine-item {
               leaf re-name {
                 type string;
               }
               choice output-tags {
                 case actual-tag {
                   container aamw-av-sig-exempt-list {
                     uses aamw-av-sig-exempt-list-block;
                   }
                 }
               }
             }
           }
         }
       }
     }
   }
   rpc get-appid-application-signature-detail {
     description "Show application signature details";
     input {
       uses command-forwarding;
       leaf application-name {
         type string;
       }
       leaf start {
         description "Show application details from a given position";
         type union {
           type string {
             pattern "<.*>|$.*";
           }
           type uint32 {
             range "1 .. 65535";
           }
         }
       }
       leaf count {
         description "Number of applications to show";
         type union {
           type string {
             pattern "<.*>|$.*";
           }
           type uint32 {
             range "1 .. 65535";
           }
         }
       }
     }
     output {
       choice output-tags {
         case output-tag {
           leaf output {
             type string;
           }
         }
         case actual-tag {
           anyxml appid-application-signature-detail;
         }
         case multichassis-tag {
           anyxml multi-routing-engine-results;
         }
       }
     }
   }
   rpc get-appid-application-signature-summary {
     description "Show application signature summary";
     input {
       uses command-forwarding;
     }
     output {
       choice output-tags {
         case output-tag {
           leaf output {
             type string;
           }
         }
         case actual-tag {
           anyxml appid-application-signature-summary;
         }
         case multichassis-tag {
           anyxml multi-routing-engine-results;
         }
       }
     }
   }
   rpc get-appid-micro-applications-list {
     description "Show micro-applications list";
     input {
       uses command-forwarding;
     }
     output {
       choice output-tags {
         case output-tag {
           leaf output {
             type string;
           }
         }
         case actual-tag {
           anyxml appid-micro-applications-list;
         }
         case multichassis-tag {
           anyxml multi-routing-engine-results;
         }
       }
     }
   }
   rpc get-appid-non-configurable-application-list {
     description "Show non-configurable application list";
     input {
       uses command-forwarding;
     }
     output {
       choice output-tags {
         case output-tag {
           leaf output {
             type string;
           }
         }
         case actual-tag {
           anyxml appid-non-configurable-application-list;
         }
         case multichassis-tag {
           anyxml multi-routing-engine-results;
         }
       }
     }
   }
   rpc get-appid-application-signature {
     description "Show obsolete application list";
     input {
       uses command-forwarding;
     }
     output {
       choice output-tags {
         case actual-tag {
           container appid-application-signature {
             uses appid-application-signature-block;
           }
         }
         case multichassis-tag {
           container multi-routing-engine-results {
             list multi-routing-engine-item {
               leaf re-name {
                 type string;
               }
               choice output-tags {
                 case actual-tag {
                   container appid-application-signature {
                     uses appid-application-signature-block;
                   }
                 }
               }
             }
           }
         }
       }
     }
   }
   rpc get-appid-entry-signature-detail {
     description "Show application/group signature details";
     input {
       leaf entry-name {
         type string;
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
     output {
       choice output-tags {
         case output-tag {
           leaf output {
             type string;
           }
         }
         case actual-tag {
           anyxml appid-entry-signature-detail;
         }
         case multichassis-tag {
           anyxml multi-routing-engine-results;
         }
       }
     }
   }
   rpc get-appid-entry-signature-filter {
     description "Apply filter on entry details";
     input {
       leaf category {
         description "Filter by entry category";
         type string;
       }
       leaf definition {
         description "Filter by predefined/custom entry";
         type enumeration {
           enum "predefined" {
             description "Predefined app";
           }
           enum "custom" {
             description "Customer defined app";
           }
         }
       }
       leaf entry-name {
         description "Filter by entry name";
         type string;
       }
       leaf risk {
         description "Filter by entry risk";
         type union {
           type string {
             pattern "<.*>|$.*";
           }
           type uint32 {
             range "1 .. 5";
           }
         }
       }
       leaf subcategory {
         description "Filter by entry subcategory";
         type string;
       }
       leaf status {
         description "Filter by entry enabled/disabled";
         type enumeration {
           enum "enabled" {
             description "Application is enabled";
           }
           enum "disabled" {
             description "Application is disabled";
           }
         }
       }
       leaf type {
         description "Filter by application/group entry";
         type enumeration {
           enum "application" {
             description "Application";
           }
           enum "group" {
             description "Group";
           }
         }
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
     output {
       choice output-tags {
         case output-tag {
           leaf output {
             type string;
           }
         }
         case actual-tag {
           anyxml appid-entry-signature-detail;
         }
         case multichassis-tag {
           anyxml multi-routing-engine-results;
         }
       }
     }
   }
   rpc get-appid-entry-category-detail {
     description "List of categories of application available";
     output {
       choice output-tags {
         case output-tag {
           leaf output {
             type string;
           }
         }
         case actual-tag {
           anyxml appid-entry-category-detail;
         }
         case multichassis-tag {
           anyxml multi-routing-engine-results;
         }
       }
     }
   }
   rpc get-appid-entry-subcategory-detail {
     description "List of subcategories of application available";
     output {
       choice output-tags {
         case output-tag {
           leaf output {
             type string;
           }
         }
         case actual-tag {
           anyxml appid-entry-subcategory-detail;
         }
         case multichassis-tag {
           anyxml multi-routing-engine-results;
         }
       }
     }
   }
   rpc get-appid-application-group-detail {
     description "Show application group details";
     input {
       uses command-forwarding;
       leaf group-name {
         type string;
       }
     }
     output {
       choice output-tags {
         case output-tag {
           leaf output {
             type string;
           }
         }
         case actual-tag {
           anyxml appid-application-group-detail;
         }
         case multichassis-tag {
           anyxml multi-routing-engine-results;
         }
       }
     }
   }
   rpc get-appid-application-group-summary {
     description "Show application group summary";
     input {
       uses command-forwarding;
     }
     output {
       choice output-tags {
         case output-tag {
           leaf output {
             type string;
           }
         }
         case actual-tag {
           anyxml appid-application-group-summary;
         }
         case multichassis-tag {
           anyxml multi-routing-engine-results;
         }
       }
     }
   }
   rpc get-appid-application-group {
     description "Show obsolete groups list";
     input {
       uses command-forwarding;
     }
     output {
       choice output-tags {
         case actual-tag {
           container appid-application-group {
             uses appid-application-group-block;
           }
         }
         case multichassis-tag {
           container multi-routing-engine-results {
             list multi-routing-engine-item {
               leaf re-name {
                 type string;
               }
               choice output-tags {
                 case actual-tag {
                   container appid-application-group {
                     uses appid-application-group-block;
                   }
                 }
               }
             }
           }
         }
       }
     }
   }
   rpc get-appid-application-system-cache {
     description "Show application system cache";
     input {
       uses command-forwarding;
       choice lsys {
         case logical-system {
         }
         case tenant {
         }
       }
     }
     output {
       choice output-tags {
         case actual-tag {
           container appid-application-system-cache-information {
             uses appid-application-system-cache-information-block;
           }
         }
         case multichassis-tag {
           container multi-routing-engine-results {
             list multi-routing-engine-item {
               leaf re-name {
                 type string;
               }
               choice output-tags {
                 case actual-tag {
                   container appid-application-system-cache-information {
                     uses appid-application-system-cache-information-block;
                   }
                 }
               }
             }
           }
         }
       }
     }
   }
   rpc get-appid-counter {
     description "Show the application identification counters";
     input {
       uses command-forwarding;
       choice lsys {
         case logical-system {
         }
         case tenant {
         }
       }
     }
     output {
       choice output-tags {
         case actual-tag {
           container appid-counter-information {
             uses appid-counter-information-block;
           }
         }
         case multichassis-tag {
           container multi-routing-engine-results {
             list multi-routing-engine-item {
               leaf re-name {
                 type string;
               }
               choice output-tags {
                 case actual-tag {
                   container appid-counter-information {
                     uses appid-counter-information-block;
                   }
                 }
               }
             }
           }
         }
       }
     }
   }
   rpc get-appid-counter-encrypted {
     description "Counters for SSL encrypted sessions";
     status deprecated;
     input {
       uses command-forwarding;
     }
     output {
       choice output-tags {
         case actual-tag {
           container appid-counter-information {
             uses appid-counter-information-block;
           }
         }
         case multichassis-tag {
           container multi-routing-engine-results {
             list multi-routing-engine-item {
               leaf re-name {
                 type string;
               }
               choice output-tags {
                 case actual-tag {
                   container appid-counter-information {
                     uses appid-counter-information-block;
                   }
                 }
               }
             }
           }
         }
       }
     }
   }
   rpc get-commit-status {
     description "Show config commit status";
     input {
       uses command-forwarding;
     }
     output {
       choice output-tags {
         case actual-tag {
           container appid-commit-status {
             uses appid-commit-status-block;
           }
         }
         case multichassis-tag {
           container multi-routing-engine-results {
             list multi-routing-engine-item {
               leaf re-name {
                 type string;
               }
               choice output-tags {
                 case actual-tag {
                   container appid-commit-status {
                     uses appid-commit-status-block;
                   }
                 }
               }
             }
           }
         }
       }
     }
   }
   rpc get-appid-application-statistics {
     description "Show the application statistics";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
     output {
       choice output-tags {
         case actual-tag {
           container appid-application-statistics-information {
             uses appid-application-statistics-information-block;
           }
         }
         case multichassis-tag {
           container multi-routing-engine-results {
             list multi-routing-engine-item {
               leaf re-name {
                 type string;
               }
               choice output-tags {
                 case actual-tag {
                   container appid-application-statistics-information {
                     uses appid-application-statistics-information-block;
                   }
                 }
               }
             }
           }
         }
       }
     }
   }
   rpc get-appid-application-statistics-detail {
     description "Show the application statistics detail";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
     output {
       choice output-tags {
         case output-tag {
           leaf output {
             type string;
           }
         }
         case actual-tag {
           anyxml appid-application-statistics-detail;
         }
         case multichassis-tag {
           anyxml multi-routing-engine-results;
         }
       }
     }
   }
   rpc get-appid-application-group-statistics {
     description "Show the application group statistics";
     input {
       uses command-forwarding;
       choice lsys {
         case logical-system {
         }
         case tenant {
         }
       }
       leaf interval {
         description "Displays current interval application group statistics irrespective of interval";
         default "1";
         type union {
           type string {
             pattern "<.*>|$.*";
           }
           type uint32 {
             range 1;
           }
         }
       }
     }
     output {
       choice output-tags {
         case actual-tag {
           container appid-application-group-statistics-information {
             uses appid-application-group-statistics-information-block;
           }
         }
         case multichassis-tag {
           container multi-routing-engine-results {
             list multi-routing-engine-item {
               leaf re-name {
                 type string;
               }
               choice output-tags {
                 case actual-tag {
                   container appid-application-group-statistics-information {
                     uses appid-application-group-statistics-information-block;
                   }
                 }
               }
             }
           }
         }
       }
     }
   }
   rpc get-application-id-status-information {
     description "Show the application identification status";
     input {
       uses command-forwarding;
     }
     output {
       choice output-tags {
         case actual-tag {
           container appid-status-information {
             uses appid-status-information-block;
           }
         }
         case multichassis-tag {
           container multi-routing-engine-results {
             list multi-routing-engine-item {
               leaf re-name {
                 type string;
               }
               choice output-tags {
                 case actual-tag {
                   container appid-status-information {
                     uses appid-status-information-block;
                   }
                 }
               }
             }
           }
         }
       }
     }
   }
   rpc get-appid-package-version {
     description "Show the current application package version";
     input {
       uses command-forwarding;
       leaf detail {
         description "Detail status of sigpack & failed sigpack version";
         type empty;
       }
     }
     output {
       choice output-tags {
         case actual-tag {
           container appid-package-version {
             uses appid-package-version-block;
           }
         }
         case multichassis-tag {
           container multi-routing-engine-results {
             list multi-routing-engine-item {
               leaf re-name {
                 type string;
               }
               choice output-tags {
                 case actual-tag {
                   container appid-package-version {
                     uses appid-package-version-block;
                   }
                 }
               }
             }
           }
         }
       }
     }
   }
   rpc get-appid-pkt-capture-counter {
     description "Show the application identification packet capture counters";
     input {
       uses command-forwarding;
     }
     output {
       choice output-tags {
         case actual-tag {
           container appid-pkt-capture-counter-information {
             uses appid-pkt-capture-counter-information-block;
           }
         }
         case multichassis-tag {
           container multi-routing-engine-results {
             list multi-routing-engine-item {
               leaf re-name {
                 type string;
               }
               choice output-tags {
                 case actual-tag {
                   container appid-pkt-capture-counter-information {
                     uses appid-pkt-capture-counter-information-block;
                   }
                 }
               }
             }
           }
         }
       }
     }
   }
   rpc get-recent-appid-sigpack-information {
     description "Show the recent application package versions";
     input {
       uses command-forwarding;
     }
     output {
       choice output-tags {
         case actual-tag {
           container recent-appid-sigpack-information {
             uses recent-appid-sigpack-information-block;
           }
         }
         case multichassis-tag {
           container multi-routing-engine-results {
             list multi-routing-engine-item {
               leaf re-name {
                 type string;
               }
               choice output-tags {
                 case actual-tag {
                   container recent-appid-sigpack-information {
                     uses recent-appid-sigpack-information-block;
                   }
                 }
               }
             }
           }
         }
       }
     }
   }
   rpc get-lrf-statistics {
     description "Show lrf statistics";
     output {
       choice output-tags {
         case actual-tag {
           container lrf-statistics-summary {
             uses lrf-statistics-summary-block;
           }
         }
         case multichassis-tag {
           container multi-routing-engine-results {
             list multi-routing-engine-item {
               leaf re-name {
                 type string;
               }
               choice output-tags {
                 case actual-tag {
                   container lrf-statistics-summary {
                     uses lrf-statistics-summary-block;
                   }
                 }
               }
             }
           }
         }
       }
     }
   }
   rpc get-lrf-collector-statistics {
     description "Show lrf collector statistics";
     input {
       leaf collector-name {
         description "Name of collector";
         type string;
       }
     }
     output {
       choice output-tags {
         case actual-tag {
           container lrf-collector-statistics-summary {
             uses lrf-collector-statistics-summary-block;
           }
         }
         case multichassis-tag {
           container multi-routing-engine-results {
             list multi-routing-engine-item {
               leaf re-name {
                 type string;
               }
               choice output-tags {
                 case actual-tag {
                   container lrf-collector-statistics-summary {
                     uses lrf-collector-statistics-summary-block;
                   }
                 }
               }
             }
           }
         }
       }
     }
   }
   rpc get-lrf-rule-statistics {
     description "Show lrf rule statistics";
     input {
       leaf rule-name {
         description "Name of rule";
         type string;
       }
     }
     output {
       choice output-tags {
         case actual-tag {
           container lrf-rule-statistics-summary {
             uses lrf-rule-statistics-summary-block;
           }
         }
         case multichassis-tag {
           container multi-routing-engine-results {
             list multi-routing-engine-item {
               leaf re-name {
                 type string;
               }
               choice output-tags {
                 case actual-tag {
                   container lrf-rule-statistics-summary {
                     uses lrf-rule-statistics-summary-block;
                   }
                 }
               }
             }
           }
         }
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       choice output-tags {
         case actual-tag {
           container lrf-template {
             uses lrf-template-block;
           }
         }
         case multichassis-tag {
           container multi-routing-engine-results {
             list multi-routing-engine-item {
               leaf re-name {
                 type string;
               }
               choice output-tags {
                 case actual-tag {
                   container lrf-template {
                     uses lrf-template-block;
                   }
                 }
               }
             }
           }
         }
       }
     }
   }
   rpc get-service-accounting-information {
     description "Show sampled accounting service";
     output {
       choice output-tags {
         case output-tag {
           leaf output {
             type string;
           }
         }
         case actual-tag {
           anyxml service-accounting-information;
         }
         case multichassis-tag {
           anyxml multi-routing-engine-results;
         }
       }
     }
   }
   rpc get-service-accounting-status-information {
     description "Show service accounting parameters";
     input {
       leaf status-information {
         description "Name of service, wildcard, or 'all'";
         type string;
       }
     }
     output {
       choice output-tags {
         case output-tag {
           leaf output {
             type string;
           }
         }
         case actual-tag {
           anyxml service-accounting-status-information;
         }
         case multichassis-tag {
           anyxml multi-routing-engine-results;
         }
       }
     }
   }
   rpc get-service-accounting-status-inline-jflow-information {
     description "Show service accounting inline Jflow parameters";
     input {
       leaf inline-jflow-information {
         description "FPC Slot for inline Jflow";
         type union {
           type string {
             pattern "<.*>|$.*";
           }
           type uint32;
         }
       }
     }
     output {
       choice output-tags {
         case actual-tag {
           container services-accounting-information {
             uses services-accounting-information-block;
           }
         }
         case multichassis-tag {
           container multi-routing-engine-results {
             list multi-routing-engine-item {
               leaf re-name {
                 type string;
               }
               choice output-tags {
                 case actual-tag {
                   container services-accounting-information {
                     uses services-accounting-information-block;
                   }
                 }
               }
             }
           }
         }
       }
     }
   }
   rpc get-service-accounting-usage-information {
     description "Show CPU usage";
     input {
       leaf usage-information {
         description "Name of service, wildcard, or 'all'";
         type string;
       }
     }
     output {
       choice output-tags {
         case output-tag {
           leaf output {
             type string;
           }
         }
         case actual-tag {
           anyxml service-accounting-usage-information;
         }
         case multichassis-tag {
           anyxml multi-routing-engine-results;
         }
       }
     }
   }
   rpc get-service-accounting-memory-information {
     description "Show memory information";
     input {
       leaf memory-information {
         description "Name of service, wildcard, or 'all'";
         type string;
       }
     }
     output {
       choice output-tags {
         case output-tag {
           leaf output {
             type string;
           }
         }
         case actual-tag {
           anyxml service-accounting-memory-information;
         }
         case multichassis-tag {
           anyxml multi-routing-engine-results;
         }
       }
     }
   }
   rpc get-service-accounting-flow-information {
     description "Show flow information";
     input {
       leaf flow-information {
         description "Name of service, wildcard, or 'all'";
         type string;
       }
       leaf logical-system {
         description "Name of logical system";
         type string {
         }
       }
     }
     output {
       choice output-tags {
         case output-tag {
           leaf output {
             type string;
           }
         }
         case actual-tag {
           anyxml service-accounting-flow-information;
         }
         case multichassis-tag {
           anyxml multi-routing-engine-results;
         }
       }
     }
   }
   rpc get-service-accounting-status-inline-jflow-flow-information {
     description "Show service accounting inline Jflow flow information";
     input {
       leaf inline-jflow-flow-information {
         description "FPC Slot for inline Jflow";
         type union {
           type string {
             pattern "<.*>|$.*";
           }
           type uint32;
         }
       }
     }
     output {
       choice output-tags {
         case actual-tag {
           container services-accounting-information {
             uses services-accounting-information-block;
           }
         }
         case multichassis-tag {
           container multi-routing-engine-results {
             list multi-routing-engine-item {
               leaf re-name {
                 type string;
               }
               choice output-tags {
                 case actual-tag {
                   container services-accounting-information {
                     uses services-accounting-information-block;
                   }
                 }
               }
             }
           }
         }
       }
     }
   }
   rpc get-service-accounting-flow-detail {
     description "Show flow detail";
     input {
       leaf flow-detail-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
       leaf source-as {
         description "Filter term source AS";
         type union {
           type uint32;
           type string {
             pattern "<.*>|$.*";
           }
         }
       }
       leaf destination-as {
         description "Filter term destination AS";
         type union {
           type uint32;
           type string {
             pattern "<.*>|$.*";
           }
         }
       }
       leaf tos {
         description "Filter term ToS";
         type union {
           type uint32;
           type string {
             pattern "<.*>|$.*";
           }
         }
       }
       leaf proto {
         description "Filter term protocol";
         type union {
           type uint32;
           type string {
             pattern "<.*>|$.*";
           }
         }
       }
     }
     output {
       choice output-tags {
         case output-tag {
           leaf output {
             type string;
           }
         }
         case actual-tag {
           anyxml service-accounting-flow-detail;
         }
         case multichassis-tag {
           anyxml multi-routing-engine-results;
         }
       }
     }
   }
   rpc get-service-accounting-aggregation-information {
     description "Show aggregation information";
     output {
       choice output-tags {
         case output-tag {
           leaf output {
             type string;
           }
         }
         case actual-tag {
           anyxml service-accounting-aggregation-information;
         }
         case multichassis-tag {
           anyxml multi-routing-engine-results;
         }
       }
     }
   }
   rpc get-service-accounting-aggregation-as-information {
     description "Show aggregation type AS";
     input {
       leaf as-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type union {
           type uint32;
           type string {
             pattern "<.*>|$.*";
           }
         }
       }
       leaf destination-as {
         description "Filter term destination AS";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output-tags {
         case output-tag {
           leaf output {
             type string;
           }
         }
         case actual-tag {
           anyxml service-accounting-aggregation-as-information;
         }
         case multichassis-tag {
           anyxml multi-routing-engine-results;
         }
       }
     }
   }
   rpc get-service-accounting-aggregation-protocol-port-information {
     description "Show aggregation type protocol-port";
     input {
       leaf protocol-port-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type union {
           type uint32;
           type string {
             pattern "<.*>|$.*";
           }
         }
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
     }
     output {
       choice output-tags {
         case output-tag {
           leaf output {
             type string;
           }
         }
         case actual-tag {
           anyxml service-accounting-aggregation-protocol-port-information;
         }
         case multichassis-tag {
           anyxml multi-routing-engine-results;
         }
       }
     }
   }
   rpc get-service-accounting-aggregation-source-prefix-information {
     description "Show aggregation type source-prefix";
     input {
       leaf source-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
     }
     output {
       choice output-tags {
         case output-tag {
           leaf output {
             type string;
           }
         }
         case actual-tag {
           anyxml service-accounting-aggregation-source-prefix-information;
         }
         case multichassis-tag {
           anyxml multi-routing-engine-results;
         }
       }
     }
   }
   rpc get-service-accounting-aggregation-destination-prefix-information {
     description "Show aggregation type destination-prefix";
     input {
       leaf destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output-tags {
         case output-tag {
           leaf output {
             type string;
           }
         }
         case actual-tag {
           anyxml service-accounting-aggregation-destination-prefix-information;
         }
         case multichassis-tag {
           anyxml multi-routing-engine-results;
         }
       }
     }
   }
   rpc get-service-accounting-aggregation-source-destination-prefix-information {
     description "Show aggregation type source-destination-prefix";
     input {
       leaf source-destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output-tags {
         case output-tag {
           leaf output {
             type string;
           }
         }
         case actual-tag {
           anyxml service-accounting-aggregation-source-destination-prefix-information;
         }
         case multichassis-tag {
           anyxml multi-routing-engine-results;
         }
       }
     }
   }
   rpc get-service-accounting-aggregation-template-information {
     description "Show aggregation type template";
     input {
       leaf template-name {
         description "Name of template";
         type string;
         mandatory true;
       }
       leaf logical-system {
         description "Name of logical system";
         type string {
         }
       }
       leaf display {
         default "terse";
         type enumeration {
           enum "extensive" {
             description "Display extensive output";
           }
           enum "detail" {
             description "Display detailed output";
           }
           enum "terse" {
             description "Display terse output (default)";
           }
         }
       }
     }
     output {
       choice output-tags {
         case output-tag {
           leaf output {
             type string;
           }
         }
         case actual-tag {
           anyxml service-accounting-aggregation-template-information;
         }
         case multichassis-tag {
           anyxml multi-routing-engine-results;
         }
       }
     }
   }
   rpc get-service-accounting-errors-information {
     description "Show error statistics";
     input {
       leaf error-information {
         description "Name of service, wildcard, or 'all'";
         type string;
       }
     }
     output {
       choice output-tags {
         case output-tag {
           leaf output {
             type string;
           }
         }
         case actual-tag {
           anyxml service-accounting-errors-information;
         }
         case multichassis-tag {
           anyxml multi-routing-engine-results;
         }
       }
     }
   }
   rpc get-service-accounting-error-inline-jflow-information {
     description "Show service accounting inline Jflow error information";
     input {
       leaf inline-jflow-error-information {
         description "FPC Slot for inline Jflow";
         type union {
           type string {
             pattern "<.*>|$.*";
           }
           type uint32;
         }
       }
     }
     output {
       choice output-tags {
         case actual-tag {
           container services-accounting-information {
             uses services-accounting-information-block;
           }
         }
         case multichassis-tag {
           container multi-routing-engine-results {
             list multi-routing-engine-item {
               leaf re-name {
                 type string;
               }
               choice output-tags {
                 case actual-tag {
                   container services-accounting-information {
                     uses services-accounting-information-block;
                   }
                 }
               }
             }
           }
         }
       }
     }
   }
   rpc get-packet-distribution-information {
     description "Show packet size distribution";
     input {
       leaf packet-size-distribution-information {
         description "Name of service, wildcard, or 'all'";
         type string;
       }
     }
     output {
       choice output-tags {
         case output-tag {
           leaf output {
             type string;
           }
         }
         case actual-tag {
           anyxml packet-distribution-information;
         }
         case multichassis-tag {
           anyxml multi-routing-engine-results;
         }
       }
     }
   }
   rpc get-dnssnoop-cache {
     description "Show DNS-Snooping cache";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dnssnoop-cache {
             uses dnssnoop-cache-block;
           }
         }
         case multichassis-tag {
           container multi-routing-engine-results {
             list multi-routing-engine-item {
               leaf re-name {
                 type string;
               }
               choice output-tags {
                 case actual-tag {
                   container dnssnoop-cache {
                     uses dnssnoop-cache-block;
                   }
                 }
               }
             }
           }
         }
       }
     }
   }
   rpc get-dnssnoop-counters {
     description "Show DNS-Snooping counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dnssnoop-counters {
             uses dnssnoop-counters-block;
           }
         }
         case multichassis-tag {
           container multi-routing-engine-results {
             list multi-routing-engine-item {
               leaf re-name {
                 type string;
               }
               choice output-tags {
                 case actual-tag {
                   container dnssnoop-counters {
                     uses dnssnoop-counters-block;
                   }
                 }
               }
             }
           }
         }
       }
     }
   }
   rpc get-icap-redir-statistics {
     description "Show ICAP redirect service statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container icap-redir-statistics {
             uses icap-redir-statistics-block;
           }
         }
         case multichassis-tag {
           container multi-routing-engine-results {
             list multi-routing-engine-item {
               leaf re-name {
                 type string;
               }
               choice output-tags {
                 case actual-tag {
                   container icap-redir-statistics {
                     uses icap-redir-statistics-block;
                   }
                 }
               }
             }
           }
         }
       }
     }
   }
   rpc get-icap-redir-status {
     description "Show ICAP redirect profile status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container icap-redir-status {
             uses icap-redir-status-block;
           }
         }
         case multichassis-tag {
           container multi-routing-engine-results {
             list multi-routing-engine-item {
               leaf re-name {
                 type string;
               }
               choice output-tags {
                 case actual-tag {
                   container icap-redir-status {
                     uses icap-redir-status-block;
                   }
                 }
               }
             }
           }
         }
       }
     }
   }
   rpc get-services-firewall-policies {
     description "Show services policies";
     input {
       uses command-forwarding;
       leaf policy-name {
         description "Show the policy information matching the given policy name";
         type string;
       }
       leaf detail {
         description "Show the detailed information";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
       leaf stateful-firewall-rule {
         description "Show policy info matching given stateful-firewall-rule name";
         type string;
       }
     }
     output {
       choice output-tags {
         case output-tag {
           leaf output {
             type string;
           }
         }
         case actual-tag {
           anyxml services-policies;
         }
         case multichassis-tag {
           anyxml multi-routing-engine-results;
         }
       }
     }
   }
   rpc get-services-firewall-policies-information {
     description "Show the policy information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml policy-internal-information;
         }
         case multichassis-tag {
           anyxml multi-routing-engine-results;
         }
       }
     }
   }
   rpc get-services-policy-checksum-information {
     description "Show policy information checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       choice output-tags {
         case output-tag {
           leaf output {
             type string;
           }
         }
         case actual-tag {
           anyxml policy-context-checksum-info;
         }
         case multichassis-tag {
           anyxml multi-routing-engine-results;
         }
       }
     }
   }
   rpc get-services-policies-hit-count {
     description "Show the hit count of policies";
     input {
       uses command-forwarding;
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container policy-hit-count-service-router {
             uses policy-hit-count-service-router-block;
           }
         }
         case multichassis-tag {
           container multi-routing-engine-results {
             list multi-routing-engine-item {
               leaf re-name {
                 type string;
               }
               choice output-tags {
                 case actual-tag {
                   container policy-hit-count-service-router {
                     uses policy-hit-count-service-router-block;
                   }
                 }
               }
             }
           }
         }
       }
     }
   }
   rpc get-secintel-category-feed {
     description "Show category detail information";
     input {
       uses command-forwarding;
       leaf category-name {
         description "Category name";
         type string;
         mandatory true;
       }
       leaf feed-name {
         description "Feed name";
         type string;
         mandatory true;
       }
       leaf start {
         description "Start number";
         type union {
           type uint32;
           type string {
             pattern "<.*>|$.*";
           }
         }
       }
       leaf count {
         description "Total number";
         type union {
           type uint32;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml secintel-category-feed;
         }
         case multichassis-tag {
           anyxml multi-routing-engine-results;
         }
       }
     }
   }
   rpc get-secintel-category-list {
     description "Show all category names";
     input {
       uses command-forwarding;
     }
     output {
       choice output-tags {
         case output-tag {
           leaf output {
             type string;
           }
         }
         case actual-tag {
           anyxml secintel-category-list;
         }
         case multichassis-tag {
           anyxml multi-routing-engine-results;
         }
       }
     }
   }
   rpc get-secintel-category-summary {
     description "Show category summary";
     input {
       uses command-forwarding;
       leaf category-name {
         description "Show specified category summary";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml secintel-category-summary;
         }
         case multichassis-tag {
           anyxml multi-routing-engine-results;
         }
       }
     }
   }
   rpc get-secintel-recommended-action {
     description "Show security intelligence recommended action ";
     input {
       uses command-forwarding;
       leaf category-name {
         description "Show category recommended action";
         type string;
       }
     }
     output {
       choice output-tags {
         case actual-tag {
           container secintel-recommended-action {
             uses secintel-recommended-action-block;
           }
         }
         case multichassis-tag {
           container multi-routing-engine-results {
             list multi-routing-engine-item {
               leaf re-name {
                 type string;
               }
               choice output-tags {
                 case actual-tag {
                   container secintel-recommended-action {
                     uses secintel-recommended-action-block;
                   }
                 }
               }
             }
           }
         }
       }
     }
   }
   rpc get-secintel-redirect-files {
     description "Show redirect files information";
     input {
       uses command-forwarding;
       leaf file-name {
         description "Show redirect-file content";
         type string {
         }
       }
     }
     output {
       choice output-tags {
         case actual-tag {
           container secintel-redirect-files {
             uses secintel-redirect-files-block;
           }
         }
         case multichassis-tag {
           container multi-routing-engine-results {
             list multi-routing-engine-item {
               leaf re-name {
                 type string;
               }
               choice output-tags {
                 case actual-tag {
                   container secintel-redirect-files {
                     uses secintel-redirect-files-block;
                   }
                 }
               }
             }
           }
         }
       }
     }
   }
   rpc get-secintel-update-status {
     description "Show update status";
     input {
       uses command-forwarding;
     }
     output {
       choice output-tags {
         case output-tag {
           leaf output {
             type string;
           }
         }
         case actual-tag {
           anyxml secintel-update-status;
         }
         case multichassis-tag {
           anyxml multi-routing-engine-results;
         }
       }
     }
   }
   rpc get-secintel-post-status {
     description "Show sec-profiling feed post status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml secintel-post-status;
         }
         case multichassis-tag {
           anyxml multi-routing-engine-results;
         }
       }
     }
   }
   rpc get-secintel-statistics {
     description "Show security intelligence statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container secintel-statistics {
             uses secintel-statistics-block;
           }
         }
         case multichassis-tag {
           container multi-routing-engine-results {
             list multi-routing-engine-item {
               leaf re-name {
                 type string;
               }
               choice output-tags {
                 case actual-tag {
                   container secintel-statistics {
                     uses secintel-statistics-block;
                   }
                 }
               }
             }
           }
         }
       }
     }
   }
   rpc get-secintel-statistics-profile {
     description "Show security intelligence profile statistics";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml secintel-statistics-profile;
         }
         case multichassis-tag {
           anyxml multi-routing-engine-results;
         }
       }
     }
   }
   rpc get-dns-statistics {
     description "Show security intelligence dns-statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dns-statistics {
             uses dns-statistics-block;
           }
         }
         case multichassis-tag {
           container multi-routing-engine-results {
             list multi-routing-engine-item {
               leaf re-name {
                 type string;
               }
               choice output-tags {
                 case actual-tag {
                   container dns-statistics {
                     uses dns-statistics-block;
                   }
                 }
               }
             }
           }
         }
       }
     }
   }
   rpc get-dns-statistics-profile {
     description "Show security intelligence dns-profile statistics";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml dns-statistics-profile;
         }
         case multichassis-tag {
           anyxml multi-routing-engine-results;
         }
       }
     }
   }
   rpc get-dns-filtering-cache {
     description "Show DNS-Filtering cache";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dns-filtering-cache {
             uses dns-filtering-cache-block;
           }
         }
         case multichassis-tag {
           container multi-routing-engine-results {
             list multi-routing-engine-item {
               leaf re-name {
                 type string;
               }
               choice output-tags {
                 case actual-tag {
                   container dns-filtering-cache {
                     uses dns-filtering-cache-block;
                   }
                 }
               }
             }
           }
         }
       }
     }
   }
   rpc get-dns-filtering-cache-summary {
     description "Show DNS-Filtering Cache Summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dns-filtering-cache-summary {
             uses dns-filtering-cache-summary-block;
           }
         }
         case multichassis-tag {
           container multi-routing-engine-results {
             list multi-routing-engine-item {
               leaf re-name {
                 type string;
               }
               choice output-tags {
                 case actual-tag {
                   container dns-filtering-cache-summary {
                     uses dns-filtering-cache-summary-block;
                   }
                 }
               }
             }
           }
         }
       }
     }
   }
   rpc get-dns-filtering-cache-c2 {
     description "Show DNS-Filtering Cache C2-Entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dns-filtering-cache-c2 {
             uses dns-filtering-cache-c2-block;
           }
         }
         case multichassis-tag {
           container multi-routing-engine-results {
             list multi-routing-engine-item {
               leaf re-name {
                 type string;
               }
               choice output-tags {
                 case actual-tag {
                   container dns-filtering-cache-c2 {
                     uses dns-filtering-cache-c2-block;
                   }
                 }
               }
             }
           }
         }
       }
     }
   }
   rpc get-dns-filtering-cache-benign {
     description "Show DNS-Filtering Cache Benign-Entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container dns-filtering-cache-benign {
             uses dns-filtering-cache-benign-block;
           }
         }
         case multichassis-tag {
           container multi-routing-engine-results {
             list multi-routing-engine-item {
               leaf re-name {
                 type string;
               }
               choice output-tags {
                 case actual-tag {
                   container dns-filtering-cache-benign {
                     uses dns-filtering-cache-benign-block;
                   }
                 }
               }
             }
           }
         }
       }
     }
   }
   rpc get-web-transparent-proxy-session-detail {
     description "Show transparent web proxy session detail";
     input {
       uses command-forwarding;
     }
     output {
       choice output-tags {
         case actual-tag {
           container web-transparent-proxy-session-information {
             uses web-transparent-proxy-session-information-block;
           }
         }
         case multichassis-tag {
           container multi-routing-engine-results {
             list multi-routing-engine-item {
               leaf re-name {
                 type string;
               }
               choice output-tags {
                 case actual-tag {
                   container web-transparent-proxy-session-information {
                     uses web-transparent-proxy-session-information-block;
                   }
                 }
               }
             }
           }
         }
       }
     }
   }
   rpc get-web-transparent-proxy-session-summary {
     description "Show transparent web proxy session summary";
     input {
       uses command-forwarding;
     }
     output {
       choice output-tags {
         case actual-tag {
           container web-transparent-proxy-session-information {
             uses web-transparent-proxy-session-information-block;
           }
         }
         case multichassis-tag {
           container multi-routing-engine-results {
             list multi-routing-engine-item {
               leaf re-name {
                 type string;
               }
               choice output-tags {
                 case actual-tag {
                   container web-transparent-proxy-session-information {
                     uses web-transparent-proxy-session-information-block;
                   }
                 }
               }
             }
           }
         }
       }
     }
   }
   rpc get-web-transparent-proxy-statistics {
     description "Show transparent web proxy statistics";
     input {
       uses command-forwarding;
     }
     output {
       choice output-tags {
         case actual-tag {
           container web-transparent-proxy-statistics {
             uses web-transparent-proxy-statistics-block;
           }
         }
         case multichassis-tag {
           container multi-routing-engine-results {
             list multi-routing-engine-item {
               leaf re-name {
                 type string;
               }
               choice output-tags {
                 case actual-tag {
                   container web-transparent-proxy-statistics {
                     uses web-transparent-proxy-statistics-block;
                   }
                 }
               }
             }
           }
         }
       }
     }
   }
   rpc get-web-explicit-proxy-session-detail {
     description "Show web explicit-proxy session detail";
     input {
       uses command-forwarding;
     }
     output {
       choice output-tags {
         case actual-tag {
           container web-explicit-proxy-session-information {
             uses web-explicit-proxy-session-information-block;
           }
         }
         case multichassis-tag {
           container multi-routing-engine-results {
             list multi-routing-engine-item {
               leaf re-name {
                 type string;
               }
               choice output-tags {
                 case actual-tag {
                   container web-explicit-proxy-session-information {
                     uses web-explicit-proxy-session-information-block;
                   }
                 }
               }
             }
           }
         }
       }
     }
   }
   rpc get-web-explicit-proxy-session-summary {
     description "Show web explicit proxy session summary";
     input {
       uses command-forwarding;
     }
     output {
       choice output-tags {
         case actual-tag {
           container web-explicit-proxy-session-information {
             uses web-explicit-proxy-session-information-block;
           }
         }
         case multichassis-tag {
           container multi-routing-engine-results {
             list multi-routing-engine-item {
               leaf re-name {
                 type string;
               }
               choice output-tags {
                 case actual-tag {
                   container web-explicit-proxy-session-information {
                     uses web-explicit-proxy-session-information-block;
                   }
                 }
               }
             }
           }
         }
       }
     }
   }
   rpc get-web-explicit-proxy-statistics {
     description "Show web explicit proxy staticstics";
     input {
       uses command-forwarding;
     }
     output {
       choice output-tags {
         case actual-tag {
           container web-explicit-proxy-statistics {
             uses web-explicit-proxy-statistics-block;
           }
         }
         case multichassis-tag {
           container multi-routing-engine-results {
             list multi-routing-engine-item {
               leaf re-name {
                 type string;
               }
               choice output-tags {
                 case actual-tag {
                   container web-explicit-proxy-statistics {
                     uses web-explicit-proxy-statistics-block;
                   }
                 }
               }
             }
           }
         }
       }
     }
   }
   rpc get-web-proxy-dns-fc-entries {
     description "Show web proxy forwarding cache information";
     input {
       uses command-forwarding;
     }
     output {
       choice output-tags {
         case actual-tag {
           container web-proxy-dns-fc-entries {
             uses web-proxy-dns-fc-entries-block;
           }
         }
         case multichassis-tag {
           container multi-routing-engine-results {
             list multi-routing-engine-item {
               leaf re-name {
                 type string;
               }
               choice output-tags {
                 case actual-tag {
                   container web-proxy-dns-fc-entries {
                     uses web-proxy-dns-fc-entries-block;
                   }
                 }
               }
             }
           }
         }
       }
     }
   }
   rpc get-web-proxy-dns-fc-entries-dump {
     description "Show web proxy forwarding cache information for specified dns-name";
     input {
       leaf dns-name {
         description "Show DNS cache matching the given DNS name";
         type string;
         mandatory true;
       }
     }
     output {
       choice output-tags {
         case actual-tag {
           container web-proxy-dns-fc-entries {
             uses web-proxy-dns-fc-entries-block;
           }
         }
         case multichassis-tag {
           container multi-routing-engine-results {
             list multi-routing-engine-item {
               leaf re-name {
                 type string;
               }
               choice output-tags {
                 case actual-tag {
                   container web-proxy-dns-fc-entries {
                     uses web-proxy-dns-fc-entries-block;
                   }
                 }
               }
             }
           }
         }
       }
     }
   }
   rpc get-web-proxy-dns-fc-statistics {
     description "Show web proxy staticstics";
     input {
       uses command-forwarding;
     }
     output {
       choice output-tags {
         case actual-tag {
           container web-proxy-dns-fc-statistics {
             uses web-proxy-dns-fc-statistics-block;
           }
         }
         case multichassis-tag {
           container multi-routing-engine-results {
             list multi-routing-engine-item {
               leaf re-name {
                 type string;
               }
               choice output-tags {
                 case actual-tag {
                   container web-proxy-dns-fc-statistics {
                     uses web-proxy-dns-fc-statistics-block;
                   }
                 }
               }
             }
           }
         }
       }
     }
   }
   rpc get-web-proxy-dns-gc-entries {
     description "Show web proxy global cache information";
     input {
       uses command-forwarding;
     }
     output {
       choice output-tags {
         case actual-tag {
           container web-proxy-dns-fc-entries {
             uses web-proxy-dns-fc-entries-block;
           }
         }
         case multichassis-tag {
           container multi-routing-engine-results {
             list multi-routing-engine-item {
               leaf re-name {
                 type string;
               }
               choice output-tags {
                 case actual-tag {
                   container web-proxy-dns-fc-entries {
                     uses web-proxy-dns-fc-entries-block;
                   }
                 }
               }
             }
           }
         }
       }
     }
   }
   rpc get-web-proxy-dns-gc-entries-dump {
     description "Show web proxy global cache information for specified dnsname";
     input {
       uses command-forwarding;
       leaf dns-name {
         description "Show DNS cache matching the given DNS name";
         type string;
       }
     }
     output {
       choice output-tags {
         case actual-tag {
           container web-proxy-dns-fc-entries {
             uses web-proxy-dns-fc-entries-block;
           }
         }
         case multichassis-tag {
           container multi-routing-engine-results {
             list multi-routing-engine-item {
               leaf re-name {
                 type string;
               }
               choice output-tags {
                 case actual-tag {
                   container web-proxy-dns-fc-entries {
                     uses web-proxy-dns-fc-entries-block;
                   }
                 }
               }
             }
           }
         }
       }
     }
   }
   rpc get-web-proxy-dns-gc-statistics {
     description "Show web proxy global staticstics";
     input {
       uses command-forwarding;
     }
     output {
       choice output-tags {
         case actual-tag {
           container web-proxy-dns-gc-statistics {
             uses web-proxy-dns-gc-statistics-block;
           }
         }
         case multichassis-tag {
           container multi-routing-engine-results {
             list multi-routing-engine-item {
               leaf re-name {
                 type string;
               }
               choice output-tags {
                 case actual-tag {
                   container web-proxy-dns-gc-statistics {
                     uses web-proxy-dns-gc-statistics-block;
                   }
                 }
               }
             }
           }
         }
       }
     }
   }
   rpc get-analytics-agent-information {
     description "Show analytics service agent information";
     input {
       leaf level {
         default "brief";
         type enumeration {
           enum "detail" {
             description "Display detailed data";
           }
           enum "brief" {
             description "Display brief data (default)";
           }
         }
       }
     }
     output {
       choice output-tags {
         case actual-tag {
           container analytics-agent-information {
             uses analytics-agent-information-block;
           }
         }
         case multichassis-tag {
           container multi-routing-engine-results {
             list multi-routing-engine-item {
               leaf re-name {
                 type string;
               }
               choice output-tags {
                 case actual-tag {
                   container analytics-agent-information {
                     uses analytics-agent-information-block;
                   }
                 }
               }
             }
           }
         }
       }
     }
   }
   rpc get-services-analytics-dialout-statistics {
     description "Show telemetry dialout statistics";
     output {
       choice output-tags {
         case actual-tag {
           container services-analytics-dialout-statistics {
             uses services-analytics-dialout-statistics-block;
           }
         }
         case multichassis-tag {
           container multi-routing-engine-results {
             list multi-routing-engine-item {
               leaf re-name {
                 type string;
               }
               choice output-tags {
                 case actual-tag {
                   container services-analytics-dialout-statistics {
                     uses services-analytics-dialout-statistics-block;
                   }
                 }
               }
             }
           }
         }
       }
     }
   }
   rpc get-probe-results {
     description "Show probe results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       choice output-tags {
         case actual-tag {
           container probe-results {
             uses probe-results-block;
           }
         }
         case multichassis-tag {
           container multi-routing-engine-results {
             list multi-routing-engine-item {
               leaf re-name {
                 type string;
               }
               choice output-tags {
                 case actual-tag {
                   container probe-results {
                     uses probe-results-block;
                   }
                 }
               }
             }
           }
         }
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       choice output-tags {
         case actual-tag {
           container history-results {
             uses history-results-block;
           }
         }
         case multichassis-tag {
           container multi-routing-engine-results {
             list multi-routing-engine-item {
               leaf re-name {
                 type string;
               }
               choice output-tags {
                 case actual-tag {
                   container history-results {
                     uses history-results-block;
                   }
                 }
               }
             }
           }
         }
       }
     }
   }
   rpc get-active-servers {
     description "Show configured servers";
     output {
       choice output-tags {
         case actual-tag {
           container active-servers {
             uses active-servers-block;
           }
         }
         case multichassis-tag {
           container multi-routing-engine-results {
             list multi-routing-engine-item {
               leaf re-name {
                 type string;
               }
               choice output-tags {
                 case actual-tag {
                   container active-servers {
                     uses active-servers-block;
                   }
                 }
               }
             }
           }
         }
       }
     }
   }
   rpc twamp-information {
     description "Show TWAMP information";
     output {
       choice output-tags {
         case output-tag {
           leaf output {
             type string;
           }
         }
         case multichassis-tag {
           anyxml multi-routing-engine-results;
         }
       }
     }
   }
   rpc twamp-client-information {
     description "Show TWAMP client information";
     output {
       choice output-tags {
         case actual-tag {
           container twamp-client-information {
             uses twamp-client-information-block;
           }
         }
         case multichassis-tag {
           container multi-routing-engine-results {
             list multi-routing-engine-item {
               leaf re-name {
                 type string;
               }
               choice output-tags {
                 case actual-tag {
                   container twamp-client-information {
                     uses twamp-client-information-block;
                   }
                 }
               }
             }
           }
         }
       }
     }
   }
   rpc twamp-client-connection-information {
     description "Display connection information";
     input {
       leaf connection-name {
         description "Control connection name";
         default "all";
         type string;
       }
     }
     output {
       choice output-tags {
         case output-tag {
           leaf output {
             type string;
           }
         }
         case multichassis-tag {
           anyxml multi-routing-engine-results;
         }
       }
     }
   }
   rpc twamp-client-test-session {
     description "Display test session information";
     input {
       leaf control-connection {
         description "Control connection name";
         type string {
           length "1 .. 32";
         }
       }
       leaf test-session {
         description "Test session name";
         type string {
           length "1 .. 32";
         }
       }
     }
     output {
       choice output-tags {
         case output-tag {
           leaf output {
             type string;
           }
         }
         case multichassis-tag {
           anyxml multi-routing-engine-results;
         }
       }
     }
   }
   rpc twamp-get-probe-results {
     description "Display test session results";
     input {
       leaf control-connection {
         description "Control connection name";
         type string;
       }
       leaf test-session {
         description "Test session name";
         type string;
       }
     }
     output {
       choice output-tags {
         case actual-tag {
           container probe-results {
             uses probe-results-block;
           }
         }
         case multichassis-tag {
           container multi-routing-engine-results {
             list multi-routing-engine-item {
               leaf re-name {
                 type string;
               }
               choice output-tags {
                 case actual-tag {
                   container probe-results {
                     uses probe-results-block;
                   }
                 }
               }
             }
           }
         }
       }
     }
   }
   rpc twamp-get-history-results {
     description "Display test session history results";
     input {
       leaf verbosity_level {
         default "brief";
         type enumeration {
           enum "brief" {
             description "Display brief output (default)";
           }
           enum "detail" {
             description "Display detailed output";
           }
         }
       }
       leaf control-connection {
         description "Control connection name";
         type string;
       }
       leaf test-session {
         description "Test session name";
         type string;
       }
       leaf since {
         description "Show history since YYYY-MM-DD.HH:MM:SS";
         type jt:time;
       }
     }
     output {
       choice output-tags {
         case actual-tag {
           container history-results {
             uses history-results-block;
           }
         }
         case multichassis-tag {
           container multi-routing-engine-results {
             list multi-routing-engine-item {
               leaf re-name {
                 type string;
               }
               choice output-tags {
                 case actual-tag {
                   container history-results {
                     uses history-results-block;
                   }
                 }
               }
             }
           }
         }
       }
     }
   }
   rpc twamp-server-information {
     description "Show TWAMP server information";
     output {
       choice output-tags {
         case actual-tag {
           container twamp-server-information {
             uses twamp-server-information-block;
           }
         }
         case multichassis-tag {
           container multi-routing-engine-results {
             list multi-routing-engine-item {
               leaf re-name {
                 type string;
               }
               choice output-tags {
                 case actual-tag {
                   container twamp-server-information {
                     uses twamp-server-information-block;
                   }
                 }
               }
             }
           }
         }
       }
     }
   }
   rpc twamp-server-connection-information {
     description "Display connection information";
     input {
       leaf connection-id {
         description "Connection ID";
         default "all";
         type string;
       }
     }
     output {
       choice output-tags {
         case output-tag {
           leaf output {
             type string;
           }
         }
         case multichassis-tag {
           anyxml multi-routing-engine-results;
         }
       }
     }
   }
   rpc twamp-server-session-information {
     description "Display session information";
     input {
       leaf session-id {
         description "Session ID";
         default "all";
         type string;
       }
     }
     output {
       choice output-tags {
         case output-tag {
           leaf output {
             type string;
           }
         }
         case multichassis-tag {
           anyxml multi-routing-engine-results;
         }
       }
     }
   }
   rpc get-rfc2544-bench-test-id-information {
     description "Show rfc2544 test id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output-tags {
         case output-tag {
           leaf output {
             type string;
           }
         }
         case actual-tag {
           anyxml rfc2544-test-id-information;
         }
         case multichassis-tag {
           anyxml multi-routing-engine-results;
         }
       }
     }
   }
   rpc get-rfc2544-bench-active-tests-information {
     description "Show rfc2544 active tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output-tags {
         case output-tag {
           leaf output {
             type string;
           }
         }
         case actual-tag {
           anyxml rfc2544-active-tests-information;
         }
         case multichassis-tag {
           anyxml multi-routing-engine-results;
         }
       }
     }
   }
   rpc get-rfc2544-bench-aborted-tests-information {
     description "Show rfc2544 aborted tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output-tags {
         case output-tag {
           leaf output {
             type string;
           }
         }
         case actual-tag {
           anyxml rfc2544-aborted-tests-information;
         }
         case multichassis-tag {
           anyxml multi-routing-engine-results;
         }
       }
     }
   }
   rpc get-rfc2544-bench-completed-tests-information {
     description "Show rfc2544 completed tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output-tags {
         case output-tag {
           leaf output {
             type string;
           }
         }
         case actual-tag {
           anyxml rfc2544-completed-tests-information;
         }
         case multichassis-tag {
           anyxml multi-routing-engine-results;
         }
       }
     }
   }
   rpc get-rfc2544-bench-summary-information {
     description "Show rfc2544 summary";
     output {
       choice output-tags {
         case output-tag {
           leaf output {
             type string;
           }
         }
         case actual-tag {
           anyxml rfc2544-summary-information;
         }
         case multichassis-tag {
           anyxml multi-routing-engine-results;
         }
       }
     }
   }
   rpc get-service-mss-sessions-information {
     description "Show mobile subscriber data sessions";
     input {
       leaf imsi {
         description "IMSI of subscriber";
         type string {
           length "5 .. 15";
         }
       }
     }
     output {
       choice output-tags {
         case output-tag {
           leaf output {
             type string;
           }
         }
         case actual-tag {
           anyxml service-mss-sessions-information;
         }
         case multichassis-tag {
           anyxml multi-routing-engine-results;
         }
       }
     }
   }
   rpc get-service-hcm-sessions-stats {
     description "Show hcm session statistics";
     input {
       leaf imsi {
         description "IMSI of subscriber";
         type string {
           length "5 .. 15";
         }
         mandatory true;
       }
     }
     output {
       choice output-tags {
         case output-tag {
           leaf output {
             type string;
           }
         }
         case actual-tag {
           anyxml service-hcm-sessions-stats;
         }
         case multichassis-tag {
           anyxml multi-routing-engine-results;
         }
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output-tags {
         case output-tag {
           leaf output {
             type string;
           }
         }
         case actual-tag {
           anyxml service-tdf-sessions-information;
         }
         case multichassis-tag {
           anyxml multi-routing-engine-results;
         }
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output-tags {
         case output-tag {
           leaf output {
             type string;
           }
         }
         case actual-tag {
           anyxml service-tdf-hcm-sessions-stats;
         }
         case multichassis-tag {
           anyxml multi-routing-engine-results;
         }
       }
     }
   }
   rpc get-service-crtp-params-information {
     description "Show Compressed Real-Time Protocol information";
     input {
       leaf interface {
         description "Name of link services interface";
         type string;
       }
     }
     output {
       choice output-tags {
         case output-tag {
           leaf output {
             type string;
           }
         }
         case actual-tag {
           anyxml service-crtp-params-information;
         }
         case multichassis-tag {
           anyxml multi-routing-engine-results;
         }
       }
     }
   }
   rpc get-service-crtp-extensive-information {
     description "Show CRTP extensive output";
     input {
       leaf interface {
         description "Name of link services interface";
         type string;
       }
     }
     output {
       choice output-tags {
         case output-tag {
           leaf output {
             type string;
           }
         }
         case actual-tag {
           anyxml service-crtp-extensive-information;
         }
         case multichassis-tag {
           anyxml multi-routing-engine-results;
         }
       }
     }
   }
   rpc get-service-crtp-flow-table-information {
     description "Show CRTP flow table entries";
     input {
       leaf interface {
         description "Name of link services interface";
         type string;
       }
     }
     output {
       choice output-tags {
         case actual-tag {
           container service-crtp-flow-table-information {
             uses service-crtp-flow-table-information-block;
           }
         }
         case multichassis-tag {
           container multi-routing-engine-results {
             list multi-routing-engine-item {
               leaf re-name {
                 type string;
               }
               choice output-tags {
                 case actual-tag {
                   container service-crtp-flow-table-information {
                     uses service-crtp-flow-table-information-block;
                   }
                 }
               }
             }
           }
         }
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
     output {
       choice output-tags {
         case output-tag {
           leaf output {
             type string;
           }
         }
         case actual-tag {
           anyxml global-pcp-statistics-information;
         }
         case multichassis-tag {
           anyxml multi-routing-engine-results;
         }
       }
     }
   }
   rpc get-ssl-statistics {
     description "Show ssl proxy statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-statistics {
             uses ssl-statistics-block;
           }
         }
         case multichassis-tag {
           container multi-routing-engine-results {
             list multi-routing-engine-item {
               leaf re-name {
                 type string;
               }
               choice output-tags {
                 case actual-tag {
                   container ssl-statistics {
                     uses ssl-statistics-block;
                   }
                 }
               }
             }
           }
         }
       }
     }
   }
   rpc get-ssl-status {
     description "Show ssl proxy status";
     input {
       uses command-forwarding;
       leaf pic-info {
         description "PIC ID";
         type string;
       }
     }
     output {
       choice output-tags {
         case actual-tag {
           container ssl-status {
             uses ssl-status-block;
           }
         }
         case multichassis-tag {
           container multi-routing-engine-results {
             list multi-routing-engine-item {
               leaf re-name {
                 type string;
               }
               choice output-tags {
                 case actual-tag {
                   container ssl-status {
                     uses ssl-status-block;
                   }
                 }
               }
             }
           }
         }
       }
     }
   }
   rpc get-ssl-counters {
     description "Show all ssl proxy counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-ssl-error-counters {
     description "Show ssl proxy error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-ssl-info-counters {
     description "Show ssl proxy info counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-ssl-proxy-profile-all {
     description "Show all ssl proxy profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-profile-list {
             uses ssl-profile-list-block;
           }
         }
         case multichassis-tag {
           container multi-routing-engine-results {
             list multi-routing-engine-item {
               leaf re-name {
                 type string;
               }
               choice output-tags {
                 case actual-tag {
                   container ssl-profile-list {
                     uses ssl-profile-list-block;
                   }
                 }
               }
             }
           }
         }
       }
     }
   }
   rpc get-ssl-proxy-profile-detail {
     description "Show profile information matching the given profile name";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf profile-name {
         description "Ssl proxy profile name";
         type string;
         mandatory true;
       }
     }
     output {
       choice output-tags {
         case actual-tag {
           container ssl-profile-detail {
             uses ssl-profile-detail-block;
           }
         }
         case multichassis-tag {
           container multi-routing-engine-results {
             list multi-routing-engine-item {
               leaf re-name {
                 type string;
               }
               choice output-tags {
                 case actual-tag {
                   container ssl-profile-detail {
                     uses ssl-profile-detail-block;
                   }
                 }
               }
             }
           }
         }
       }
     }
   }
   rpc get-ssl-proxy-session-cache-entries-summary {
     description "Show summary of session cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-sess-cache-entries {
             uses ssl-proxy-sess-cache-entries-block;
           }
         }
         case multichassis-tag {
           container multi-routing-engine-results {
             list multi-routing-engine-item {
               leaf re-name {
                 type string;
               }
               choice output-tags {
                 case actual-tag {
                   container ssl-proxy-sess-cache-entries {
                     uses ssl-proxy-sess-cache-entries-block;
                   }
                 }
               }
             }
           }
         }
       }
     }
   }
   rpc get-ssl-proxy-session-cache-entries-detail {
     description "Show detailed output of session cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-sess-cache-entries {
             uses ssl-proxy-sess-cache-entries-block;
           }
         }
         case multichassis-tag {
           container multi-routing-engine-results {
             list multi-routing-engine-item {
               leaf re-name {
                 type string;
               }
               choice output-tags {
                 case actual-tag {
                   container ssl-proxy-sess-cache-entries {
                     uses ssl-proxy-sess-cache-entries-block;
                   }
                 }
               }
             }
           }
         }
       }
     }
   }
   rpc get-ssl-proxy-session-cache-statistics {
     description "Show session cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-sess-cache-statistics {
             uses ssl-proxy-sess-cache-statistics-block;
           }
         }
         case multichassis-tag {
           container multi-routing-engine-results {
             list multi-routing-engine-item {
               leaf re-name {
                 type string;
               }
               choice output-tags {
                 case actual-tag {
                   container ssl-proxy-sess-cache-statistics {
                     uses ssl-proxy-sess-cache-statistics-block;
                   }
                 }
               }
             }
           }
         }
       }
     }
   }
   rpc get-ssl-proxy-certificate-cache-entries-summary {
     description "Show summary of certificate cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-cert-cache-entries {
             uses ssl-proxy-cert-cache-entries-block;
           }
         }
         case multichassis-tag {
           container multi-routing-engine-results {
             list multi-routing-engine-item {
               leaf re-name {
                 type string;
               }
               choice output-tags {
                 case actual-tag {
                   container ssl-proxy-cert-cache-entries {
                     uses ssl-proxy-cert-cache-entries-block;
                   }
                 }
               }
             }
           }
         }
       }
     }
   }
   rpc get-ssl-proxy-certificate-cache-entries-detail {
     description "Show detailed output of certificate cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-cert-cache-entries {
             uses ssl-proxy-cert-cache-entries-block;
           }
         }
         case multichassis-tag {
           container multi-routing-engine-results {
             list multi-routing-engine-item {
               leaf re-name {
                 type string;
               }
               choice output-tags {
                 case actual-tag {
                   container ssl-proxy-cert-cache-entries {
                     uses ssl-proxy-cert-cache-entries-block;
                   }
                 }
               }
             }
           }
         }
       }
     }
   }
   rpc get-ssl-proxy-cert-cache-statistics {
     description "Show certificate cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-proxy-cert-cache-statistics {
             uses ssl-proxy-cert-cache-statistics-block;
           }
         }
         case multichassis-tag {
           container multi-routing-engine-results {
             list multi-routing-engine-item {
               leaf re-name {
                 type string;
               }
               choice output-tags {
                 case actual-tag {
                   container ssl-proxy-cert-cache-statistics {
                     uses ssl-proxy-cert-cache-statistics-block;
                   }
                 }
               }
             }
           }
         }
       }
     }
   }
   rpc get-ssl-certificate-all {
     description "Show all ssl certificates";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-certificate {
             uses ssl-certificate-block;
           }
         }
         case multichassis-tag {
           container multi-routing-engine-results {
             list multi-routing-engine-item {
               leaf re-name {
                 type string;
               }
               choice output-tags {
                 case actual-tag {
                   container ssl-certificate {
                     uses ssl-certificate-block;
                   }
                 }
               }
             }
           }
         }
       }
     }
   }
   rpc get-ssl-certificate-id-brief {
     description "Show brief information about certificate id";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       choice output-tags {
         case actual-tag {
           container ssl-certificate-id-detail {
             uses ssl-certificate-id-detail-block;
           }
         }
         case multichassis-tag {
           container multi-routing-engine-results {
             list multi-routing-engine-item {
               leaf re-name {
                 type string;
               }
               choice output-tags {
                 case actual-tag {
                   container ssl-certificate-id-detail {
                     uses ssl-certificate-id-detail-block;
                   }
                 }
               }
             }
           }
         }
       }
     }
   }
   rpc get-ssl-certificate-id-detail {
     description "Show detail information about certificate id";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       choice output-tags {
         case actual-tag {
           container ssl-certificate-id-detail {
             uses ssl-certificate-id-detail-block;
           }
         }
         case multichassis-tag {
           container multi-routing-engine-results {
             list multi-routing-engine-item {
               leaf re-name {
                 type string;
               }
               choice output-tags {
                 case actual-tag {
                   container ssl-certificate-id-detail {
                     uses ssl-certificate-id-detail-block;
                   }
                 }
               }
             }
           }
         }
       }
     }
   }
   rpc get-terminator-counters {
     description "Show all ssl terminator counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-terminator-error-counters {
     description "Show ssl terminator error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-terminator-handshake-counters {
     description "Show ssl terminator handshake counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-ssl-terminator-profile-all {
     description "Show all ssl terminator profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-profile-list {
             uses ssl-profile-list-block;
           }
         }
         case multichassis-tag {
           container multi-routing-engine-results {
             list multi-routing-engine-item {
               leaf re-name {
                 type string;
               }
               choice output-tags {
                 case actual-tag {
                   container ssl-profile-list {
                     uses ssl-profile-list-block;
                   }
                 }
               }
             }
           }
         }
       }
     }
   }
   rpc get-ssl-terminator-profile-brief {
     description "Terminator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       choice output-tags {
         case actual-tag {
           container ssl-term-profile-detail {
             uses ssl-term-profile-detail-block;
           }
         }
         case multichassis-tag {
           container multi-routing-engine-results {
             list multi-routing-engine-item {
               leaf re-name {
                 type string;
               }
               choice output-tags {
                 case actual-tag {
                   container ssl-term-profile-detail {
                     uses ssl-term-profile-detail-block;
                   }
                 }
               }
             }
           }
         }
       }
     }
   }
   rpc get-ssl-terminator-profile-detail {
     description "Terminator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       choice output-tags {
         case actual-tag {
           container ssl-term-profile-detail {
             uses ssl-term-profile-detail-block;
           }
         }
         case multichassis-tag {
           container multi-routing-engine-results {
             list multi-routing-engine-item {
               leaf re-name {
                 type string;
               }
               choice output-tags {
                 case actual-tag {
                   container ssl-term-profile-detail {
                     uses ssl-term-profile-detail-block;
                   }
                 }
               }
             }
           }
         }
       }
     }
   }
   rpc get-initiator-counters {
     description "Show all ssl initiator counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-initiator-error-counters {
     description "Show ssl initiator error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-initiator-handshake-counters {
     description "Show ssl initiator handshake counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-counters {
             uses ssl-counters-block;
           }
         }
         case multichassis-tag {
           container multi-routing-engine-results {
             list multi-routing-engine-item {
               leaf re-name {
                 type string;
               }
               choice output-tags {
                 case actual-tag {
                   container ssl-counters {
                     uses ssl-counters-block;
                   }
                 }
               }
             }
           }
         }
       }
     }
   }
   rpc get-ssl-initiator-profile-all {
     description "Show all ssl initiator profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-profile-list {
             uses ssl-profile-list-block;
           }
         }
         case multichassis-tag {
           container multi-routing-engine-results {
             list multi-routing-engine-item {
               leaf re-name {
                 type string;
               }
               choice output-tags {
                 case actual-tag {
                   container ssl-profile-list {
                     uses ssl-profile-list-block;
                   }
                 }
               }
             }
           }
         }
       }
     }
   }
   rpc get-ssl-initiator-profile-brief {
     description "Initiator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       choice output-tags {
         case actual-tag {
           container ssl-term-profile-detail {
             uses ssl-term-profile-detail-block;
           }
         }
         case multichassis-tag {
           container multi-routing-engine-results {
             list multi-routing-engine-item {
               leaf re-name {
                 type string;
               }
               choice output-tags {
                 case actual-tag {
                   container ssl-term-profile-detail {
                     uses ssl-term-profile-detail-block;
                   }
                 }
               }
             }
           }
         }
       }
     }
   }
   rpc get-ssl-initiator-profile-detail {
     description "Initiator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       choice output-tags {
         case actual-tag {
           container ssl-term-profile-detail {
             uses ssl-term-profile-detail-block;
           }
         }
         case multichassis-tag {
           container multi-routing-engine-results {
             list multi-routing-engine-item {
               leaf re-name {
                 type string;
               }
               choice output-tags {
                 case actual-tag {
                   container ssl-term-profile-detail {
                     uses ssl-term-profile-detail-block;
                   }
                 }
               }
             }
           }
         }
       }
     }
   }
   rpc get-ssl-session {
     description "Show ssl session details";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf flow_session_id {
         description "Flow session id";
         type string;
         mandatory true;
       }
     }
     output {
       choice output-tags {
         case actual-tag {
           container ssl-session {
             uses ssl-session-block;
           }
         }
         case multichassis-tag {
           container multi-routing-engine-results {
             list multi-routing-engine-item {
               leaf re-name {
                 type string;
               }
               choice output-tags {
                 case actual-tag {
                   container ssl-session {
                     uses ssl-session-block;
                   }
                 }
               }
             }
           }
         }
       }
     }
   }
   rpc get-ssl-droplogs {
     description "Show ssl droplogs";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output-tags {
         case actual-tag {
           container ssl-droplog {
             uses ssl-droplog-block;
           }
         }
         case multichassis-tag {
           container multi-routing-engine-results {
             list multi-routing-engine-item {
               leaf re-name {
                 type string;
               }
               choice output-tags {
                 case actual-tag {
                   container ssl-droplog {
                     uses ssl-droplog-block;
                   }
                 }
               }
             }
           }
         }
       }
     }
   }
   rpc get-ip-monitoring-status {
     description "Ip monitoring status";
     input {
       leaf policy {
         description "Policy name";
         type string;
       }
     }
     output {
       choice output-tags {
         case actual-tag {
           container ip-monitoring {
             uses ip-monitoring-block;
           }
         }
         case multichassis-tag {
           container multi-routing-engine-results {
             list multi-routing-engine-item {
               leaf re-name {
                 type string;
               }
               choice output-tags {
                 case actual-tag {
                   container ip-monitoring {
                     uses ip-monitoring-block;
                   }
                 }
               }
             }
           }
         }
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
     output {
       choice output-tags {
         case output-tag {
           leaf output {
             type string;
           }
         }
         case actual-tag {
           anyxml service-traffic-load-balance-statistics;
         }
         case multichassis-tag {
           anyxml multi-routing-engine-results;
         }
       }
     }
   }
   rpc get-flb-statistics {
     description "FLB  statistics";
     input {
       leaf all {
         description "All flb instances";
         type empty;
       }
     }
     output {
       choice output-tags {
         case output-tag {
           leaf output {
             type string;
           }
         }
         case actual-tag {
           anyxml flb-statistics;
         }
         case multichassis-tag {
           anyxml multi-routing-engine-results;
         }
       }
     }
   }
   rpc traffic-load-balance-commit-status {
     description "Display commit status";
     output {
       choice output-tags {
         case actual-tag {
           container tdir-commit-status {
             uses tdir-commit-status-block;
           }
         }
         case multichassis-tag {
           container multi-routing-engine-results {
             list multi-routing-engine-item {
               leaf re-name {
                 type string;
               }
               choice output-tags {
                 case actual-tag {
                   container tdir-commit-status {
                     uses tdir-commit-status-block;
                   }
                 }
               }
             }
           }
         }
       }
     }
   }
   rpc get-uac-debug-counters {
     description "Show uac debug counters";
     input {
       uses command-forwarding;
     }
     output {
       choice output-tags {
         case actual-tag {
           container uac-debug-counters {
             uses uac-debug-counters-block;
           }
         }
         case multichassis-tag {
           container multi-routing-engine-results {
             list multi-routing-engine-item {
               leaf re-name {
                 type string;
               }
               choice output-tags {
                 case actual-tag {
                   container uac-debug-counters {
                     uses uac-debug-counters-block;
                   }
                 }
               }
             }
           }
         }
       }
     }
   }
   rpc get-uac-policies {
     description "Access policies from infranet controller";
     input {
       uses command-forwarding;
       leaf detail {
         description "Display detail output";
         type empty;
       }
       leaf identifier {
         description "Show specified policy information";
         type string;
       }
     }
     output {
       choice output-tags {
         case output-tag {
           leaf output {
             type string;
           }
         }
         case actual-tag {
           anyxml uac-policies;
         }
         case multichassis-tag {
           anyxml multi-routing-engine-results;
         }
       }
     }
   }
   rpc get-uac-auth-table {
     description "Show authentication table configured from infranet controller";
     input {
       uses command-forwarding;
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
     output {
       choice output-tags {
         case output-tag {
           leaf output {
             type string;
           }
         }
         case actual-tag {
           anyxml uac-auth-table;
         }
         case multichassis-tag {
           anyxml multi-routing-engine-results;
         }
       }
     }
   }
   rpc get-uac-status {
     description "Show connection status with infranet controller";
     input {
       uses command-forwarding;
     }
     output {
       choice output-tags {
         case output-tag {
           leaf output {
             type string;
           }
         }
         case actual-tag {
           anyxml uac-status;
         }
         case multichassis-tag {
           anyxml multi-routing-engine-results;
         }
       }
     }
   }
   rpc get-uac-role-entries {
     description "Show list of available roles";
     input {
       uses command-forwarding;
     }
     output {
       choice output-tags {
         case output-tag {
           leaf output {
             type string;
           }
         }
         case actual-tag {
           anyxml uac-role-entries;
         }
         case multichassis-tag {
           anyxml multi-routing-engine-results;
         }
       }
     }
   }
   rpc get-uac-counters {
     description "Show unified access control(uac) service related counters";
     input {
       uses command-forwarding;
     }
     output {
       choice output-tags {
         case actual-tag {
           container uac-counters {
             uses uac-counters-block;
           }
         }
         case multichassis-tag {
           container multi-routing-engine-results {
             list multi-routing-engine-item {
               leaf re-name {
                 type string;
               }
               choice output-tags {
                 case actual-tag {
                   container uac-counters {
                     uses uac-counters-block;
                   }
                 }
               }
             }
           }
         }
       }
     }
   }
   rpc get-swgauth-profile-statistics {
     description "Show captive portal statistics for given profile";
     input {
       leaf profile-name {
         description "Captive portal profile name";
         type string {
           length "1 .. 65";
         }
       }
     }
     output {
       choice output-tags {
         case actual-tag {
           container swgauth-profile-statistics {
             uses swgauth-profile-statistics-block;
           }
         }
         case multichassis-tag {
           container multi-routing-engine-results {
             list multi-routing-engine-item {
               leaf re-name {
                 type string;
               }
               choice output-tags {
                 case actual-tag {
                   container swgauth-profile-statistics {
                     uses swgauth-profile-statistics-block;
                   }
                 }
               }
             }
           }
         }
       }
     }
   }
   rpc swgauth-captiveportal-redirect-statistics {
     description "Show captive portal statistics for redirects";
     output {
       choice output-tags {
         case actual-tag {
           container swgauth-captiveportal-redirect-statistics {
             uses swgauth-captiveportal-redirect-statistics-block;
           }
         }
         case multichassis-tag {
           container multi-routing-engine-results {
             list multi-routing-engine-item {
               leaf re-name {
                 type string;
               }
               choice output-tags {
                 case actual-tag {
                   container swgauth-captiveportal-redirect-statistics {
                     uses swgauth-captiveportal-redirect-statistics-block;
                   }
                 }
               }
             }
           }
         }
       }
     }
   }
   rpc swgauth-captiveportal-connection-statistics {
     description "Show captive oprtal statistics for connection";
     output {
       choice output-tags {
         case actual-tag {
           container swgauth-captiveportal-connection-statistics {
             uses swgauth-captiveportal-connection-statistics-block;
           }
         }
         case multichassis-tag {
           container multi-routing-engine-results {
             list multi-routing-engine-item {
               leaf re-name {
                 type string;
               }
               choice output-tags {
                 case actual-tag {
                   container swgauth-captiveportal-connection-statistics {
                     uses swgauth-captiveportal-connection-statistics-block;
                   }
                 }
               }
             }
           }
         }
       }
     }
   }
   rpc get-user-group-all-debug-counters {
     description "Show debug counters";
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-user-group-ager-debug-counters {
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-user-group-batch-query-debug-counters {
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-user-group-ip-query-debug-counters {
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-user-group-message-exchange-debug-counters {
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-user-group-general-debug-counters {
     output {
       choice output-tags {
         case actual-tag {
           container user-group-debug-counters {
             uses user-group-debug-counters-block;
           }
         }
         case multichassis-tag {
           container multi-routing-engine-results {
             list multi-routing-engine-item {
               leaf re-name {
                 type string;
               }
               choice output-tags {
                 case actual-tag {
                   container user-group-debug-counters {
                     uses user-group-debug-counters-block;
                   }
                 }
               }
             }
           }
         }
       }
     }
   }
   rpc get-authentication-table-counter {
     description "Show authentication table entry internal counter";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-counter {
             uses authentication-table-counter-block;
           }
         }
         case multichassis-tag {
           container multi-routing-engine-results {
             list multi-routing-engine-item {
               leaf re-name {
                 type string;
               }
               choice output-tags {
                 case actual-tag {
                   container authentication-table-counter {
                     uses authentication-table-counter-block;
                   }
                 }
               }
             }
           }
         }
       }
     }
   }
   rpc get-authentication-table-by-address {
     description "Show authentication table entry by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-by-address {
             uses authentication-table-by-address-block;
           }
         }
         case multichassis-tag {
           container multi-routing-engine-results {
             list multi-routing-engine-item {
               leaf re-name {
                 type string;
               }
               choice output-tags {
                 case actual-tag {
                   container authentication-table-by-address {
                     uses authentication-table-by-address-block;
                   }
                 }
               }
             }
           }
         }
       }
     }
   }
   rpc get-authentication-table-by-session-id {
     description "Show authentication table entry by session-id";
     input {
       uses command-forwarding;
       leaf session-id {
         description "Session-id";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case output-tag {
           leaf output {
             type string;
           }
         }
         case actual-tag {
           anyxml authentication-table-by-session-id;
         }
         case multichassis-tag {
           anyxml multi-routing-engine-results;
         }
       }
     }
   }
   rpc get-authentication-table-by-address-type {
     description "Show authentication table entry with auth type by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-by-address {
             uses authentication-table-by-address-block;
           }
         }
         case multichassis-tag {
           container multi-routing-engine-results {
             list multi-routing-engine-item {
               leaf re-name {
                 type string;
               }
               choice output-tags {
                 case actual-tag {
                   container authentication-table-by-address {
                     uses authentication-table-by-address-block;
                   }
                 }
               }
             }
           }
         }
       }
     }
   }
   rpc get-authentication-table-all {
     description "Show the entire authentication table in the userid daemon";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       leaf service-id {
         description "Show authentication table entries for service identities only";
         default "all";
         type string;
       }
     }
     output {
       choice output-tags {
         case actual-tag {
           container authentication-table-all {
             uses authentication-table-all-block;
           }
         }
         case multichassis-tag {
           container multi-routing-engine-results {
             list multi-routing-engine-item {
               leaf re-name {
                 type string;
               }
               choice output-tags {
                 case actual-tag {
                   container authentication-table-all {
                     uses authentication-table-all-block;
                   }
                 }
               }
             }
           }
         }
       }
     }
   }
   rpc get-authentication-table-all-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-all-by-group {
             uses authentication-table-all-by-group-block;
           }
         }
         case multichassis-tag {
           container multi-routing-engine-results {
             list multi-routing-engine-item {
               leaf re-name {
                 type string;
               }
               choice output-tags {
                 case actual-tag {
                   container authentication-table-all-by-group {
                     uses authentication-table-all-by-group-block;
                   }
                 }
               }
             }
           }
         }
       }
     }
   }
   rpc get-authentication-table-all-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-all-by-user {
             uses authentication-table-all-by-user-block;
           }
         }
         case multichassis-tag {
           container multi-routing-engine-results {
             list multi-routing-engine-item {
               leaf re-name {
                 type string;
               }
               choice output-tags {
                 case actual-tag {
                   container authentication-table-all-by-user {
                     uses authentication-table-all-by-user-block;
                   }
                 }
               }
             }
           }
         }
       }
     }
   }
   rpc get-authentication-table-all-type {
     description "Show the entire authentication table in the userid daemon";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case actual-tag {
           container authentication-table-all {
             uses authentication-table-all-block;
           }
         }
         case multichassis-tag {
           container multi-routing-engine-results {
             list multi-routing-engine-item {
               leaf re-name {
                 type string;
               }
               choice output-tags {
                 case actual-tag {
                   container authentication-table-all {
                     uses authentication-table-all-block;
                   }
                 }
               }
             }
           }
         }
       }
     }
   }
   rpc get-authentication-table-all-type-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-all-by-group {
             uses authentication-table-all-by-group-block;
           }
         }
         case multichassis-tag {
           container multi-routing-engine-results {
             list multi-routing-engine-item {
               leaf re-name {
                 type string;
               }
               choice output-tags {
                 case actual-tag {
                   container authentication-table-all-by-group {
                     uses authentication-table-all-by-group-block;
                   }
                 }
               }
             }
           }
         }
       }
     }
   }
   rpc get-authentication-table-all-type-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-all-by-user {
             uses authentication-table-all-by-user-block;
           }
         }
         case multichassis-tag {
           container multi-routing-engine-results {
             list multi-routing-engine-item {
               leaf re-name {
                 type string;
               }
               choice output-tags {
                 case actual-tag {
                   container authentication-table-all-by-user {
                     uses authentication-table-all-by-user-block;
                   }
                 }
               }
             }
           }
         }
       }
     }
   }
   rpc get-authentication-table-cp {
     description "Authentication source from Aruba ClearPass";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case actual-tag {
           container authentication-table-cp {
             uses authentication-table-cp-block;
           }
         }
         case multichassis-tag {
           container multi-routing-engine-results {
             list multi-routing-engine-item {
               leaf re-name {
                 type string;
               }
               choice output-tags {
                 case actual-tag {
                   container authentication-table-cp {
                     uses authentication-table-cp-block;
                   }
                 }
               }
             }
           }
         }
       }
     }
   }
   rpc get-authentication-table-cp-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-cp-by-group {
             uses authentication-table-cp-by-group-block;
           }
         }
         case multichassis-tag {
           container multi-routing-engine-results {
             list multi-routing-engine-item {
               leaf re-name {
                 type string;
               }
               choice output-tags {
                 case actual-tag {
                   container authentication-table-cp-by-group {
                     uses authentication-table-cp-by-group-block;
                   }
                 }
               }
             }
           }
         }
       }
     }
   }
   rpc get-authentication-table-cp-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-cp-by-user {
             uses authentication-table-cp-by-user-block;
           }
         }
         case multichassis-tag {
           container multi-routing-engine-results {
             list multi-routing-engine-item {
               leaf re-name {
                 type string;
               }
               choice output-tags {
                 case actual-tag {
                   container authentication-table-cp-by-user {
                     uses authentication-table-cp-by-user-block;
                   }
                 }
               }
             }
           }
         }
       }
     }
   }
   rpc get-authentication-table-ad {
     description "Show the active directory authentication table";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case actual-tag {
           container authentication-table-ad {
             uses authentication-table-ad-block;
           }
         }
         case multichassis-tag {
           container multi-routing-engine-results {
             list multi-routing-engine-item {
               leaf re-name {
                 type string;
               }
               choice output-tags {
                 case actual-tag {
                   container authentication-table-ad {
                     uses authentication-table-ad-block;
                   }
                 }
               }
             }
           }
         }
       }
     }
   }
   rpc get-authentication-table-ad-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-ad-by-group {
             uses authentication-table-ad-by-group-block;
           }
         }
         case multichassis-tag {
           container multi-routing-engine-results {
             list multi-routing-engine-item {
               leaf re-name {
                 type string;
               }
               choice output-tags {
                 case actual-tag {
                   container authentication-table-ad-by-group {
                     uses authentication-table-ad-by-group-block;
                   }
                 }
               }
             }
           }
         }
       }
     }
   }
   rpc get-authentication-table-ad-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-ad-by-user {
             uses authentication-table-ad-by-user-block;
           }
         }
         case multichassis-tag {
           container multi-routing-engine-results {
             list multi-routing-engine-item {
               leaf re-name {
                 type string;
               }
               choice output-tags {
                 case actual-tag {
                   container authentication-table-ad-by-user {
                     uses authentication-table-ad-by-user-block;
                   }
                 }
               }
             }
           }
         }
       }
     }
   }
   rpc get-authentication-table-ims {
     description "Identity management server";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf source-name {
         description "Authentication source name";
         type string {
           length "1 .. 65";
         }
       }
       leaf domain {
         description "Show identity-management-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       leaf service-id {
         description "Show authentication table entries for service identities only";
         default "all";
         type string;
       }
     }
     output {
       choice output-tags {
         case actual-tag {
           container authentication-table-ims {
             uses authentication-table-ims-block;
           }
         }
         case multichassis-tag {
           container multi-routing-engine-results {
             list multi-routing-engine-item {
               leaf re-name {
                 type string;
               }
               choice output-tags {
                 case actual-tag {
                   container authentication-table-ims {
                     uses authentication-table-ims-block;
                   }
                 }
               }
             }
           }
         }
       }
     }
   }
   rpc get-authentication-table-ims-by-group {
     description "Show authentication table entry by group name";
     input {
       uses command-forwarding;
       leaf group-name {
         description "Group name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-ims-by-group {
             uses authentication-table-ims-by-group-block;
           }
         }
         case multichassis-tag {
           container multi-routing-engine-results {
             list multi-routing-engine-item {
               leaf re-name {
                 type string;
               }
               choice output-tags {
                 case actual-tag {
                   container authentication-table-ims-by-group {
                     uses authentication-table-ims-by-group-block;
                   }
                 }
               }
             }
           }
         }
       }
     }
   }
   rpc get-authentication-table-ims-by-user {
     description "Show authentication table entry by user name";
     input {
       uses command-forwarding;
       leaf user-name {
         description "User name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container authentication-table-ims-by-user {
             uses authentication-table-ims-by-user-block;
           }
         }
         case multichassis-tag {
           container multi-routing-engine-results {
             list multi-routing-engine-item {
               leaf re-name {
                 type string;
               }
               choice output-tags {
                 case actual-tag {
                   container authentication-table-ims-by-user {
                     uses authentication-table-ims-by-user-block;
                   }
                 }
               }
             }
           }
         }
       }
     }
   }
   rpc get-domain-controller-status {
     description "Show domain-controller status";
     input {
       uses command-forwarding;
       leaf domain {
         description "Show domain-controller status per domain";
         type string {
           length "1 .. 65";
         }
       }
       leaf level {
         default "brief";
         type enumeration {
           enum "brief" {
             description "Show brief output (default)";
           }
           enum "extensive" {
             description "Show extensive output";
           }
         }
       }
     }
     output {
       choice output-tags {
         case actual-tag {
           container domain-controller-status {
             uses domain-controller-status-block;
           }
         }
         case multichassis-tag {
           container multi-routing-engine-results {
             list multi-routing-engine-item {
               leaf re-name {
                 type string;
               }
               choice output-tags {
                 case actual-tag {
                   container domain-controller-status {
                     uses domain-controller-status-block;
                   }
                 }
               }
             }
           }
         }
       }
     }
   }
   rpc get-ip-user-mapping-statistics {
     description "Show ip-user-mapping statistics";
     input {
       uses command-forwarding;
       leaf domain {
         description "Show ip-user-mapping statistics per domain";
         type string {
           length "1 .. 65";
         }
       }
     }
     output {
       choice output-tags {
         case actual-tag {
           container ip-user-mapping-statistics {
             uses ip-user-mapping-statistics-block;
           }
         }
         case multichassis-tag {
           container multi-routing-engine-results {
             list multi-routing-engine-item {
               leaf re-name {
                 type string;
               }
               choice output-tags {
                 case actual-tag {
                   container ip-user-mapping-statistics {
                     uses ip-user-mapping-statistics-block;
                   }
                 }
               }
             }
           }
         }
       }
     }
   }
   rpc get-ip-user-probe-statistics {
     description "Show ip-user-probe statistics";
     input {
       uses command-forwarding;
       leaf domain {
         description "Show ip-user-probe statistics per domain";
         type string {
           length "1 .. 65";
         }
       }
     }
     output {
       choice output-tags {
         case actual-tag {
           container ip-user-probe-statistics {
             uses ip-user-probe-statistics-block;
           }
         }
         case multichassis-tag {
           container multi-routing-engine-results {
             list multi-routing-engine-item {
               leaf re-name {
                 type string;
               }
               choice output-tags {
                 case actual-tag {
                   container ip-user-probe-statistics {
                     uses ip-user-probe-statistics-block;
                   }
                 }
               }
             }
           }
         }
       }
     }
   }
   rpc get-user-group-mapping-statistics {
     description "Show user-group-mapping statistics";
     input {
       uses command-forwarding;
       leaf domain {
         description "Show user-group-mapping statistics per domain";
         type string {
           length "1 .. 65";
         }
       }
     }
     output {
       choice output-tags {
         case actual-tag {
           container user-group-mapping-statistics {
             uses user-group-mapping-statistics-block;
           }
         }
         case multichassis-tag {
           container multi-routing-engine-results {
             list multi-routing-engine-item {
               leaf re-name {
                 type string;
               }
               choice output-tags {
                 case actual-tag {
                   container user-group-mapping-statistics {
                     uses user-group-mapping-statistics-block;
                   }
                 }
               }
             }
           }
         }
       }
     }
   }
   rpc get-all-configuration {
     description "Show active-directory-access configuration";
     input {
       uses command-forwarding;
     }
     output {
       choice output-tags {
         case output-tag {
           leaf output {
             type string;
           }
         }
         case actual-tag {
           anyxml all-configuration;
         }
         case multichassis-tag {
           anyxml multi-routing-engine-results;
         }
       }
     }
   }
   rpc get-users-by-group {
     description "Show specified group's users. If timeout, wait several minutes and try again.";
     input {
       uses command-forwarding;
       leaf group-name {
         description "Specified group name";
         type string {
           length "1 .. 65";
         }
         mandatory true;
       }
       leaf domain {
         description "Show users per domain";
         type string {
           length "1 .. 65";
         }
         mandatory true;
       }
     }
     output {
       choice output-tags {
         case actual-tag {
           container users-by-group {
             uses users-by-group-block;
           }
         }
         case multichassis-tag {
           container multi-routing-engine-results {
             list multi-routing-engine-item {
               leaf re-name {
                 type string;
               }
               choice output-tags {
                 case actual-tag {
                   container users-by-group {
                     uses users-by-group-block;
                   }
                 }
               }
             }
           }
         }
       }
     }
   }
   rpc get-groups-by-user {
     description "Show specified user's groups. If timeout, wait several minutes and try again.";
     input {
       uses command-forwarding;
       leaf user-name {
         description "Specified user name";
         type string {
           length "1 .. 65";
         }
         mandatory true;
       }
       leaf domain {
         description "Show groups per domain";
         type string {
           length "1 .. 65";
         }
         mandatory true;
       }
       leaf in-local-cache {
         description "Show only groups in local cache";
         type empty;
       }
     }
     output {
       choice output-tags {
         case actual-tag {
           container groups-by-user {
             uses groups-by-user-block;
           }
         }
         case multichassis-tag {
           container multi-routing-engine-results {
             list multi-routing-engine-item {
               leaf re-name {
                 type string;
               }
               choice output-tags {
                 case actual-tag {
                   container groups-by-user {
                     uses groups-by-user-block;
                   }
                 }
               }
             }
           }
         }
       }
     }
   }
   rpc get-user-group-mapping-status {
     description "Show user-group-mapping status";
     input {
       uses command-forwarding;
       leaf domain {
         description "Show user-group-mapping status per domain";
         type string {
           length "1 .. 65";
         }
       }
     }
     output {
       choice output-tags {
         case actual-tag {
           container user-group-mapping-status {
             uses user-group-mapping-status-block;
           }
         }
         case multichassis-tag {
           container multi-routing-engine-results {
             list multi-routing-engine-item {
               leaf re-name {
                 type string;
               }
               choice output-tags {
                 case actual-tag {
                   container user-group-mapping-status {
                     uses user-group-mapping-status-block;
                   }
                 }
               }
             }
           }
         }
       }
     }
   }
   rpc get-ad-ug-mapping-fetching {
     description "Show user-group-mapping fetching";
     input {
       uses command-forwarding;
     }
     output {
       choice output-tags {
         case output-tag {
           leaf output {
             type string;
           }
         }
         case multichassis-tag {
           anyxml multi-routing-engine-results;
         }
       }
     }
   }
   rpc get-fetching-status {
     description "Show user-group-mapping fetching status";
     input {
       uses command-forwarding;
     }
     output {
       choice output-tags {
         case actual-tag {
           container fetching-status {
             uses fetching-status-block;
           }
         }
         case multichassis-tag {
           container multi-routing-engine-results {
             list multi-routing-engine-item {
               leaf re-name {
                 type string;
               }
               choice output-tags {
                 case actual-tag {
                   container fetching-status {
                     uses fetching-status-block;
                   }
                 }
               }
             }
           }
         }
       }
     }
   }
   rpc get-periodic-fetching {
     description "Show user-group-mapping periodic fetching";
     input {
       uses command-forwarding;
     }
     output {
       choice output-tags {
         case output-tag {
           leaf output {
             type string;
           }
         }
         case multichassis-tag {
           anyxml multi-routing-engine-results;
         }
       }
     }
   }
   rpc get-periodic-fetching-status {
     description "Show user-group-mapping periodic fetching status";
     input {
       uses command-forwarding;
     }
     output {
       choice output-tags {
         case actual-tag {
           container periodic-fetching-status {
             uses periodic-fetching-status-block;
           }
         }
         case multichassis-tag {
           container multi-routing-engine-results {
             list multi-routing-engine-item {
               leaf re-name {
                 type string;
               }
               choice output-tags {
                 case actual-tag {
                   container periodic-fetching-status {
                     uses periodic-fetching-status-block;
                   }
                 }
               }
             }
           }
         }
       }
     }
   }
   rpc get-periodic-fetching-configuration {
     description "Show user-group-mapping periodic fetching configuration";
     input {
       uses command-forwarding;
     }
     output {
       choice output-tags {
         case actual-tag {
           container periodic-fetching-configuration {
             uses periodic-fetching-configuration-block;
           }
         }
         case multichassis-tag {
           container multi-routing-engine-results {
             list multi-routing-engine-item {
               leaf re-name {
                 type string;
               }
               choice output-tags {
                 case actual-tag {
                   container periodic-fetching-configuration {
                     uses periodic-fetching-configuration-block;
                   }
                 }
               }
             }
           }
         }
       }
     }
   }
   rpc get-ad-ug-mapping-refreshing {
     description "Show user-group-mapping refreshing";
     input {
       uses command-forwarding;
     }
     output {
       choice output-tags {
         case output-tag {
           leaf output {
             type string;
           }
         }
         case multichassis-tag {
           anyxml multi-routing-engine-results;
         }
       }
     }
   }
   rpc get-refreshing-status {
     description "Show user-group-mapping refreshing status";
     input {
       uses command-forwarding;
     }
     output {
       choice output-tags {
         case actual-tag {
           container refreshing-status {
             uses refreshing-status-block;
           }
         }
         case multichassis-tag {
           container multi-routing-engine-results {
             list multi-routing-engine-item {
               leaf re-name {
                 type string;
               }
               choice output-tags {
                 case actual-tag {
                   container refreshing-status {
                     uses refreshing-status-block;
                   }
                 }
               }
             }
           }
         }
       }
     }
   }
   rpc get-all-groups {
     description "Show all groups";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case output-tag {
           leaf output {
             type string;
           }
         }
         case actual-tag {
           anyxml group-list;
         }
         case multichassis-tag {
           anyxml multi-routing-engine-results;
         }
       }
     }
   }
   rpc get-all-users {
     description "Show all users";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case output-tag {
           leaf output {
             type string;
           }
         }
         case actual-tag {
           anyxml group-list;
         }
         case multichassis-tag {
           anyxml multi-routing-engine-results;
         }
       }
     }
   }
   rpc get-ad-auth-table-all-information {
     description "Show the entire active directory authentication table";
     input {
       uses command-forwarding;
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case output-tag {
           leaf output {
             type string;
           }
         }
         case actual-tag {
           anyxml active-directory-authentication-table;
         }
         case multichassis-tag {
           anyxml multi-routing-engine-results;
         }
       }
     }
   }
   rpc get-ad-auth-table-by-address-information {
     description "Show active directory authentication table entry by ip-address";
     input {
       uses command-forwarding;
       leaf ip-address {
         description "IP address";
         type jt:ipaddr;
         mandatory true;
       }
     }
     output {
       choice output-tags {
         case output-tag {
           leaf output {
             type string;
           }
         }
         case multichassis-tag {
           anyxml multi-routing-engine-results;
         }
       }
     }
   }
   rpc get-ad-auth-table-by-group-information {
     description "Show active directory authentication table entry by group name";
     input {
       uses command-forwarding;
       leaf group-name {
         description "Group name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case output-tag {
           leaf output {
             type string;
           }
         }
         case multichassis-tag {
           anyxml multi-routing-engine-results;
         }
       }
     }
   }
   rpc get-ad-auth-table-by-user-information {
     description "Show active directory authentication table entry by user name";
     input {
       uses command-forwarding;
       leaf user-name {
         description "User name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case output-tag {
           leaf output {
             type string;
           }
         }
         case multichassis-tag {
           anyxml multi-routing-engine-results;
         }
       }
     }
   }
   rpc get-cp-user-query-statistics {
     description "Show ClearPass user query counters";
     input {
       uses command-forwarding;
     }
     output {
       choice output-tags {
         case actual-tag {
           container cp-user-query-statistics {
             uses cp-user-query-statistics-block;
           }
         }
         case multichassis-tag {
           container multi-routing-engine-results {
             list multi-routing-engine-item {
               leaf re-name {
                 type string;
               }
               choice output-tags {
                 case actual-tag {
                   container cp-user-query-statistics {
                     uses cp-user-query-statistics-block;
                   }
                 }
               }
             }
           }
         }
       }
     }
   }
   rpc get-cp-user-query-status {
     description "Show ClearPass user query status";
     input {
       uses command-forwarding;
     }
     output {
       choice output-tags {
         case actual-tag {
           container cp-user-query-status {
             uses cp-user-query-status-block;
           }
         }
         case multichassis-tag {
           container multi-routing-engine-results {
             list multi-routing-engine-item {
               leaf re-name {
                 type string;
               }
               choice output-tags {
                 case actual-tag {
                   container cp-user-query-status {
                     uses cp-user-query-status-block;
                   }
                 }
               }
             }
           }
         }
       }
     }
   }
   rpc get-device-identity-table-all {
     description "Show the entire device identity table";
     input {
       uses command-forwarding;
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container device-identity-table-all {
             uses device-identity-table-all-block;
           }
         }
         case multichassis-tag {
           container multi-routing-engine-results {
             list multi-routing-engine-item {
               leaf re-name {
                 type string;
               }
               choice output-tags {
                 case actual-tag {
                   container device-identity-table-all {
                     uses device-identity-table-all-block;
                   }
                 }
               }
             }
           }
         }
       }
     }
   }
   rpc get-device-identity-table-by-address {
     description "Show device identity table entry by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container device-identity-table-by-address {
             uses device-identity-table-by-address-block;
           }
         }
         case multichassis-tag {
           container multi-routing-engine-results {
             list multi-routing-engine-item {
               leaf re-name {
                 type string;
               }
               choice output-tags {
                 case actual-tag {
                   container device-identity-table-by-address {
                     uses device-identity-table-by-address-block;
                   }
                 }
               }
             }
           }
         }
       }
     }
   }
   rpc get-device-identity-table-by-device-id {
     description "Show device identity table entry by device id";
     input {
       uses command-forwarding;
       leaf device-id {
         description "Device ID";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output-tags {
         case actual-tag {
           container device-identity-table-by-device-id {
             uses device-identity-table-by-device-id-block;
           }
         }
         case multichassis-tag {
           container multi-routing-engine-results {
             list multi-routing-engine-item {
               leaf re-name {
                 type string;
               }
               choice output-tags {
                 case actual-tag {
                   container device-identity-table-by-device-id {
                     uses device-identity-table-by-device-id-block;
                   }
                 }
               }
             }
           }
         }
       }
     }
   }
   rpc get-device-identity-table-by-group {
     description "Show device identity table entry by group name";
     input {
       uses command-forwarding;
       leaf group-name {
         description "Group name";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output-tags {
         case actual-tag {
           container device-identity-table-by-group {
             uses device-identity-table-by-group-block;
           }
         }
         case multichassis-tag {
           container multi-routing-engine-results {
             list multi-routing-engine-item {
               leaf re-name {
                 type string;
               }
               choice output-tags {
                 case actual-tag {
                   container device-identity-table-by-group {
                     uses device-identity-table-by-group-block;
                   }
                 }
               }
             }
           }
         }
       }
     }
   }
   rpc dump-property-lib {
     description "Dump property lib content";
     output {
       choice output-tags {
         case output-tag {
           leaf output {
             type string;
           }
         }
         case actual-tag {
           anyxml dump-property-lib;
         }
         case multichassis-tag {
           anyxml multi-routing-engine-results;
         }
       }
     }
   }
   rpc get-end-user-profile-address {
     description "Specified all address of specified end-user-profile";
     input {
       leaf profile-name {
         description "Specified profile name";
         type string {
           length "1 .. 65";
         }
       }
       leaf ip-start {
         description "IP from address";
         type jt:ipaddr;
       }
       leaf ip-end {
         description "IP to address";
         type jt:ipaddr;
       }
       leaf sort-by-profile {
         description "Sort by end-user-profile";
         type empty;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       choice output-tags {
         case output-tag {
           leaf output {
             type string;
           }
         }
         case actual-tag {
           anyxml get-end-user-profile-address;
         }
         case multichassis-tag {
           anyxml multi-routing-engine-results;
         }
       }
     }
   }
   rpc get-end-user-profile-statistics {
     description "Show end-user-profile ip-mapping statistics";
     input {
       uses command-forwarding;
     }
     output {
       choice output-tags {
         case output-tag {
           leaf output {
             type string;
           }
         }
         case actual-tag {
           anyxml get-end-user-profile-statistics;
         }
         case multichassis-tag {
           anyxml multi-routing-engine-results;
         }
       }
     }
   }
   rpc get-jims-query-statistics {
     description "Show identity management query counters";
     input {
       uses command-forwarding;
       choice session_or_ip {
         case session {
           leaf session {
             description "Show identity management session counters";
             type empty;
           }
         }
         case ip {
           leaf ip {
             description "Show identity management ip counters";
             type empty;
           }
         }
       }
     }
     output {
       choice output-tags {
         case actual-tag {
           container jims-query-statistics {
             uses jims-query-statistics-block;
           }
         }
         case multichassis-tag {
           container multi-routing-engine-results {
             list multi-routing-engine-item {
               leaf re-name {
                 type string;
               }
               choice output-tags {
                 case actual-tag {
                   container jims-query-statistics {
                     uses jims-query-statistics-block;
                   }
                 }
               }
             }
           }
         }
       }
     }
   }
   rpc get-jims-query-status {
     description "Show identity management query status";
     input {
       uses command-forwarding;
     }
     output {
       choice output-tags {
         case actual-tag {
           container jims-query-status {
             uses jims-query-status-block;
           }
         }
         case multichassis-tag {
           container multi-routing-engine-results {
             list multi-routing-engine-item {
               leaf re-name {
                 type string;
               }
               choice output-tags {
                 case actual-tag {
                   container jims-query-status {
                     uses jims-query-status-block;
                   }
                 }
               }
             }
           }
         }
       }
     }
   }
   rpc get-jims-more-information {
     description "Show more information of identity management";
     input {
       uses command-forwarding;
     }
     output {
       choice output-tags {
         case actual-tag {
           container jims-more-info {
             uses jims-more-info-block;
           }
         }
         case multichassis-tag {
           container multi-routing-engine-results {
             list multi-routing-engine-item {
               leaf re-name {
                 type string;
               }
               choice output-tags {
                 case actual-tag {
                   container jims-more-info {
                     uses jims-more-info-block;
                   }
                 }
               }
             }
           }
         }
       }
     }
   }
   rpc get-jims-validator-information {
     description "Show counter and status of jims validator query server of identity management";
     input {
       uses command-forwarding;
     }
     output {
       choice output-tags {
         case output-tag {
           leaf output {
             type string;
           }
         }
         case multichassis-tag {
           anyxml multi-routing-engine-results;
         }
       }
     }
   }
   rpc get-jims-validator-query-statistics {
     description "Show identity management jims validator query counters";
     input {
       uses command-forwarding;
     }
     output {
       choice output-tags {
         case actual-tag {
           container jims-validator-query-statistics {
             uses jims-validator-query-statistics-block;
           }
         }
         case multichassis-tag {
           container multi-routing-engine-results {
             list multi-routing-engine-item {
               leaf re-name {
                 type string;
               }
               choice output-tags {
                 case actual-tag {
                   container jims-validator-query-statistics {
                     uses jims-validator-query-statistics-block;
                   }
                 }
               }
             }
           }
         }
       }
     }
   }
   rpc get-jims-validator-query-status {
     description "Show identity management jims validator query status";
     input {
       uses command-forwarding;
     }
     output {
       choice output-tags {
         case actual-tag {
           container jims-validator-query-status {
             uses jims-validator-query-status-block;
           }
         }
         case multichassis-tag {
           container multi-routing-engine-results {
             list multi-routing-engine-item {
               leaf re-name {
                 type string;
               }
               choice output-tags {
                 case actual-tag {
                   container jims-validator-query-status {
                     uses jims-validator-query-status-block;
                   }
                 }
               }
             }
           }
         }
       }
     }
   }
   rpc get-dispatcher-statistics {
     description "Show statistics";
     input {
       uses command-forwarding;
     }
     output {
       choice output-tags {
         case output-tag {
           leaf output {
             type string;
           }
         }
         case actual-tag {
           anyxml get-dispatcher-statistics;
         }
         case multichassis-tag {
           anyxml multi-routing-engine-results;
         }
       }
     }
   }
   rpc get-ld-jims-query-statistics {
     description "Show logical domain identity management query counters";
     input {
       uses command-forwarding;
     }
     output {
       choice output-tags {
         case actual-tag {
           container ld-jims-query-statistics {
             uses ld-jims-query-statistics-block;
           }
         }
         case multichassis-tag {
           container multi-routing-engine-results {
             list multi-routing-engine-item {
               leaf re-name {
                 type string;
               }
               choice output-tags {
                 case actual-tag {
                   container ld-jims-query-statistics {
                     uses ld-jims-query-statistics-block;
                   }
                 }
               }
             }
           }
         }
       }
     }
   }
   rpc get-ld-jims-query-status {
     description "Show logical domain identity management query status";
     input {
       uses command-forwarding;
     }
     output {
       choice output-tags {
         case actual-tag {
           container ld-jims-query-status {
             uses ld-jims-query-status-block;
           }
         }
         case multichassis-tag {
           container multi-routing-engine-results {
             list multi-routing-engine-item {
               leaf re-name {
                 type string;
               }
               choice output-tags {
                 case actual-tag {
                   container ld-jims-query-status {
                     uses ld-jims-query-status-block;
                   }
                 }
               }
             }
           }
         }
       }
     }
   }
   rpc get-validate-statistics-from-jims {
     description "Show validate statistics device/group/user from JIMS";
     input {
       uses command-forwarding;
     }
     output {
       choice output-tags {
         case output-tag {
           leaf output {
             type string;
           }
         }
         case multichassis-tag {
           anyxml multi-routing-engine-results;
         }
       }
     }
   }
   rpc get-forward-header-lookup-statistics {
     description "Show http forward header parsing statistics";
     input {
       uses command-forwarding;
     }
     output {
       choice output-tags {
         case actual-tag {
           container forward-header-lookup-statistics {
             uses forward-header-lookup-statistics-block;
           }
         }
         case multichassis-tag {
           container multi-routing-engine-results {
             list multi-routing-engine-item {
               leaf re-name {
                 type string;
               }
               choice output-tags {
                 case actual-tag {
                   container forward-header-lookup-statistics {
                     uses forward-header-lookup-statistics-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ift-global-information-block {
     container ift-global {
       leaf device-id {
         type uint32;
         description
           "Unique device identifier";
       }
       leaf meta-data-stack-length {
         type uint32;
         description
           "Maximum length of the meta-data";
       }
       leaf hop-limit {
         type uint32;
         description
           "Maximum hop limit";
       }
       leaf flow-type {
         type string;
         description
           "Traffic flow type";
       }
       leaf mode {
         type string;
         description
           "IFA mode type - live or probe";
       }
       leaf no-ipv6-address-match {
         type uint32;
         description
           "IPV6 address match allowed or not";
       }
       leaf clock-source {
         type string;
         description
           "Clock source for timestamping";
       }
     }
   }
   grouping ift-profile-information-block {
     list ift-profile {
       leaf profile-name {
         type string;
         description
           "Profile name";
       }
       leaf sample-rate {
         type uint32;
         description
           "Ratio of packets to be sampled (1 out of N)";
       }
       container collector-info {
         leaf source-address {
           type string;
           description
             "Source address";
         }
         leaf destination-address {
           type string;
           description
             "Destination address";
         }
         leaf destination-port {
           type int32;
           description
             "Destination port";
         }
         leaf maximum-clip-length {
           type int32;
           description
             "Clip length of data packet";
         }
         leaf mtu {
           type int32;
           description
             "MTU of export packets";
         }
       }
     }
   }
   grouping ift-stats-information-block {
     container ift-stats {
       leaf init-packets {
         type uint64;
         description
           "IFA initator statistics";
       }
       leaf transit-packets {
         type uint64;
         description
           "IFA transit statistics";
       }
       leaf terminate-rx-packets {
         type uint64;
         description
           "IFA termination rx statistics";
       }
       leaf terminate-tx-packets {
         type uint64;
         description
           "IFA termination tx statistics";
       }
       leaf terminate-tx-records {
         type uint64;
         description
           "IFA termination tx records";
       }
     }
   }
   grouping aamw-statistics-block {
     leaf aamw-statistics-interested {
       type uint32;
     }
     leaf aamw-statistics-ignored {
       type uint32;
     }
     leaf aamw-statistics-blacklist-hit-counter {
       type uint32;
     }
     leaf aamw-statistics-whitelist-hit-counter {
       type uint32;
     }
     leaf aamw-statistics-total-session-actives {
       type uint32;
     }
     leaf aamw-statistics-http-session-actives {
       type uint32;
     }
     leaf aamw-statistics-https-session-actives {
       type uint32;
     }
     leaf aamw-statistics-http2-session-actives {
       type uint32;
     }
     leaf aamw-statistics-smtp-session-actives {
       type uint32;
     }
     leaf aamw-statistics-smtps-session-actives {
       type uint32;
     }
     leaf aamw-statistics-imap-session-actives {
       type uint32;
     }
     leaf aamw-statistics-imaps-session-actives {
       type uint32;
     }
     leaf aamw-statistics-smb-session-actives {
       type uint32;
     }
     leaf aamw-statistics-total-session-blocked {
       type uint32;
     }
     leaf aamw-statistics-http-session-blocked {
       type uint32;
     }
     leaf aamw-statistics-https-session-blocked {
       type uint32;
     }
     leaf aamw-statistics-http2-session-blocked {
       type uint32;
     }
     leaf aamw-statistics-smtp-session-blocked {
       type uint32;
     }
     leaf aamw-statistics-smtps-session-blocked {
       type uint32;
     }
     leaf aamw-statistics-imap-session-blocked {
       type uint32;
     }
     leaf aamw-statistics-imaps-session-blocked {
       type uint32;
     }
     leaf aamw-statistics-smb-session-blocked {
       type uint32;
     }
     leaf aamw-statistics-total-session-permitted {
       type uint32;
     }
     leaf aamw-statistics-http-session-permitted {
       type uint32;
     }
     leaf aamw-statistics-https-session-permitted {
       type uint32;
     }
     leaf aamw-statistics-http2-session-permitted {
       type uint32;
     }
     leaf aamw-statistics-smtp-session-permitted {
       type uint32;
     }
     leaf aamw-statistics-smtps-session-permitted {
       type uint32;
     }
     leaf aamw-statistics-imap-session-permitted {
       type uint32;
     }
     leaf aamw-statistics-imaps-session-permitted {
       type uint32;
     }
     leaf aamw-statistics-smb-session-permitted {
       type uint32;
     }
     leaf aamw-statistics-total-file-submission-success {
       type uint32;
     }
     leaf aamw-statistics-http-file-submission-success {
       type uint32;
     }
     leaf aamw-statistics-https-file-submission-success {
       type uint32;
     }
     leaf aamw-statistics-http2-file-submission-success {
       type uint32;
     }
     leaf aamw-statistics-smtp-file-submission-success {
       type uint32;
     }
     leaf aamw-statistics-smtps-file-submission-success {
       type uint32;
     }
     leaf aamw-statistics-imap-file-submission-success {
       type uint32;
     }
     leaf aamw-statistics-imaps-file-submission-success {
       type uint32;
     }
     leaf aamw-statistics-smb-file-submission-success {
       type uint32;
     }
     leaf aamw-statistics-total-file-submission-failure {
       type uint32;
     }
     leaf aamw-statistics-http-file-submission-failure {
       type uint32;
     }
     leaf aamw-statistics-https-file-submission-failure {
       type uint32;
     }
     leaf aamw-statistics-http2-file-submission-failure {
       type uint32;
     }
     leaf aamw-statistics-smtp-file-submission-failure {
       type uint32;
     }
     leaf aamw-statistics-smtps-file-submission-failure {
       type uint32;
     }
     leaf aamw-statistics-imap-file-submission-failure {
       type uint32;
     }
     leaf aamw-statistics-imaps-file-submission-failure {
       type uint32;
     }
     leaf aamw-statistics-smb-file-submission-failure {
       type uint32;
     }
     leaf aamw-statistics-total-file-submission-not-needed {
       type uint32;
     }
     leaf aamw-statistics-http-file-submission-not-needed {
       type uint32;
     }
     leaf aamw-statistics-https-file-submission-not-needed {
       type uint32;
     }
     leaf aamw-statistics-http2-file-submission-not-needed {
       type uint32;
     }
     leaf aamw-statistics-smtp-file-submission-not-needed {
       type uint32;
     }
     leaf aamw-statistics-smtps-file-submission-not-needed {
       type uint32;
     }
     leaf aamw-statistics-imap-file-submission-not-needed {
       type uint32;
     }
     leaf aamw-statistics-imaps-file-submission-not-needed {
       type uint32;
     }
     leaf aamw-statistics-smb-file-submission-not-needed {
       type uint32;
     }
     leaf aamw-statistics-total-file-verdict-meets_threshold {
       type uint32;
     }
     leaf aamw-statistics-http-file-verdict-meets_threshold {
       type uint32;
     }
     leaf aamw-statistics-https-file-verdict-meets_threshold {
       type uint32;
     }
     leaf aamw-statistics-http2-file-verdict-meets-threshold {
       type uint32;
     }
     leaf aamw-statistics-smtp-file-verdict-meets_threshold {
       type uint32;
     }
     leaf aamw-statistics-smtps-file-verdict-meets_threshold {
       type uint32;
     }
     leaf aamw-statistics-imap-file-verdict-meets_threshold {
       type uint32;
     }
     leaf aamw-statistics-imaps-file-verdict-meets_threshold {
       type uint32;
     }
     leaf aamw-statistics-smb-file-verdict-meets_threshold {
       type uint32;
     }
     leaf aamw-statistics-total-file-verdict-under_threshold {
       type uint32;
     }
     leaf aamw-statistics-http-file-verdict-under_threshold {
       type uint32;
     }
     leaf aamw-statistics-https-file-verdict-under_threshold {
       type uint32;
     }
     leaf aamw-statistics-http2-file-verdict-under-threshold {
       type uint32;
     }
     leaf aamw-statistics-smtp-file-verdict-under_threshold {
       type uint32;
     }
     leaf aamw-statistics-smtps-file-verdict-under_threshold {
       type uint32;
     }
     leaf aamw-statistics-imap-file-verdict-under_threshold {
       type uint32;
     }
     leaf aamw-statistics-imaps-file-verdict-under_threshold {
       type uint32;
     }
     leaf aamw-statistics-smb-file-verdict-under_threshold {
       type uint32;
     }
     leaf aamw-statistics-total-file-fallback-blocked {
       type uint32;
     }
     leaf aamw-statistics-http-file-fallback-blocked {
       type uint32;
     }
     leaf aamw-statistics-https-file-fallback-blocked {
       type uint32;
     }
     leaf aamw-statistics-http2-file-fallback-blocked {
       type uint32;
     }
     leaf aamw-statistics-smtp-file-fallback-blocked {
       type uint32;
     }
     leaf aamw-statistics-smtps-file-fallback-blocked {
       type uint32;
     }
     leaf aamw-statistics-imap-file-fallback-blocked {
       type uint32;
     }
     leaf aamw-statistics-imaps-file-fallback-blocked {
       type uint32;
     }
     leaf aamw-statistics-smb-file-fallback-blocked {
       type uint32;
     }
     leaf aamw-statistics-total-fallback-block-service-not-ready {
       type uint32;
     }
     leaf aamw-statistics-http-fallback-block-service-not-ready {
       type uint32;
     }
     leaf aamw-statistics-https-fallback-block-service-not-ready {
       type uint32;
     }
     leaf aamw-statistics-http2-fallback-block-service-not-ready {
       type uint32;
     }
     leaf aamw-statistics-smtp-fallback-block-service-not-ready {
       type uint32;
     }
     leaf aamw-statistics-smtps-fallback-block-service-not-ready {
       type uint32;
     }
     leaf aamw-statistics-imap-fallback-block-service-not-ready {
       type uint32;
     }
     leaf aamw-statistics-imaps-fallback-block-service-not-ready {
       type uint32;
     }
     leaf aamw-statistics-smb-fallback-block-service-not-ready {
       type uint32;
     }
     leaf aamw-statistics-total-fallback-block-out-of-resource {
       type uint32;
     }
     leaf aamw-statistics-http-fallback-block-out-of-resource {
       type uint32;
     }
     leaf aamw-statistics-https-fallback-block-out-of-resource {
       type uint32;
     }
     leaf aamw-statistics-http2-fallback-block-out-of-resource {
       type uint32;
     }
     leaf aamw-statistics-smtp-fallback-block-out-of-resource {
       type uint32;
     }
     leaf aamw-statistics-smtps-fallback-block-out-of-resource {
       type uint32;
     }
     leaf aamw-statistics-imap-fallback-block-out-of-resource {
       type uint32;
     }
     leaf aamw-statistics-imaps-fallback-block-out-of-resource {
       type uint32;
     }
     leaf aamw-statistics-smb-fallback-block-out-of-resource {
       type uint32;
     }
     leaf aamw-statistics-total-fallback-block-content-size {
       type uint32;
     }
     leaf aamw-statistics-http-fallback-block-content-size {
       type uint32;
     }
     leaf aamw-statistics-https-fallback-block-content-size {
       type uint32;
     }
     leaf aamw-statistics-http2-fallback-block-content-size {
       type uint32;
     }
     leaf aamw-statistics-smtp-fallback-block-content-size {
       type uint32;
     }
     leaf aamw-statistics-smtps-fallback-block-content-size {
       type uint32;
     }
     leaf aamw-statistics-imap-fallback-block-content-size {
       type uint32;
     }
     leaf aamw-statistics-imaps-fallback-block-content-size {
       type uint32;
     }
     leaf aamw-statistics-smb-fallback-block-content-size {
       type uint32;
     }
     leaf aamw-statistics-total-fallback-block-timeout {
       type uint32;
     }
     leaf aamw-statistics-http-fallback-block-timeout {
       type uint32;
     }
     leaf aamw-statistics-https-fallback-block-timeout {
       type uint32;
     }
     leaf aamw-statistics-http2-fallback-block-timeout {
       type uint32;
     }
     leaf aamw-statistics-smtp-fallback-block-timeout {
       type uint32;
     }
     leaf aamw-statistics-smtps-fallback-block-timeout {
       type uint32;
     }
     leaf aamw-statistics-imap-fallback-block-timeout {
       type uint32;
     }
     leaf aamw-statistics-imaps-fallback-block-timeout {
       type uint32;
     }
     leaf aamw-statistics-smb-fallback-block-timeout {
       type uint32;
     }
     leaf aamw-statistics-total-fallback-block-unknown-file {
       type uint32;
     }
     leaf aamw-statistics-http-fallback-block-unknown-file {
       type uint32;
     }
     leaf aamw-statistics-https-fallback-block-unknown-file {
       type uint32;
     }
     leaf aamw-statistics-http2-fallback-block-unknown-file {
       type uint32;
     }
     leaf aamw-statistics-smtp-fallback-block-unknown-file {
       type uint32;
     }
     leaf aamw-statistics-smtps-fallback-block-unknown-file {
       type uint32;
     }
     leaf aamw-statistics-imap-fallback-block-unknown-file {
       type uint32;
     }
     leaf aamw-statistics-imaps-fallback-block-unknown-file {
       type uint32;
     }
     leaf aamw-statistics-smb-fallback-block-unknown-file {
       type uint32;
     }
     leaf aamw-statistics-total-file-fallback-permitted {
       type uint32;
     }
     leaf aamw-statistics-http-file-fallback-permitted {
       type uint32;
     }
     leaf aamw-statistics-https-file-fallback-permitted {
       type uint32;
     }
     leaf aamw-statistics-http2-file-fallback-permitted {
       type uint32;
     }
     leaf aamw-statistics-smtp-file-fallback-permitted {
       type uint32;
     }
     leaf aamw-statistics-smtps-file-fallback-permitted {
       type uint32;
     }
     leaf aamw-statistics-imap-file-fallback-permitted {
       type uint32;
     }
     leaf aamw-statistics-imaps-file-fallback-permitted {
       type uint32;
     }
     leaf aamw-statistics-smb-file-fallback-permitted {
       type uint32;
     }
     leaf aamw-statistics-total-fallback-permit-service-not-ready {
       type uint32;
     }
     leaf aamw-statistics-http-fallback-permit-service-not-ready {
       type uint32;
     }
     leaf aamw-statistics-https-fallback-permit-service-not-ready {
       type uint32;
     }
     leaf aamw-statistics-http2-fallback-permit-service-not-ready {
       type uint32;
     }
     leaf aamw-statistics-smtp-fallback-permit-service-not-ready {
       type uint32;
     }
     leaf aamw-statistics-smtps-fallback-permit-service-not-ready {
       type uint32;
     }
     leaf aamw-statistics-imap-fallback-permit-service-not-ready {
       type uint32;
     }
     leaf aamw-statistics-imaps-fallback-permit-service-not-ready {
       type uint32;
     }
     leaf aamw-statistics-smb-fallback-permit-service-not-ready {
       type uint32;
     }
     leaf aamw-statistics-total-fallback-permit-out-of-resource {
       type uint32;
     }
     leaf aamw-statistics-http-fallback-permit-out-of-resource {
       type uint32;
     }
     leaf aamw-statistics-https-fallback-permit-out-of-resource {
       type uint32;
     }
     leaf aamw-statistics-http2-fallback-permit-out-of-resource {
       type uint32;
     }
     leaf aamw-statistics-smtp-fallback-permit-out-of-resource {
       type uint32;
     }
     leaf aamw-statistics-smtps-fallback-permit-out-of-resource {
       type uint32;
     }
     leaf aamw-statistics-imap-fallback-permit-out-of-resource {
       type uint32;
     }
     leaf aamw-statistics-imaps-fallback-permit-out-of-resource {
       type uint32;
     }
     leaf aamw-statistics-smb-fallback-permit-out-of-resource {
       type uint32;
     }
     leaf aamw-statistics-total-fallback-permit-content-size {
       type uint32;
     }
     leaf aamw-statistics-http-fallback-permit-content-size {
       type uint32;
     }
     leaf aamw-statistics-https-fallback-permit-content-size {
       type uint32;
     }
     leaf aamw-statistics-http2-fallback-permit-content-size {
       type uint32;
     }
     leaf aamw-statistics-smtp-fallback-permit-content-size {
       type uint32;
     }
     leaf aamw-statistics-smtps-fallback-permit-content-size {
       type uint32;
     }
     leaf aamw-statistics-imap-fallback-permit-content-size {
       type uint32;
     }
     leaf aamw-statistics-imaps-fallback-permit-content-size {
       type uint32;
     }
     leaf aamw-statistics-smb-fallback-permit-content-size {
       type uint32;
     }
     leaf aamw-statistics-total-fallback-permit-timeout {
       type uint32;
     }
     leaf aamw-statistics-http-fallback-permit-timeout {
       type uint32;
     }
     leaf aamw-statistics-https-fallback-permit-timeout {
       type uint32;
     }
     leaf aamw-statistics-http2-fallback-permit-timeout {
       type uint32;
     }
     leaf aamw-statistics-smtp-fallback-permit-timeout {
       type uint32;
     }
     leaf aamw-statistics-smtps-fallback-permit-timeout {
       type uint32;
     }
     leaf aamw-statistics-imap-fallback-permit-timeout {
       type uint32;
     }
     leaf aamw-statistics-imaps-fallback-permit-timeout {
       type uint32;
     }
     leaf aamw-statistics-smb-fallback-permit-timeout {
       type uint32;
     }
     leaf aamw-statistics-total-fallback-permit-unknown-file {
       type uint32;
     }
     leaf aamw-statistics-http-fallback-permit-unknown-file {
       type uint32;
     }
     leaf aamw-statistics-https-fallback-permit-unknown-file {
       type uint32;
     }
     leaf aamw-statistics-http2-fallback-permit-unknown-file {
       type uint32;
     }
     leaf aamw-statistics-smtp-fallback-permit-unknown-file {
       type uint32;
     }
     leaf aamw-statistics-smtps-fallback-permit-unknown-file {
       type uint32;
     }
     leaf aamw-statistics-imap-fallback-permit-unknown-file {
       type uint32;
     }
     leaf aamw-statistics-imaps-fallback-permit-unknown-file {
       type uint32;
     }
     leaf aamw-statistics-smb-fallback-permit-unknown-file {
       type uint32;
     }
     leaf aamw-statistics-total-file-ignored_by_sample_rate {
       type uint32;
     }
     leaf aamw-statistics-http-file-ignored_by_sample_rate {
       type uint32;
     }
     leaf aamw-statistics-https-file-ignored_by_sample_rate {
       type uint32;
     }
     leaf aamw-statistics-http2-file-ignored-by-sample-rate {
       type uint32;
     }
     leaf aamw-statistics-smtp-file-ignored_by_sample_rate {
       type uint32;
     }
     leaf aamw-statistics-smtps-file-ignored_by_sample_rate {
       type uint32;
     }
     leaf aamw-statistics-imap-file-ignored_by_sample_rate {
       type uint32;
     }
     leaf aamw-statistics-imaps-file-ignored_by_sample_rate {
       type uint32;
     }
     leaf aamw-statistics-smb-file-ignored_by_sample_rate {
       type uint32;
     }
     leaf aamw-statistics-total-email-scanned {
       type uint32;
     }
     leaf aamw-statistics-smtp-email-scanned {
       type uint32;
     }
     leaf aamw-statistics-smtps-email-scanned {
       type uint32;
     }
     leaf aamw-statistics-imap-email-scanned {
       type uint32;
     }
     leaf aamw-statistics-imaps-email-scanned {
       type uint32;
     }
     leaf aamw-statistics-total-email-permitted {
       type uint32;
     }
     leaf aamw-statistics-smtp-email-permitted {
       type uint32;
     }
     leaf aamw-statistics-smtps-email-permitted {
       type uint32;
     }
     leaf aamw-statistics-imap-email-permitted {
       type uint32;
     }
     leaf aamw-statistics-imaps-email-permitted {
       type uint32;
     }
     leaf aamw-statistics-total-email-blocked {
       type uint32;
     }
     leaf aamw-statistics-smtp-email-blocked {
       type uint32;
     }
     leaf aamw-statistics-smtps-email-blocked {
       type uint32;
     }
     leaf aamw-statistics-imap-email-blocked {
       type uint32;
     }
     leaf aamw-statistics-imaps-email-blocked {
       type uint32;
     }
     leaf aamw-statistics-total-email-tag-and-delivered {
       type uint32;
     }
     leaf aamw-statistics-smtp-email-tag-and-delivered {
       type uint32;
     }
     leaf aamw-statistics-smtps-email-tag-and-delivered {
       type uint32;
     }
     leaf aamw-statistics-imap-email-tag-and-delivered {
       type uint32;
     }
     leaf aamw-statistics-imaps-email-tag-and-delivered {
       type uint32;
     }
     leaf aamw-statistics-total-email-quarantined {
       type uint32;
     }
     leaf aamw-statistics-smtp-email-quarantined {
       type uint32;
     }
     leaf aamw-statistics-smtps-email-quarantined {
       type uint32;
     }
     leaf aamw-statistics-imap-email-quarantined {
       type uint32;
     }
     leaf aamw-statistics-imaps-email-quarantined {
       type uint32;
     }
     leaf aamw-statistics-total-email-fallback-blocked {
       type uint32;
     }
     leaf aamw-statistics-smtp-email-fallback-blocked {
       type uint32;
     }
     leaf aamw-statistics-smtps-email-fallback-blocked {
       type uint32;
     }
     leaf aamw-statistics-imap-email-fallback-blocked {
       type uint32;
     }
     leaf aamw-statistics-imaps-email-fallback-blocked {
       type uint32;
     }
     leaf aamw-statistics-total-email-fallback-block-service-not-ready {
       type uint32;
     }
     leaf aamw-statistics-smtp-email-fallback-block-service-not-ready {
       type uint32;
     }
     leaf aamw-statistics-smtps-email-fallback-block-service-not-ready {
       type uint32;
     }
     leaf aamw-statistics-imap-email-fallback-block-service-not-ready {
       type uint32;
     }
     leaf aamw-statistics-imaps-email-fallback-block-service-not-ready {
       type uint32;
     }
     leaf aamw-statistics-total-email-fallback-block-out-of-resource {
       type uint32;
     }
     leaf aamw-statistics-smtp-email-fallback-block-out-of-resource {
       type uint32;
     }
     leaf aamw-statistics-smtps-email-fallback-block-out-of-resource {
       type uint32;
     }
     leaf aamw-statistics-imap-email-fallback-block-out-of-resource {
       type uint32;
     }
     leaf aamw-statistics-imaps-email-fallback-block-out-of-resource {
       type uint32;
     }
     leaf aamw-statistics-total-email-fallback-block-content-size {
       type uint32;
     }
     leaf aamw-statistics-smtp-email-fallback-block-content-size {
       type uint32;
     }
     leaf aamw-statistics-smtps-email-fallback-block-content-size {
       type uint32;
     }
     leaf aamw-statistics-imap-email-fallback-block-content-size {
       type uint32;
     }
     leaf aamw-statistics-imaps-email-fallback-block-content-size {
       type uint32;
     }
     leaf aamw-statistics-total-email-fallback-block-timeout {
       type uint32;
     }
     leaf aamw-statistics-smtp-email-fallback-block-timeout {
       type uint32;
     }
     leaf aamw-statistics-smtps-email-fallback-block-timeout {
       type uint32;
     }
     leaf aamw-statistics-imap-email-fallback-block-timeout {
       type uint32;
     }
     leaf aamw-statistics-imaps-email-fallback-block-timeout {
       type uint32;
     }
     leaf aamw-statistics-total-email-fallback-block-unknown-file {
       type uint32;
     }
     leaf aamw-statistics-smtp-email-fallback-block-unknown-file {
       type uint32;
     }
     leaf aamw-statistics-smtps-email-fallback-block-unknown-file {
       type uint32;
     }
     leaf aamw-statistics-imap-email-fallback-block-unknown-file {
       type uint32;
     }
     leaf aamw-statistics-imaps-email-fallback-block-unknown-file {
       type uint32;
     }
     leaf aamw-statistics-total-email-fallback-permitted {
       type uint32;
     }
     leaf aamw-statistics-smtp-email-fallback-permitted {
       type uint32;
     }
     leaf aamw-statistics-smtps-email-fallback-permitted {
       type uint32;
     }
     leaf aamw-statistics-imap-email-fallback-permitted {
       type uint32;
     }
     leaf aamw-statistics-imaps-email-fallback-permitted {
       type uint32;
     }
     leaf aamw-statistics-total-email-fallback-permit-service-not-ready {
       type uint32;
     }
     leaf aamw-statistics-smtp-email-fallback-permit-service-not-ready {
       type uint32;
     }
     leaf aamw-statistics-smtps-email-fallback-permit-service-not-ready {
       type uint32;
     }
     leaf aamw-statistics-imap-email-fallback-permit-service-not-ready {
       type uint32;
     }
     leaf aamw-statistics-imaps-email-fallback-permit-service-not-ready {
       type uint32;
     }
     leaf aamw-statistics-total-email-fallback-permit-out-of-resource {
       type uint32;
     }
     leaf aamw-statistics-smtp-email-fallback-permit-out-of-resource {
       type uint32;
     }
     leaf aamw-statistics-smtps-email-fallback-permit-out-of-resource {
       type uint32;
     }
     leaf aamw-statistics-imap-email-fallback-permit-out-of-resource {
       type uint32;
     }
     leaf aamw-statistics-imaps-email-fallback-permit-out-of-resource {
       type uint32;
     }
     leaf aamw-statistics-total-email-fallback-permit-content-size {
       type uint32;
     }
     leaf aamw-statistics-smtp-email-fallback-permit-content-size {
       type uint32;
     }
     leaf aamw-statistics-smtps-email-fallback-permit-content-size {
       type uint32;
     }
     leaf aamw-statistics-imap-email-fallback-permit-content-size {
       type uint32;
     }
     leaf aamw-statistics-imaps-email-fallback-permit-content-size {
       type uint32;
     }
     leaf aamw-statistics-total-email-fallback-permit-timeout {
       type uint32;
     }
     leaf aamw-statistics-smtp-email-fallback-permit-timeout {
       type uint32;
     }
     leaf aamw-statistics-smtps-email-fallback-permit-timeout {
       type uint32;
     }
     leaf aamw-statistics-imap-email-fallback-permit-timeout {
       type uint32;
     }
     leaf aamw-statistics-imaps-email-fallback-permit-timeout {
       type uint32;
     }
     leaf aamw-statistics-total-email-fallback-permit-unknown-file {
       type uint32;
     }
     leaf aamw-statistics-smtp-email-fallback-permit-unknown-file {
       type uint32;
     }
     leaf aamw-statistics-smtps-email-fallback-permit-unknown-file {
       type uint32;
     }
     leaf aamw-statistics-imap-email-fallback-permit-unknown-file {
       type uint32;
     }
     leaf aamw-statistics-imaps-email-fallback-permit-unknown-file {
       type uint32;
     }
     leaf aamw-statistics-total-email-hit-whitelist {
       type uint32;
     }
     leaf aamw-statistics-smtp-email-hit-whitelist {
       type uint32;
     }
     leaf aamw-statistics-smtps-email-hit-whitelist {
       type uint32;
     }
     leaf aamw-statistics-imap-email-hit-whitelist {
       type uint32;
     }
     leaf aamw-statistics-imaps-email-hit-whitelist {
       type uint32;
     }
     leaf aamw-statistics-total-email-hit-blacklist {
       type uint32;
     }
     leaf aamw-statistics-smtp-email-blacklist {
       type uint32;
     }
     leaf aamw-statistics-smtps-email-blacklist {
       type uint32;
     }
     leaf aamw-statistics-imap-email-blacklist {
       type uint32;
     }
     leaf aamw-statistics-imaps-email-blacklist {
       type uint32;
     }
     leaf aamw-statistics-total-hash-eligible {
       type uint32;
     }
     leaf aamw-statistics-http-hash-eligible {
       type uint32;
     }
     leaf aamw-statistics-https-hash-eligible {
       type uint32;
     }
     leaf aamw-statistics-total-hash-selected {
       type uint32;
     }
     leaf aamw-statistics-http-hash-selected {
       type uint32;
     }
     leaf aamw-statistics-https-hash-selected {
       type uint32;
     }
     leaf aamw-statistics-total-hash-submitted {
       type uint32;
     }
     leaf aamw-statistics-http-hash-submitted {
       type uint32;
     }
     leaf aamw-statistics-https-hash-submitted {
       type uint32;
     }
     leaf aamw-statistics-total-hash-fail {
       type uint32;
     }
     leaf aamw-statistics-http-hash-fail {
       type uint32;
     }
     leaf aamw-statistics-https-hash-fail {
       type uint32;
     }
     leaf aamw-statistics-total-hash-known {
       type uint32;
     }
     leaf aamw-statistics-http-hash-known {
       type uint32;
     }
     leaf aamw-statistics-https-hash-known {
       type uint32;
     }
     leaf aamw-statistics-total-hash-unknown {
       type uint32;
     }
     leaf aamw-statistics-http-hash-unknown {
       type uint32;
     }
     leaf aamw-statistics-https-hash-unknown {
       type uint32;
     }
     leaf aamw-statistics-total-hash-verdict-timeout {
       type uint32;
     }
     leaf aamw-statistics-http-hash-verdict-timeout {
       type uint32;
     }
     leaf aamw-statistics-https-hash-verdict-timeout {
       type uint32;
     }
   }
   grouping aamw-redirect-files-block {
     leaf aamw-redirect-files-name {
       type string;
     }
     leaf aamw-redirect-files-size {
       type uint64;
     }
     leaf aamw-redirect-files-time {
       type string;
     }
     leaf aamw-redirect-file-content {
       type string;
     }
   }
   grouping aamw-policy-block {
     leaf aamw-policy-name {
       type string;
     }
     leaf aamw-used-profile-name {
       type string;
     }
     leaf aamw-applications {
       type string;
     }
     leaf aamw-verdict-number {
       type string;
     }
     leaf aamw-verdict-action {
       type string;
     }
     leaf aamw-verdict-notification {
       type string;
     }
     leaf aamw-default-notification {
       type string;
     }
     leaf aamw-whitelist-notification {
       type string;
     }
     leaf aamw-blacklist-notification {
       type string;
     }
     leaf aamw-policy-header {
       type string;
     }
     leaf aamw-fallback-action {
       type string;
     }
     leaf aamw-fallback-notification {
       type string;
     }
     leaf aamw-ml-scan-header {
       type string;
     }
     leaf aamw-ml-scan-action {
       type string;
     }
     leaf aamw-ml-scan-notification {
       type string;
     }
     leaf aamw-ml-default-notification {
       type string;
     }
     leaf aamw-protocol-name {
       type string;
     }
     leaf aamw-protocol-profile-name {
       type string;
     }
     leaf aamw-protocol-verdict-number {
       type string;
     }
     leaf aamw-protocol-verdict-action {
       type string;
     }
     leaf aamw-protocol-verdict-notification {
       type string;
     }
   }
   grouping aamw-profile-block {
     leaf aamw-profile-name {
       type string;
     }
     leaf aamw-profile-version {
       type uint32;
     }
     leaf aamw-profile-desc {
       type string;
     }
     leaf aamw-profile-disable_ftype {
       type string;
     }
     leaf aamw-profile-disable-category {
       type string;
     }
     leaf aamw-profile-category-sample {
       type string;
     }
   }
   grouping aamw-status-block {
     leaf aamw-server-hostname {
       type string;
     }
     leaf aamw-server-realm {
       type string;
     }
     leaf aamw-server-port {
       type uint32;
     }
     leaf aamw-proxy-hostname {
       type string;
     }
     leaf aamw-proxy-port {
       type string;
     }
     leaf aamw-detail-header1 {
       type string;
     }
     leaf aamw-connection-time {
       type string;
     }
     leaf aamw-connection-status {
       type string;
     }
     leaf aamw-detail-header2 {
       type string;
     }
     leaf aamw-card-info {
       type string;
     }
     leaf aamw-connection-active-number {
       type uint32;
     }
     leaf aamw-connection-failures {
       type uint32;
     }
   }
   grouping aamw-default-policy-block {
     leaf aamw-policy-name {
       type string;
     }
     leaf aamw-used-profile-name {
       type string;
     }
     leaf aamw-applications {
       type string;
     }
     leaf aamw-verdict-number {
       type string;
     }
     leaf aamw-verdict-action {
       type string;
     }
     leaf aamw-verdict-notification {
       type string;
     }
     leaf aamw-default-notification {
       type string;
     }
     leaf aamw-whitelist-notification {
       type string;
     }
     leaf aamw-blacklist-notification {
       type string;
     }
     leaf aamw-policy-header {
       type string;
     }
     leaf aamw-fallback-action {
       type string;
     }
     leaf aamw-fallback-notification {
       type string;
     }
     leaf aamw-ml-scan-header {
       type string;
     }
     leaf aamw-ml-scan-action {
       type string;
     }
     leaf aamw-ml-scan-notification {
       type string;
     }
     leaf aamw-ml-default-notification {
       type string;
     }
     leaf aamw-protocol-name {
       type string;
     }
     leaf aamw-protocol-profile-name {
       type string;
     }
     leaf aamw-protocol-verdict-number {
       type string;
     }
     leaf aamw-protocol-verdict-action {
       type string;
     }
     leaf aamw-protocol-verdict-notification {
       type string;
     }
   }
   grouping aamw-version-block {
     leaf aamw-version-email-config {
       type uint32;
     }
     leaf aamw-version-global-whitelist {
       type uint32;
     }
     leaf aamw-version-global-blacklist {
       type uint32;
     }
     leaf aamw-version-custom-whitelist {
       type uint32;
     }
     leaf aamw-version-custom-blacklist {
       type uint32;
     }
     leaf aamw-version-category-mapping {
       type uint32;
     }
     leaf aamw-version-ideneification-signature {
       type uint32;
     }
   }
   grouping aamw-sig-exempt-list-block {
     leaf-list aamw-sig-exempt-list-sig-id {
       type string;
     }
     leaf aamw-sig-exempt-list-count {
       type uint32;
     }
   }
   grouping dynamic-filtering-connection-status-block {
     leaf message {
       type string;
     }
     leaf url {
       type string;
     }
     leaf port {
       type int32;
     }
     leaf purl {
       type string;
     }
     leaf pport {
       type string;
     }
     container dynamic-filtering-connection-block {
       description
         "Display status for RE connections from dyn-filterd daemon";
       leaf conn-block-header {
         type string;
       }
       leaf conn-interface {
         type string;
       }
       leaf conn-count {
         type int32;
       }
       leaf conn-status {
         type string;
       }
       leaf conn-last-connect {
         type string;
       }
       leaf conn-last-failure {
         type string;
       }
       leaf conn-total-failure {
         type int32;
       }
       leaf conn-pkts-sent {
         type int32;
       }
       leaf conn-pkts-rcvd {
         type int32;
       }
     }
   }
   grouping sm-dns-statistics-block {
     leaf sm-dns-statistics-cache-hits {
       type uint64;
     }
     leaf sm-dns-statistics-cache-misses {
       type uint64;
     }
     leaf sm-dns-statistics-c2-sessions-permitted {
       type uint64;
     }
     leaf sm-dns-statistics-c2-sessions-dropped {
       type uint64;
     }
     leaf sm-dns-statistics-c2-sessions-sinkholed {
       type uint64;
     }
     leaf sm-dns-statistics-domain-submission-success {
       type uint64;
     }
     leaf sm-dns-statistics-domain-submission-failures {
       type uint64;
     }
     leaf sm-dns-statistics-safe-verdicts-received {
       type uint64;
     }
     leaf sm-dns-statistics-c2-verdicts-received {
       type uint64;
     }
     leaf sm-dns-statistics-dns-tunnels-detected {
       type uint64;
     }
     leaf sm-dns-statistics-latency-fallback-triggered {
       type uint64;
     }
     leaf sm-dns-statistics-average-latency {
       type uint32;
     }
     leaf sm-dns-statistics-maximum-latency {
       type uint32;
     }
     leaf sm-dns-statistics-minimum-latency {
       type uint32;
     }
     leaf sm-dns-statistics-sub50ms-response {
       type uint32;
     }
     leaf sm-dns-statistics-sub50ms-response-percent {
       type uint32;
     }
     leaf sm-dns-statistics-sub100ms-response {
       type uint32;
     }
     leaf sm-dns-statistics-sub100ms-response-percent {
       type uint32;
     }
     leaf sm-dns-statistics-sub250ms-response {
       type uint32;
     }
     leaf sm-dns-statistics-sub250ms-response-percent {
       type uint32;
     }
     leaf sm-dns-statistics-sub500ms-response {
       type uint32;
     }
     leaf sm-dns-statistics-sub500ms-response-percent {
       type uint32;
     }
     leaf-list logical-system-name {
       type string;
       description
         "Name of the logical system";
     }
     leaf-list dns-logical-system {
       type string;
       description
         "Logical system name";
     }
     leaf-list sm-dns-logical-system {
       type string;
       description
         "Logical system name";
     }
     leaf-list sm-dns-wl-logical-system {
       type string;
       description
         "Logical system name";
     }
   }
   grouping security-dynamic-address-block {
     leaf da-ipc-entry-add {
       type int32;
       description
         "Num of entry add IPC message object created";
     }
     leaf da-ipc-entry-del {
       type int32;
       description
         "Num of entry del IPC message object created";
     }
     leaf da-ipc-entry-trace-option {
       type int32;
       description
         "Num of trace option IPC message object created";
     }
     leaf da-ipc-batch-sent {
       type int32;
       description
         "Num of IPC message batches have been sent";
     }
     leaf da-malloc-failure {
       type int32;
       description
         "Counter of malloc failure";
     }
     leaf da-ipc-init {
       type string;
       description
         "Timestamp for IPC initialization";
     }
     leaf da-pfe-conn-first {
       type string;
       description
         "Timestamp for first PFE connection";
     }
     leaf da-pfe-conn-last {
       type string;
       description
         "Timestamp for last PFE connection";
     }
     leaf da-pfe-conn-failure {
       type string;
       description
         "Timestamp for last PFE connection failure";
     }
     leaf da-instance-name {
       type string;
       description
         "Name of dynamic address instance";
     }
     leaf da-ip-entry-idx {
       type int32;
       description
         "Position in found IP entries";
     }
     leaf da-ip-start {
       type string;
       description
         "Numerically minimal IP address within the range";
     }
     leaf da-ip-end {
       type string;
       description
         "Numerically maximal IP address within the range";
     }
     leaf da-name {
       type string;
       description
         "Dynamic address name";
     }
     leaf da-country-code {
       type string;
       description
         "Country code";
     }
     leaf da-lsys-name {
       type string;
       description
         "Logical system name";
     }
     leaf da-lsysinfo {
       type string;
       description
         "Dynamic address logical-system tenant name";
     }
     leaf feed-ref-da-name {
       type string;
       description
         "Dynamic address name";
     }
     leaf da-id {
       type int32;
       description
         "Dynamic address ID";
     }
     leaf da-sscan-status {
       type string;
       description
         "Dynamic address session scan module status";
     }
     leaf da-sscan-hold-interval {
       type string;
       description
         "Dynamic address session scan hold interval";
     }
     leaf da-sscan-entry-status {
       type string;
       description
         "Dynamic address session scan entry status";
     }
     leaf da-feed-server-name {
       type string;
       description
         "Feed server name";
     }
     leaf da-feed-server-lsysinfo {
       type string;
       description
         "Feed server logical-system tenant name";
     }
     leaf da-feed-name {
       type string;
       description
         "Feed source name";
     }
     leaf da-feed-lsysinfo {
       type string;
       description
         "Feed logical-system tenant name";
     }
     leaf da-category-name {
       type string;
       description
         "Category name";
     }
     leaf da-category-feed {
       type string;
       description
         "Category feed";
     }
     leaf da-property-name {
       type string;
       description
         "Property name";
     }
     leaf da-property-value {
       type string;
       description
         "Property value";
     }
     leaf da-property-value-start {
       type string;
       description
         "Property start value inclusive";
     }
     leaf da-property-value-end {
       type string;
       description
         "Property nd value inclusive";
     }
     leaf da-inst-name {
       type string;
       description
         "Dynamic address instance name";
     }
     leaf da-total-count {
       type int32;
       description
         "Number of entries";
     }
     leaf da-entry-cnt-v4 {
       type int32;
       description
         "IPv4 entry count";
     }
     leaf da-entry-cnt-v6 {
       type int32;
       description
         "IPv6 entry count";
     }
     leaf da-entry-cnt-mapping-feed {
       type int32;
       description
         "Mapping feed count";
     }
     leaf da-config-flags {
       type string;
       description
         "Configuration flags";
     }
     leaf da-feed-server-cnt {
       type int32;
       description
         "Number of feed server";
     }
     leaf da-feed-cnt {
       type int32;
       description
         "Number of feed";
     }
     leaf da-cnt {
       type int32;
       description
         "Number of dynamic address entry";
     }
     leaf da-cnt-total-v4 {
       type int32;
       description
         "IPv4 entry count";
     }
     leaf da-cnt-total-feed-v4 {
       type int32;
       description
         "IPv4 entry count from feed";
     }
     leaf da-cnt-total-v6 {
       type int32;
       description
         "IPv6 entry count";
     }
     leaf da-cnt-total-feed-v6 {
       type int32;
       description
         "IPv6 entry count from feed";
     }
     leaf da-feed-server-ca-profile-name {
       type string;
       description
         "Certificate profile name";
     }
     leaf da-feed-server-tls-profile-name {
       type string;
       description
         "TLS profile name";
     }
     leaf da-feed-server-user-name {
       type string;
       description
         "User name";
     }
     leaf da-feed-server-url {
       type string;
       description
         "Common url for feeds under same server";
     }
     leaf da-feed-server-routing-table {
       type string;
       description
         "Preferred routing table";
     }
     leaf da-feed-server-update-interval {
       type int32;
       description
         "The interval between end of last retrieval and start of next 
         retrieval when feed does not configure it";
     }
     leaf da-feed-server-hold-interval {
       type int32;
       description
         "The time to hold data when feed update failed";
     }
     leaf da-feed-update-interval {
       type int32;
       description
         "The interval between end of last retrieval and start of next 
         retrieval when feed does not configure it";
     }
     leaf da-feed-hold-interval {
       type int32;
       description
         "The time to hold data when feed update failed";
     }
     leaf da-feed-url {
       type int32;
       description
         "The URL to retreive dynamic address feed";
     }
     leaf da-feed-routing-table {
       type string;
       description
         "Preferred routing table";
     }
     leaf da-feed-ca-profile-name {
       type string;
       description
         "Certificate profile name";
     }
     leaf da-feed-stat-hist-total-update {
       type int32;
       description
         "Total number of updates on this feed";
     }
     leaf da-feed-stat-db-total-v4 {
       type int32;
       description
         "Total number of IPv4 entries in db from this feed";
     }
     leaf da-feed-stat-db-total-v6 {
       type int32;
       description
         "Total number of IPv6 entries in db from this feed";
     }
     leaf da-feed-stat-hist-total-err-download {
       type int32;
       description
         "Total number of download error on this feed";
     }
     leaf da-feed-stat-hist-total-err-db {
       type int32;
       description
         "Total number of db error on this feed";
     }
     leaf da-feed-stat-hist-total-err-other {
       type int32;
       description
         "Total number of other error on this feed";
     }
     leaf da-feed-stat-hist-total-ageout {
       type int32;
       description
         "Total number of ageout this feed";
     }
     leaf da-feed-stat-last-update-file-size {
       type int32;
       description
         "File size of last update";
     }
     leaf da-feed-stat-last-update-ipv4 {
       type int32;
       description
         "Total number of IPv4 entries contained in last update";
     }
     leaf da-feed-stat-last-update-ipv6 {
       type int32;
       description
         "Total number of IPv6 entries contained in last update";
     }
     leaf da-feed-stat-last-update-time-cost {
       type string;
       description
         "Seconds it took for last update parsing";
     }
     leaf da-feed-stat-last-download-time-cost {
       type string;
       description
         "Seconds it took for last downloading";
     }
     leaf da-feed-stat-last-update-begin-timestamp {
       type string;
       description
         "The time when last update began";
     }
     leaf da-feed-stat-last-update-end-timestamp {
       type string;
       description
         "The time when last update finished";
     }
     leaf da-feed-stat-last-update-status {
       type string;
       description
         "Last update status";
     }
     leaf da-feed-stat-last-download-begin-timestamp {
       type string;
       description
         "The time when last download began";
     }
     leaf da-feed-stat-last-download-end-timestamp {
       type string;
       description
         "The time when last download finished";
     }
     leaf da-feed-stat-last-err-download-timestamp {
       type string;
       description
         "The time when last download error happened";
     }
     leaf da-feed-stat-last-err-db-timestamp {
       type string;
       description
         "The time when last db error happened";
     }
     leaf da-feed-stat-last-err-other-timestamp {
       type string;
       description
         "The time when last other error happened";
     }
     leaf da-feed-stat-last-ageout-timestamp {
       type string;
       description
         "The time when last ageout happened";
     }
     leaf da-feed-stat-wakeup-update-time {
       type string;
       description
         "The time when next update happened";
     }
     leaf da-feed-stat-wakeup-expire-time {
       type string;
       description
         "The time when next expire happened";
     }
     leaf da-feed-stat-flag {
       type int32;
       description
         "Flags for feed";
     }
     container da-ip-entry {
       leaf da-ip-entry-idx {
         type int32;
         description
           "Position in found IP entries";
       }
       leaf da-ip-start {
         type string;
         description
           "Numerically minimal IP address within the range";
       }
       leaf da-ip-end {
         type string;
         description
           "Numerically maximal IP address within the range";
       }
       leaf da-feed-name {
         type string;
         description
           "Feed source name";
       }
       leaf da-name {
         type string;
         description
           "Dynamic address name";
       }
       leaf da-country-code {
         type string;
         description
           "Country code";
       }
     }
     container da-ip-entry-lsys {
       leaf da-ip-entry-idx {
         type int32;
         description
           "Position in found IP entries";
       }
       leaf da-ip-start {
         type string;
         description
           "Numerically minimal IP address within the range";
       }
       leaf da-ip-end {
         type string;
         description
           "Numerically maximal IP address within the range";
       }
       leaf da-feed-name {
         type string;
         description
           "Feed source name";
       }
       leaf da-name {
         type string;
         description
           "Dynamic address name";
       }
       leaf da-country-code {
         type string;
         description
           "Country code";
       }
       leaf da-lsys-name {
         type string;
         description
           "Logical system name";
       }
     }
     container da-ip-entry-foot {
       leaf da-inst-name {
         type string;
         description
           "Dynamic address instance name";
       }
       leaf da-total-count {
         type int32;
         description
           "Number of entries";
       }
     }
   }
   grouping av-policy-block {
     leaf av-policy-name {
       type string;
     }
     leaf av-policy-action {
       type string;
     }
     leaf av-policy-verdict-number {
       type string;
     }
     leaf av-policy-notification {
       type string;
     }
     leaf av-policy-default-notification {
       type string;
     }
     leaf av-policy-header {
       type string;
     }
     leaf av-policy-fallback-action {
       type string;
     }
     leaf av-policy-fallback-notification {
       type string;
     }
     leaf av-ml-scan-header {
       type string;
     }
     leaf av-ml-scan-action {
       type string;
     }
     leaf av-ml-scan-notification {
       type string;
     }
     leaf av-ml-default-notification {
       type string;
     }
   }
   grouping av-statistics-block {
     leaf av-statistics-db-type {
       type string;
     }
     leaf av-statistics-total-sigs {
       type uint32;
     }
     leaf av-statistics-db-version {
       type string;
     }
     leaf av-statistics-db-update-time {
       type string;
     }
     leaf av-statistics-total-files-scanned {
       type uint32;
     }
     leaf av-statistics-http-files-scanned {
       type uint32;
     }
     leaf av-statistics-https-files-scanned {
       type uint32;
     }
     leaf av-statistics-http2-files-scanned {
       type uint32;
     }
     leaf av-statistics-smtp-files-scanned {
       type uint32;
     }
     leaf av-statistics-smtps-files-scanned {
       type uint32;
     }
     leaf av-statistics-imap-files-scanned {
       type uint32;
     }
     leaf av-statistics-imaps-files-scanned {
       type uint32;
     }
     leaf av-statistics-smb-files-scanned {
       type uint32;
     }
     leaf av-statistics-total-files-found {
       type uint32;
     }
     leaf av-statistics-http-files-found {
       type uint32;
     }
     leaf av-statistics-https-files-found {
       type uint32;
     }
     leaf av-statistics-http2-files-found {
       type uint32;
     }
     leaf av-statistics-smtp-files-found {
       type uint32;
     }
     leaf av-statistics-smtps-files-found {
       type uint32;
     }
     leaf av-statistics-imap-files-found {
       type uint32;
     }
     leaf av-statistics-imaps-files-found {
       type uint32;
     }
     leaf av-statistics-smb-files-found {
       type uint32;
     }
     leaf av-statistics-total-files-blocked {
       type uint32;
     }
     leaf av-statistics-http-files-blocked {
       type uint32;
     }
     leaf av-statistics-https-files-blocked {
       type uint32;
     }
     leaf av-statistics-http2-files-blocked {
       type uint32;
     }
     leaf av-statistics-smtp-files-blocked {
       type uint32;
     }
     leaf av-statistics-smtps-files-blocked {
       type uint32;
     }
     leaf av-statistics-imap-files-blocked {
       type uint32;
     }
     leaf av-statistics-imaps-files-blocked {
       type uint32;
     }
     leaf av-statistics-smb-files-blocked {
       type uint32;
     }
     leaf av-statistics-total-files-permitted {
       type uint32;
     }
     leaf av-statistics-http-files-permitted {
       type uint32;
     }
     leaf av-statistics-https-files-permitted {
       type uint32;
     }
     leaf av-statistics-http2-files-permitted {
       type uint32;
     }
     leaf av-statistics-smtp-files-permitted {
       type uint32;
     }
     leaf av-statistics-smtps-files-permitted {
       type uint32;
     }
     leaf av-statistics-imap-files-permitted {
       type uint32;
     }
     leaf av-statistics-imaps-files-permitted {
       type uint32;
     }
     leaf av-statistics-smb-files-permitted {
       type uint32;
     }
     leaf av-statistics-block-cache-hit {
       type uint32;
     }
     leaf av-statistics-block-cache-current {
       type uint32;
     }
     leaf av-statistics-block-cache-timeout {
       type uint32;
     }
   }
   grouping av-ml-statistics-block {
     leaf av-ml-scan-engine-version {
       type string;
     }
     leaf av-ml-scan-engine-update-time {
       type string;
     }
     leaf av-ml-statistics-total-files-scanned {
       type uint32;
     }
     leaf av-ml-statistics-http-files-scanned {
       type uint32;
     }
     leaf av-ml-statistics-https-files-scanned {
       type uint32;
     }
     leaf av-ml-statistics-http2-files-scanned {
       type uint32;
     }
     leaf av-ml-statistics-smtp-files-scanned {
       type uint32;
     }
     leaf av-ml-statistics-smtps-files-scanned {
       type uint32;
     }
     leaf av-ml-statistics-imap-files-scanned {
       type uint32;
     }
     leaf av-ml-statistics-imaps-files-scanned {
       type uint32;
     }
     leaf av-ml-statistics-smb-files-scanned {
       type uint32;
     }
     leaf av-ml-statistics-total-files-found {
       type uint32;
     }
     leaf av-ml-statistics-http-files-found {
       type uint32;
     }
     leaf av-ml-statistics-https-files-found {
       type uint32;
     }
     leaf av-ml-statistics-http2-files-found {
       type uint32;
     }
     leaf av-ml-statistics-smtp-files-found {
       type uint32;
     }
     leaf av-ml-statistics-smtps-files-found {
       type uint32;
     }
     leaf av-ml-statistics-imap-files-found {
       type uint32;
     }
     leaf av-ml-statistics-imaps-files-found {
       type uint32;
     }
     leaf av-ml-statistics-smb-files-found {
       type uint32;
     }
     leaf av-ml-statistics-total-files-blocked {
       type uint32;
     }
     leaf av-ml-statistics-http-files-blocked {
       type uint32;
     }
     leaf av-ml-statistics-https-files-blocked {
       type uint32;
     }
     leaf av-ml-statistics-http2-files-blocked {
       type uint32;
     }
     leaf av-ml-statistics-smtp-files-blocked {
       type uint32;
     }
     leaf av-ml-statistics-smtps-files-blocked {
       type uint32;
     }
     leaf av-ml-statistics-imap-files-blocked {
       type uint32;
     }
     leaf av-ml-statistics-imaps-files-blocked {
       type uint32;
     }
     leaf av-ml-statistics-smb-files-blocked {
       type uint32;
     }
     leaf av-ml-statistics-total-files-permitted {
       type uint32;
     }
     leaf av-ml-statistics-http-files-permitted {
       type uint32;
     }
     leaf av-ml-statistics-https-files-permitted {
       type uint32;
     }
     leaf av-ml-statistics-http2-files-permitted {
       type uint32;
     }
     leaf av-ml-statistics-smtp-files-permitted {
       type uint32;
     }
     leaf av-ml-statistics-smtps-files-permitted {
       type uint32;
     }
     leaf av-ml-statistics-imap-files-permitted {
       type uint32;
     }
     leaf av-ml-statistics-imaps-files-permitted {
       type uint32;
     }
     leaf av-ml-statistics-smb-files-permitted {
       type uint32;
     }
   }
   grouping aamw-av-sig-exempt-list-block {
     leaf-list aamw-av-sig-exempt-list-sig-id {
       type string;
     }
     leaf aamw-av-sig-exempt-list-count {
       type uint64;
     }
   }
   grouping appid-application-signature-block {
     container application-signature-summary {
       description
         "Application signature summary";
       leaf total-applications {
         type int32;
         description
           "Total number of applications";
       }
       leaf total-nested-applications {
         type int32;
         description
           "Total number of nested applications";
       }
       list application-signature-list {
         leaf-list application-name {
           type string;
           description
             "Name of an application or nested application";
         }
         leaf application-disabled {
           type string;
           description
             "Whether an application or nested application is disabled";
         }
         leaf application-id {
           type int32;
           description
             "Application ID";
         }
         leaf application-order {
           type string;
           description
             "Application matching order";
         }
       }
     }
     container application-signature-detail {
       container application-signature-detail-header {
         leaf-list application-name {
           type string;
           description
             "Name of an application or nested application";
         }
         leaf application-type {
           type string;
           description
             "Type of an application or nested application";
         }
         leaf application-description {
           type string;
           description
             "Application description";
         }
         leaf application-id {
           type int32;
           description
             "Application ID";
         }
         leaf application-priority {
           type string;
           description
             "Application priority";
         }
         leaf application-order {
           type string;
           description
             "Application matching order";
         }
         leaf application-disabled {
           type string;
           description
             "Whether an application or nested application is disabled";
         }
         leaf application-cacheable {
           type string;
           description
             "Whether application is cacheable or not";
         }
         leaf application-configurable {
           type string;
           description
             "Whether application is configurable or not";
         }
         leaf application-activation-date {
           type string;
           description
             "Activation Date";
         }
         leaf application-last-modified {
           type string;
           description
             "Last Modified";
         }
         leaf application-number-parent-groups {
           type int32;
           description
             "Number of application's parent groups";
         }
         leaf application-expired-date {
           type string;
           description
             "When it may be expired";
         }
         leaf application-number-signatures {
           type int32;
           description
             "Number of signatures in an application";
         }
         list application-group-list {
           leaf-list group-name {
             type string;
             description
               "Application group name";
           }
         }
         list application-tag-list {
           container application-tag {
             leaf application-tag-name {
               type string;
               description
                 "Application tag name";
             }
             leaf application-tag-value {
               type string;
               description
                 "Application tag value";
             }
           }
         }
         list application-consolidated-protocols-ports {
           list application-consolidated-protocols {
             leaf application-app-name {
               type string;
               description
                 "Application app name";
             }
             leaf application-app-value {
               type string;
               description
                 "Application app value";
             }
           }
           list application-consolidated-tcp-ports {
             leaf application-ports {
               type int32;
               description
                 "TCP/UDP ports";
             }
           }
           list application-consolidated-udp-ports {
             leaf application-ports {
               type int32;
               description
                 "TCP/UDP ports";
             }
           }
         }
         list application-over-list-usp {
           leaf application-app-name {
             type string;
             description
               "Application app name";
           }
           leaf application-app-value {
             type string;
             description
               "Application app value";
           }
           leaf application-signature-name {
             type string;
             description
               "Signature name for over applications";
           }
           leaf application-port-range {
             type string;
             description
               "Application port range";
           }
           leaf application-num-members {
             type int32;
             description
               "Number of members in an application rule";
           }
           list application-member-list-usp {
             leaf application-member-name {
               type string;
               description
                 "Application member name";
             }
             leaf application-member-depth {
               type int32;
               description
                 "Application member depth";
             }
             leaf application-member-context {
               type string;
               description
                 "Application member context";
             }
             leaf application-member-pattern {
               type string;
               description
                 "Application member pattern";
             }
             leaf application-member-direction {
               type string;
               description
                 "Application member direction";
             }
           }
         }
         list application-over-list {
           container application-over {
             leaf application-app-name {
               type string;
               description
                 "Application app name";
             }
             leaf application-app-value {
               type string;
               description
                 "Application app value";
             }
             leaf application-chain-order {
               type string;
               description
                 "Application rule chain order";
             }
             leaf application-order {
               type string;
               description
                 "Application matching order";
             }
             leaf application-order-priority {
               type string;
               description
                 "Application rule order priority";
             }
             leaf application-port-range {
               type string;
               description
                 "Application port range";
             }
             leaf application-num-members {
               type int32;
               description
                 "Number of members in an application rule";
             }
             list application-member-list {
               leaf application-member-name {
                 type string;
                 description
                   "Application member name";
               }
               leaf application-member-index {
                 type int32;
                 description
                   "Application member index";
               }
               leaf application-member-depth {
                 type int32;
                 description
                   "Application member depth";
               }
               leaf application-member-context {
                 type string;
                 description
                   "Application member context";
               }
               leaf application-member-pattern {
                 type string;
                 description
                   "Application member pattern";
               }
               leaf application-member-direction {
                 type string;
                 description
                   "Application member direction";
               }
             }
           }
         }
         list application-alias-list {
           leaf application-alias-name {
             type string;
             description
               "Application alias name";
           }
         }
       }
       list application-icmp-mapping-detail {
         leaf icmp-order {
           type string;
           description
             "ICMP matching order";
         }
         leaf icmp-order-priority {
           type string;
           description
             "ICMP rule order priority";
         }
         leaf icmp-mapping-type {
           type int32;
           description
             "Application ICMP mapping type";
         }
         leaf icmp-mapping-code {
           type int32;
           description
             "Application ICMP mapping code";
         }
       }
       list application-ip-protocol-mapping-detail {
         leaf ip-protocol-order {
           type string;
           description
             "IP protocol matching order";
         }
         leaf ip-protocol-order-priority {
           type string;
           description
             "Ip protocol rule order priority";
         }
         leaf ip-protocol-number {
           type int32;
           description
             "Application IP protocol mapping protocol number";
         }
       }
       list application-address-mapping-detail {
         leaf address-mapping-name {
           type string;
           description
             "Application address mapping name";
         }
         leaf address-order {
           type string;
           description
             "IP address matching order";
         }
         leaf address-order-priority {
           type string;
           description
             "IP address rule order priority";
         }
         leaf address-mapping-src-ip {
           type string;
           description
             "Application address mapping source IP";
         }
         leaf address-mapping-src-wildcard-addr {
           type string;
           description
             "Application address mapping source wildcard address";
         }
         leaf address-mapping-src-wildcard-mask {
           type string;
           description
             "Application address mapping source wildcard mask";
         }
         leaf address-mapping-src-port-range {
           type string;
           description
             "Application address mapping source port range";
         }
         leaf address-mapping-dst-ip {
           type string;
           description
             "Application address mapping destination IP";
         }
         leaf address-mapping-dst-wildcard-addr {
           type string;
           description
             "Application address mapping destination wildcard address";
         }
         leaf address-mapping-dst-wildcard-mask {
           type string;
           description
             "Application address mapping destination wildcard mask";
         }
         leaf address-mapping-dst-port-range {
           type string;
           description
             "Application address mapping destination port range";
         }
         leaf address-mapping-order {
           type int32;
           description
             "Application address mapping order";
         }
       }
       container regular-application-signature-detail {
         leaf application-default-ports {
           type string;
           description
             "Application default ports";
         }
         leaf signature-port-range {
           type string;
           description
             "Application port range";
         }
         leaf signature-cts-dfa-pattern {
           type string;
           description
             "Client to server DFA pattern";
         }
         leaf signature-cts-pcre-pattern {
           type string;
           description
             "Client to server regex pattern";
         }
         leaf signature-stc-dfa-pattern {
           type string;
           description
             "Server to client DFA pattern";
         }
         leaf signature-stc-pcre-pattern {
           type string;
           description
             "Server to client regex pattern";
         }
         leaf application-min-data {
           type string;
           description
             "Minimum bytes need to inspect for this application";
         }
         leaf application-min-data-stc {
           type string;
           description
             "Minimum bytes from server to client need to inspect for this 
             application";
         }
         leaf application-order {
           type string;
           description
             "Application matching order";
         }
       }
       list nested-application-signature-detail {
         leaf nested-signature-name {
           type string;
           description
             "Nested application signature name";
         }
         leaf nested-l7protocol {
           type string;
           description
             "Nested application layer 7 protocol name";
         }
         leaf nested-signature-chain-order {
           type string;
           description
             "Nested signature chain order";
         }
         leaf nested-signature-max-trans {
           type string;
           description
             "Maximum transactions for a nested signature";
         }
         leaf nested-signature-order {
           type string;
           description
             "Nested signature matching order";
         }
         leaf nested-signature-num-members {
           type int32;
           description
             "Number of members in a nested signature";
         }
         list nested-signature-member-list {
           leaf nested-signature-member-index {
             type int32;
             description
               "Nested signature member index";
           }
           leaf nested-signature-member-context {
             type string;
             description
               "Nested signature member context";
           }
           leaf nested-signature-member-pattern {
             type string;
             description
               "Nested signature member pattern";
           }
           leaf nested-signature-member-direction {
             type string;
             description
               "Nested signature member direction";
           }
         }
       }
       list application-ng-address-mapping-detail {
         leaf address-mapping-name {
           type string;
           description
             "Application address mapping name";
         }
         leaf address-mapping-ip {
           type string;
           description
             "Application address mapping IP address";
         }
         leaf address-mapping-port-range {
           type string;
           description
             "Application address mapping port range";
         }
       }
     }
     container micro-applications-summary {
       description
         "Micro application signature summary";
       leaf total-micro-applications {
         type int32;
         description
           "Total number of micro applications";
       }
       list micro-applications-list {
         leaf-list application-name {
           type string;
           description
             "Name of an application or nested application";
         }
       }
     }
     container non-configurable-application-summary {
       description
         "Non-configurable application signature summary";
       leaf total-non-configurable-application {
         type int32;
         description
           "Total number of non-configurable applications";
       }
       list non-configurable-application-list {
         leaf-list application-name {
           type string;
           description
             "Name of an application or nested application";
         }
       }
     }
     container obsolete-application-summary {
       description
         "Obsolete application signature summary";
       leaf total-obsolete-application {
         type int32;
         description
           "Total number of obsolete applications";
       }
       container obsolete-application-list {
         leaf-list application-name {
           type string;
           description
             "Name of an application or nested application";
         }
       }
     }
   }
   grouping appid-application-group-block {
     container application-group-summary {
       description
         "Application group summary";
       leaf total-groups {
         type int32;
         description
           "Total number of groups";
       }
       list application-group-summary-list {
         leaf-list group-name {
           type string;
           description
             "Application group name";
         }
         leaf group-disabled {
           type string;
           description
             "Whether a group is disabled";
         }
         leaf group-id {
           type int32;
           description
             "Application group ID";
         }
       }
     }
     container application-group-detail {
       leaf-list group-name {
         type string;
         description
           "Application group name";
       }
       leaf group-description {
         type string;
         description
           "Application group description";
       }
       leaf group-id {
         type int32;
         description
           "Application group ID";
       }
       leaf group-disabled {
         type string;
         description
           "Whether a group is disabled";
       }
       leaf number-applications {
         type int32;
         description
           "Total number of applications in a group";
       }
       leaf number-sub-groups {
         type int32;
         description
           "Total number of sub groups in a group";
       }
       leaf number-parent-groups {
         type int32;
         description
           "Total number of parent groups in a group";
       }
       leaf application-expired-date {
         type string;
         description
           "When it may be expired";
       }
       list tag-group-list-detail {
         leaf tag-group-name {
           type string;
           description
             "Tag group name";
         }
         list application-tag-list-detail {
           leaf application-tag-name {
             type string;
             description
               "Application tag name";
           }
         }
       }
       list application-list-detail {
         leaf-list application-name {
           type string;
           description
             "Name of an application or nested application";
         }
       }
       list tag-group-application-list-detail {
         leaf-list application-name {
           type string;
           description
             "Name of an application or nested application";
         }
       }
       list sub-groups-list-detail {
         leaf-list group-name {
           type string;
           description
             "Application group name";
         }
       }
       list parent-groups-list-detail {
         leaf-list group-name {
           type string;
           description
             "Application group name";
         }
       }
     }
     container obsolete-group-summary {
       description
         "Obsolete application signature summary";
       leaf total-obsolete-groups {
         type int32;
         description
           "Total number of obsolete application-groups";
       }
       container obsolete-group-list {
         leaf-list group-name {
           type string;
           description
             "Application group name";
         }
       }
     }
   }
   grouping appid-application-system-cache-information-block {
     leaf message {
       type string;
       description
         "CLI ouput message";
     }
     container appid-cache-configuration-usp {
       leaf appid-asc-usp-enable {
         type string;
         description
           "Show application cache (on|off)";
       }
       leaf appid-asc-security-services-enable {
         type string;
         description
           "Show security services application cache (on|off)";
       }
       leaf appid-asc-miscellaneous-services-enable {
         type string;
         description
           "Show miscellaneous services application cache (on|off)";
       }
       leaf appid-asc-cache-timeout {
         type uint32;
         description
           "Show cache entry timeout (seconds)";
       }
     }
     container appid-cache-configuration {
       leaf appid-asc-enable {
         type string;
         description
           "Show application cache (on|off)";
       }
       leaf appid-cache-timeout {
         type uint32;
         description
           "Show cache entry timeout (seconds)";
       }
       leaf appid-nested-asc-enable {
         type string;
         description
           "Show nested application cache (on|off)";
       }
       leaf appid-cache-unknown {
         type string;
         description
           "Show cache unknown result (on|off)";
       }
     }
     list appid-application-system-cache {
       leaf pic {
         type string;
         description
           "FPC index/PIC index";
       }
       leaf message {
         type string;
         description
           "CLI ouput message";
       }
       container asc-entry {
         leaf application-groups {
           type string;
           description
             "Application groups";
         }
         leaf virtual-system-identifier {
           type string;
           description
             "Virtual system identifier";
         }
         leaf ip-address {
           type jt:ipaddr;
           description
             "IP address in application system cache";
         }
         leaf port {
           type int32;
           description
             "Port number";
         }
         leaf protocol {
           type string;
         }
         leaf appid-application {
           type string;
           description
             "Application type";
         }
         leaf classification-path {
           type string;
           description
             "Application classification path";
         }
         leaf ipv6-address {
           type jt:ipv6addr;
           description
             "IPV6 address in application system cache";
         }
         leaf index {
           type int32;
           description
             "Index";
         }
       }
     }
     container appid-application-system-cache-pic {
       leaf pic {
         type string;
         description
           "FPC index/PIC index";
       }
       list appid-application-system-cache-usp {
         leaf application-groups {
           type string;
           description
             "Application groups";
         }
         leaf virtual-system-identifier {
           type string;
           description
             "Virtual system identifier";
         }
         leaf ipv6-address {
           type jt:ipv6addr;
           description
             "IPV6 address in application system cache";
         }
         leaf port {
           type int32;
           description
             "Port number";
         }
         leaf protocol {
           type string;
         }
         leaf appid-application {
           type string;
           description
             "Application type";
         }
         leaf is_encrypted {
           type string;
           description
             "Is Encrypted";
         }
         leaf classification-path {
           type string;
           description
             "Application classification path";
         }
         leaf ip-address {
           type jt:ipaddr;
           description
             "IP address in application system cache";
         }
         leaf index {
           type int32;
           description
             "Index";
         }
       }
     }
   }
   grouping appid-counter-information-block {
     leaf message {
       type string;
       description
         "CLI ouput message";
     }
     container logical-system-counters {
       container logical-system-counter {
         leaf logical-system {
           type uint32;
           description
             "Logical system name";
         }
         leaf tenant {
           type uint32;
           description
             "Tenant name";
         }
       }
       list appid-counter-usp {
         leaf counter-name {
           type string;
           description
             "Counter name";
         }
         leaf counter-value {
           type uint32;
           description
             "Counter value";
         }
         leaf pic {
           type string;
           description
             "FPC index/PIC index";
         }
       }
     }
     list appid-counter {
       leaf pic {
         type string;
         description
           "FPC index/PIC index";
       }
       leaf message {
         type string;
         description
           "CLI ouput message";
       }
       container counter {
         leaf counter-name {
           type string;
           description
             "Counter name";
         }
         leaf counter-value {
           type uint32;
           description
             "Counter value";
         }
       }
     }
   }
   grouping appid-commit-status-block {
     leaf appid-commit-status-detail {
       type string;
       description
         "Custom signatures commit status";
     }
   }
   grouping appid-application-statistics-information-block {
     container logical-system-app-stats {
       container logical-system-app {
         leaf logical-system {
           type uint32;
           description
             "Logical system name";
         }
         leaf tenant {
           type uint32;
           description
             "Tenant name";
         }
       }
       container last-reset-stats {
         leaf last-reset {
           type string;
           description
             "Last reset timestamp";
         }
         leaf elapsed-time {
           type string;
           description
             "Elapsed time";
         }
       }
       list appid-application-statistics-usp {
         leaf-list application-name {
           type string;
           description
             "Name of an application or nested application";
         }
         leaf sessions {
           type uint32;
           description
             "Sessions per application";
         }
         leaf bytes {
           type uint32;
           description
             "Byte count";
         }
         leaf is_encrypted {
           type string;
           description
             "Is Encrypted";
         }
         leaf sessions-final-match {
           type uint32;
           description
             "Final matched sessions per application";
         }
         leaf sessions-pre-match {
           type uint32;
           description
             "Pre matched sessions per application";
         }
         leaf sessions-limits-terminated {
           type uint32;
           description
             "Limits terminated sessions per application";
         }
       }
       list appid-application-statistics-detail-usp {
         leaf-list application-name {
           type string;
           description
             "Name of an application or nested application";
         }
         leaf is_encrypted {
           type string;
           description
             "Is Encrypted";
         }
         leaf sessions-final-match {
           type uint32;
           description
             "Final matched sessions per application";
         }
         leaf sessions-pre-match {
           type uint32;
           description
             "Pre matched sessions per application";
         }
         leaf sessions-limits-terminated {
           type uint32;
           description
             "Limits terminated sessions per application";
         }
       }
       list appid-application-statistics {
         leaf-list application-name {
           type string;
           description
             "Name of an application or nested application";
         }
         leaf sessions {
           type uint32;
           description
             "Sessions per application";
         }
         leaf bytes {
           type uint32;
           description
             "Byte count";
         }
       }
     }
   }
   grouping appid-application-group-statistics-information-block {
     container logical-system-group-stats {
       container logical-system-group {
         leaf logical-system {
           type uint32;
           description
             "Logical system name";
         }
         leaf tenant {
           type uint32;
           description
             "Tenant name";
         }
       }
       container last-reset-group-stats {
         leaf last-reset {
           type string;
           description
             "Last reset timestamp";
         }
         leaf elapsed-time {
           type string;
           description
             "Elapsed time";
         }
       }
       list appid-application-group-statistics {
         leaf-list application-name {
           type string;
           description
             "Name of an application or nested application";
         }
         leaf sessions {
           type uint32;
           description
             "Sessions per application";
         }
         leaf bytes {
           type uint32;
           description
             "Byte count";
         }
       }
     }
   }
   grouping appid-status-information-block {
     container appid-pic-status {
       description
         "Application identification status for PIC";
       leaf pic {
         type string;
         description
           "FPC index/PIC index";
       }
       leaf status-name {
         type string;
         description
           "Status name";
       }
       leaf status-value {
         type string;
         description
           "Status value";
       }
       list appid-module-status {
         container status {
           leaf status-name {
             type string;
             description
               "Status name";
           }
           leaf status-value {
             type string;
             description
               "Status value";
           }
         }
       }
       list appid-asc-status {
         container status {
           leaf status-name {
             type string;
             description
               "Status name";
           }
           leaf status-value {
             type string;
             description
               "Status value";
           }
         }
       }
       list appid-protobundle-status {
         container status {
           leaf status-name {
             type string;
             description
               "Status name";
           }
           leaf status-value {
             type string;
             description
               "Status value";
           }
         }
       }
       list appid-proxy-profile-status {
         container status {
           leaf status-name {
             type string;
             description
               "Status name";
           }
           leaf status-value {
             type string;
             description
               "Status value";
           }
         }
       }
       list appid-protobundle-slot1-status {
         container status {
           leaf status-name {
             type string;
             description
               "Status name";
           }
           leaf status-value {
             type string;
             description
               "Status value";
           }
         }
       }
       list appid-protobundle-slot2-status {
         container status {
           leaf status-name {
             type string;
             description
               "Status name";
           }
           leaf status-value {
             type string;
             description
               "Status value";
           }
         }
       }
       list appid-rollback-status {
         container status {
           leaf status-name {
             type string;
             description
               "Status name";
           }
           leaf status-value {
             type string;
             description
               "Status value";
           }
         }
       }
     }
   }
   grouping appid-package-version-block {
     leaf version-detail {
       type string;
       description
         "Application package version";
     }
     leaf release-date {
       type string;
       description
         "Application package release date";
     }
     leaf version-name {
       type string;
       description
         "Version name";
     }
     leaf version-value {
       type string;
       description
         "Version value";
     }
     container appid-failed-version {
       list failed-version {
         leaf version-name {
           type string;
           description
             "Version name";
         }
         leaf version-value {
           type string;
           description
             "Version value";
         }
       }
     }
   }
   grouping appid-pkt-capture-counter-information-block {
     list pkt-capture-counter-pic {
       leaf pic {
         type string;
         description
           "FPC index/PIC index";
       }
       list pkt-capture-counter {
         leaf pkt-capture-counter-name {
           type string;
           description
             "Counter name ";
         }
         leaf pkt-capture-counter-value {
           type uint32;
           description
             "Counter value ";
         }
       }
     }
   }
   grouping recent-appid-sigpack-information-block {
     leaf-list recent-appid-sigpack-versions {
       type string;
       description
         "Appid Sigpack last-known-good versions";
     }
   }
   grouping lrf-statistics-summary-block {
     list lrf-statistics {
       description
         "LRF statistics";
       leaf interface-name {
         type string;
         description
           "Name of the adaptive services interface";
       }
       leaf flow-packets {
         type int32;
         description
           "Flow packets";
       }
       leaf flow-bytes {
         type int32;
         description
           "Flow bytes";
       }
       leaf active-flows {
         type int32;
         description
           "Active flows";
       }
       leaf total-flows {
         type int32;
         description
           "Total flows";
       }
     }
   }
   grouping lrf-collector-statistics-summary-block {
     list lrf-collector-statistics {
       description
         "LRF collector statistics";
       leaf interface-name {
         type string;
         description
           "Name of the adaptive services interface";
       }
       leaf tmpl-reg {
         type int32;
         description
           "Templates registered";
       }
       leaf tmpl-reg-failures {
         type int32;
         description
           "Template registration failures";
       }
       leaf tmpl-active {
         type int32;
         description
           "Templates active";
       }
       leaf sessions-received {
         type int32;
         description
           "Sessions received";
       }
       leaf sessions-ignored {
         type int32;
         description
           "Sessions ignored";
       }
       leaf records-logged {
         type int32;
         description
           "Records logged";
       }
       leaf rec-export {
         type int32;
         description
           "Records exported";
       }
       leaf rec-export-failures {
         type int32;
         description
           "Record export failures";
       }
       leaf rec-export-volume {
         type int32;
         description
           "Records exported for volume";
       }
       leaf rec-export-time {
         type int32;
         description
           "Records exported for time";
       }
       leaf rec-export-session-close {
         type int32;
         description
           "Records exported for session close";
       }
     }
   }
   grouping lrf-rule-statistics-summary-block {
     list lrf-rule-statistics {
       description
         "LRF rule statistics";
       leaf interface-name {
         type string;
         description
           "Name of the adaptive services interface";
       }
       leaf rule-name {
         type string;
         description
           "Rule name";
       }
       leaf rule-tmpl-name {
         type string;
         description
           "Template name";
       }
       leaf rule-tmpl-reg {
         type int32;
         description
           "Templates registered";
       }
       leaf rule-tmpl-reg-failures {
         type int32;
         description
           "Template registration failures";
       }
       leaf rule-coll-name {
         type string;
         description
           "Collector name";
       }
       leaf rule-sessions-received {
         type int32;
         description
           "Sessions received";
       }
       leaf rule-sessions-ignored {
         type int32;
         description
           "Sessions ignored";
       }
       leaf rule-sessions-logged {
         type int32;
         description
           "Sessions logged";
       }
       leaf rule-rec-export {
         type int32;
         description
           "Records exported";
       }
       leaf rule-rec-export-failures {
         type int32;
         description
           "Record export failures";
       }
       leaf rule-rec-export-volume {
         type int32;
         description
           "Records exported for volume";
       }
       leaf rule-rec-export-time {
         type int32;
         description
           "Records exported for time";
       }
       leaf rule-rec-export-session-close {
         type int32;
         description
           "Records exported for session close";
       }
     }
   }
   grouping lrf-template-block {
     leaf-list export-field {
       type string;
     }
     leaf-list export-field-id {
       type int32;
     }
     leaf-list export-field-len {
       type int32;
     }
     leaf-list export-field-vendor {
       type string;
     }
   }
   grouping services-accounting-information-block {
     leaf interface-name {
       type string;
       description
         "Physical interface name";
     }
     leaf local-index {
       type int32;
       description
         "Local physical interface index";
     }
     leaf service-name {
       type string;
       description
         "Service name";
     }
     leaf pic-status {
       type string;
       description
         "Current interface state";
     }
     container usage-information {
       description
         "Service accounting CPU utilization";
       leaf interface-name {
         type string;
         description
           "Physical interface name";
       }
       leaf uptime {
         type int32;
         description
           "CPU uptime, in milliseconds";
       }
       leaf inttime {
         type int32;
         description
           "CPU interrupt time, in microseconds";
       }
       leaf five-second-load {
         type int32;
         description
           "5-second load";
       }
       leaf one-minute-load {
         type int32;
         description
           "1-minute load";
       }
     }
     container memory-information {
       description
         "Service accounting memory utilization";
       leaf allocation-count {
         type int32;
         description
           "Flow record allocations";
       }
       leaf free-count {
         type int32;
         description
           "Flow record frees";
       }
       leaf maximum-allocated {
         type int32;
         description
           "Maximum flow records allocated";
       }
       leaf allocations-per-second {
         type int32;
         description
           "Flow record allocations per second";
       }
       leaf frees-per-second {
         type int32;
         description
           "Flow record frees per second";
       }
       leaf memory-used {
         type int32;
         description
           "Total memory used";
       }
       leaf memory-free {
         type int32;
         description
           "Total memory free";
       }
       leaf interface-name {
         type string;
         description
           "Physical interface name";
       }
       leaf v9-memory-used {
         type int32;
         description
           "Memory used by v9";
       }
     }
     container flow-information {
       description
         "Service accounting flow information";
       leaf interface-name {
         type string;
         description
           "Physical interface name";
       }
       leaf local_ifd_index {
         type int32;
         description
           "Local interface index";
       }
       leaf flow-packets {
         type int32;
         description
           "Flow packets";
       }
       leaf flow-bytes {
         type int32;
         description
           "Flow bytes";
       }
       leaf flow-packets-ten-second-rate {
         type int32;
         description
           "Flow packets 10-second rate";
       }
       leaf flow-bytes-ten-second-rate {
         type int32;
         description
           "Flow bytes 10-second rate";
       }
       leaf active-flows {
         type int32;
         description
           "Active flows";
       }
       leaf flows {
         type int32;
         description
           "Flows";
       }
       leaf flows-exported {
         type int32;
         description
           "Flows exported";
       }
       leaf flow-packets-exported {
         type int32;
         description
           "Flows packets exported";
       }
       leaf flows-expired {
         type int32;
         description
           "Flows inactive timed out";
       }
       leaf flows-aged {
         type int32;
         description
           "Flows active timed out";
       }
     }
     container vmon-mdi-template {
       description
         "MDI Templates information";
       leaf mdi-template-name {
         type string;
         description
           "Template Name";
       }
       leaf mdi-template-index {
         type uint32;
         description
           "Template Index";
       }
       leaf mdi-interval-duration {
         type uint32;
         description
           "Interval Duration";
       }
       leaf mdi-inactive-timeout {
         type uint32;
         description
           "Inactive Timeout";
       }
       leaf mdi-media-packet-count-in-l3 {
         type uint32;
         description
           "Media Packets Count in Layer3";
       }
       leaf mdi-media-packet-size {
         type uint32;
         description
           "Media Packet Size";
       }
       leaf mdi-media-rate {
         type uint32;
         description
           "Media Rate";
       }
       leaf mdi-l3-packet-rate {
         type uint32;
         description
           "Layer3 Packet Rate";
       }
       leaf mdi-df-status {
         type string;
         description
           "DF Enabled/Disabled";
       }
       leaf mdi-mlr-status {
         type string;
         description
           "MLR Enabled/Disabled";
       }
       leaf mdi-mrv-status {
         type string;
         description
           "MRV Enabled/Disabled";
       }
       leaf mdi-df-info-threshold {
         type string;
         description
           "DF Info level threshold";
       }
       leaf mdi-df-warning-threshold {
         type string;
         description
           "DF Warning level threshold";
       }
       leaf mdi-df-critical-threshold {
         type string;
         description
           "DF Ciritical level threshold";
       }
       leaf mdi-mlr-info-threshold-packet-count {
         type string;
         description
           "MLR Info level threshold";
       }
       leaf mdi-mlr-warning-threshold-packet-count {
         type string;
         description
           "MLR Warning level threshold";
       }
       leaf mdi-mlr-critical-threshold-packet-count {
         type string;
         description
           "MLR Ciritical level threshold";
       }
       leaf mdi-mlr-info-threshold-percentage {
         type string;
         description
           "MLR Info level threshold in percentage";
       }
       leaf mdi-mlr-warning-threshold-percentage {
         type string;
         description
           "MLR Warning level threshold in percentage";
       }
       leaf mdi-mlr-critical-threshold-percentage {
         type string;
         description
           "MLR Ciritical level threshold in percentage";
       }
       leaf mdi-mrv-info-threshold {
         type string;
         description
           "MRV Info level threshold";
       }
       leaf mdi-mrv-warning-threshold {
         type string;
         description
           "MRV Warning level threshold";
       }
       leaf mdi-mrv-critical-threshold {
         type string;
         description
           "MRV Ciritical level threshold";
       }
     }
     container vmon-mdi-stats {
       description
         "MDI stats information";
       leaf fpc-slot {
         type int32;
         description
           "FPC Slot";
       }
       leaf tfeb-slot {
         type int32;
         description
           "TFEB Slot";
       }
       leaf afeb-slot {
         type int32;
         description
           "AFEB Slot";
       }
       leaf mdi-active-flows {
         type uint32;
         description
           "Active flows";
       }
       leaf mdi-total-inserted-flows {
         type uint32;
         description
           "Total Inserted flows";
       }
       leaf mdi-total-deleted-flows {
         type uint32;
         description
           "Total Deleted flows";
       }
       leaf mdi-flow-packets-count {
         type uint32;
         description
           "Total Packets Count";
       }
       leaf mdi-flow-bytes-count {
         type uint32;
         description
           "Total Bytes Count";
       }
       leaf mdi-df-alarm-count {
         type uint32;
         description
           "DF alarm count";
       }
       leaf mdi-df-info-level-alarm-count {
         type uint32;
         description
           "DF info level alarm count";
       }
       leaf mdi-df-warning-level-alarm-count {
         type uint32;
         description
           "DF warning level alarm count";
       }
       leaf mdi-df-critical-level-alarm-count {
         type uint32;
         description
           "DF critical level alarm count";
       }
       leaf mdi-mlr-alarm-count {
         type uint32;
         description
           "MLR alarm count";
       }
       leaf mdi-mlr-info-level-alarm-count {
         type uint32;
         description
           "MLR info level alarm count";
       }
       leaf mdi-mlr-warning-level-alarm-count {
         type uint32;
         description
           "MLR warning level alarm count";
       }
       leaf mdi-mlr-critical-level-alarm-count {
         type uint32;
         description
           "MLR critical level alarm count";
       }
       leaf mdi-mrv-alarm-count {
         type uint32;
         description
           "MRV alarm count";
       }
       leaf mdi-mrv-info-level-alarm-count {
         type uint32;
         description
           "MRV info level alarm count";
       }
       leaf mdi-mrv-warning-level-alarm-count {
         type uint32;
         description
           "MRV warning level alarm count";
       }
       leaf mdi-mrv-critical-level-alarm-count {
         type uint32;
         description
           "MRV critical level alarm count";
       }
     }
     container vmon-mdi-errors {
       description
         "MDI errors information";
       leaf fpc-slot {
         type int32;
         description
           "FPC Slot";
       }
       leaf tfeb-slot {
         type int32;
         description
           "TFEB Slot";
       }
       leaf afeb-slot {
         type int32;
         description
           "AFEB Slot";
       }
       leaf mdi-flow-insert-error-count {
         type uint32;
         description
           "Flow insert error";
       }
       leaf mdi-flow-policer-error-count {
         type uint32;
         description
           "Flow policer error";
       }
       leaf mdi-unsupported-media-pkt-count {
         type uint32;
         description
           "Unsupported media packets count";
       }
       leaf mdi-pid-limit-exceeded {
         type uint32;
         description
           "PID limit execeeded";
       }
       leaf mdi-fragmented-pkt-count {
         type uint32;
         description
           "Fragmented packet count";
       }
       leaf mdi-max-label-exceed-count {
         type uint32;
         description
           "Maximum label exceed count";
       }
       leaf mdi-options-pkt-count {
         type uint32;
         description
           "Options packet skip MDI count";
       }
     }
     container vmon-mdi-flow-brief-split-df-mlr {
       description
         "MDI flows in brief DF MLR split";
       leaf mdi-flow-sno {
         type uint32;
         description
           "Flow row number";
       }
       leaf mdi-source-address {
         type string;
         description
           "Source address of flow";
       }
       leaf mdi-source-port {
         type uint32;
         description
           "Source port of flow";
       }
       leaf mdi-destination-address {
         type string;
         description
           "Destination address of flow";
       }
       leaf mdi-destination-port {
         type uint32;
         description
           "Destination port of flow";
       }
       leaf mdi-flow-direction {
         type string;
         description
           "MDI Flow Direction";
       }
       leaf mdi-flow-type {
         type string;
         description
           "Flow Type";
       }
       leaf mdi-last-df {
         type string;
         description
           "Last DF";
       }
       leaf mdi-last-mlr {
         type string;
         description
           "Last MLR";
       }
       leaf mdi-avg-df {
         type string;
         description
           "Average DF";
       }
       leaf mdi-avg-mlr {
         type string;
         description
           "Average MLR";
       }
       leaf mdi-last-mrv {
         type string;
         description
           "Last MRV";
       }
       leaf mdi-avg-mrv {
         type string;
         description
           "Average MRV";
       }
       leaf mdi-interface-name {
         type string;
         description
           "Interface Name";
       }
       leaf mdi-template-name {
         type string;
         description
           "Template Name";
       }
       leaf mdi-flow-identifier {
         type uint32;
         description
           "Unique Identifier of flow";
       }
     }
     container vmon-mdi-flow-detail-split-df-mlr {
       description
         "MDI flows in details";
       leaf mdi-source-address {
         type string;
         description
           "Source address of flow";
       }
       leaf mdi-source-port {
         type uint32;
         description
           "Source port of flow";
       }
       leaf mdi-destination-address {
         type string;
         description
           "Destination address of flow";
       }
       leaf mdi-destination-port {
         type uint32;
         description
           "Destination port of flow";
       }
       leaf mdi-last-df {
         type string;
         description
           "Last DF";
       }
       leaf mdi-last-mlr {
         type string;
         description
           "Last MLR";
       }
       leaf mdi-avg-df {
         type string;
         description
           "Average DF";
       }
       leaf mdi-avg-mlr {
         type string;
         description
           "Average MLR";
       }
       leaf mdi-last-mrv {
         type string;
         description
           "Last MRV";
       }
       leaf mdi-avg-mrv {
         type string;
         description
           "Average MRV";
       }
       leaf mdi-interface-name {
         type string;
         description
           "Interface Name";
       }
       leaf mdi-template-name {
         type string;
         description
           "Template Name";
       }
       leaf mdi-flow-direction {
         type string;
         description
           "MDI Flow Direction";
       }
       leaf mdi-flow-type {
         type string;
         description
           "Flow Type";
       }
       leaf mdi-mpls-labels {
         type string;
         description
           "MPLS labels";
       }
       leaf mdi-record-count {
         type uint32;
         description
           "Count of MDI records";
       }
       leaf mdi-pid-count {
         type string;
         description
           "PID Count";
       }
       leaf mdi-flow-identifier {
         type uint32;
         description
           "Unique Identifier of flow";
       }
     }
     container vmon-mdi-flow-brief {
       description
         "MDI flows in brief";
       leaf mdi-flow-sno {
         type uint32;
         description
           "Flow row number";
       }
       leaf mdi-source-address {
         type string;
         description
           "Source address of flow";
       }
       leaf mdi-source-port {
         type uint32;
         description
           "Source port of flow";
       }
       leaf mdi-destination-address {
         type string;
         description
           "Destination address of flow";
       }
       leaf mdi-destination-port {
         type uint32;
         description
           "Destination port of flow";
       }
       leaf mdi-flow-direction {
         type string;
         description
           "MDI Flow Direction";
       }
       leaf mdi-flow-type {
         type string;
         description
           "Flow Type";
       }
       leaf mdi-last-df-mlr {
         type string;
         description
           "Last DF:MLR";
       }
       leaf mdi-avg-df-mlr {
         type string;
         description
           "Average DF:MLR";
       }
       leaf mdi-last-mrv {
         type string;
         description
           "Last MRV";
       }
       leaf mdi-avg-mrv {
         type string;
         description
           "Average MRV";
       }
       leaf mdi-interface-name {
         type string;
         description
           "Interface Name";
       }
       leaf mdi-template-name {
         type string;
         description
           "Template Name";
       }
       leaf mdi-flow-identifier {
         type uint32;
         description
           "Unique Identifier of flow";
       }
     }
     container vmon-mdi-flow-detail {
       description
         "MDI flows in details";
       leaf mdi-source-address {
         type string;
         description
           "Source address of flow";
       }
       leaf mdi-source-port {
         type uint32;
         description
           "Source port of flow";
       }
       leaf mdi-destination-address {
         type string;
         description
           "Destination address of flow";
       }
       leaf mdi-destination-port {
         type uint32;
         description
           "Destination port of flow";
       }
       leaf mdi-last-df-mlr {
         type string;
         description
           "Last DF:MLR";
       }
       leaf mdi-avg-df-mlr {
         type string;
         description
           "Average DF:MLR";
       }
       leaf mdi-last-mrv {
         type string;
         description
           "Last MRV";
       }
       leaf mdi-avg-mrv {
         type string;
         description
           "Average MRV";
       }
       leaf mdi-interface-name {
         type string;
         description
           "Interface Name";
       }
       leaf mdi-template-name {
         type string;
         description
           "Template Name";
       }
       leaf mdi-flow-direction {
         type string;
         description
           "MDI Flow Direction";
       }
       leaf mdi-flow-type {
         type string;
         description
           "Flow Type";
       }
       leaf mdi-mpls-labels {
         type string;
         description
           "MPLS labels";
       }
       leaf mdi-record-count {
         type uint32;
         description
           "Count of MDI records";
       }
       leaf mdi-pid-count {
         type string;
         description
           "PID Count";
       }
       leaf mdi-flow-identifier {
         type uint32;
         description
           "Unique Identifier of flow";
       }
     }
     container vmon-mdi-record {
       leaf mdi-record-index {
         type uint32;
         description
           "MDI Record Index";
       }
       leaf mdi-df {
         type string;
         description
           "DF Value";
       }
       leaf mdi-mlr {
         type uint32;
         description
           "MLR Value";
       }
       leaf mdi-mrv {
         type string;
         description
           "MRV Value";
       }
     }
     container vmon-mdi-record-udp {
       leaf mdi-record-index {
         type uint32;
         description
           "MDI Record Index";
       }
       leaf mdi-df {
         type string;
         description
           "DF Value";
       }
       leaf mdi-mlr {
         type uint32;
         description
           "MLR Value";
       }
       leaf mdi-mrv {
         type string;
         description
           "MRV Value";
       }
       leaf mdi-pid1-val {
         type string;
         description
           "PID Value";
       }
       leaf mdi-pid1-mlr {
         type string;
         description
           "MLR Value";
       }
       leaf mdi-pid2-val {
         type string;
         description
           "PID Value";
       }
       leaf mdi-pid2-mlr {
         type string;
         description
           "MLR Value";
       }
       leaf mdi-pid3-val {
         type string;
         description
           "PID Value";
       }
       leaf mdi-pid3-mlr {
         type string;
         description
           "MLR Value";
       }
       leaf mdi-pid4-val {
         type string;
         description
           "PID Value";
       }
       leaf mdi-pid4-mlr {
         type string;
         description
           "MLR Value";
       }
       leaf mdi-pid5-val {
         type string;
         description
           "PID Value";
       }
       leaf mdi-pid5-mlr {
         type string;
         description
           "MLR Value";
       }
       leaf mdi-pid6-val {
         type string;
         description
           "PID Value";
       }
       leaf mdi-pid6-mlr {
         type string;
         description
           "MLR Value";
       }
     }
     container vmon-mdi-alarm-stats {
       description
         "Video Monitoring Alarm Stats";
       leaf mdi-df-successful-alarms {
         type uint32;
         description
           "Successful DF Alarms Generated";
       }
       leaf mdi-df-threshold-exceed-alarms {
         type uint32;
         description
           " DF Alarms Suppressed due to threshold exceed";
       }
       leaf mdi-df-same-level-alarms {
         type uint32;
         description
           " DF Alarms Suppressed due to same level";
       }
       leaf mdi-df-template-missing-alarms {
         type uint32;
         description
           " DF Alarms Suppressed due to template missing";
       }
       leaf mdi-df-alarm-syslog-generated {
         type uint32;
         description
           " DF Alarm Syslog Generated ";
       }
       leaf mdi-df-total-alarms {
         type uint32;
         description
           "Total DF Alarms Generated";
       }
       leaf mdi-mlr-successful-alarms {
         type uint32;
         description
           "Successful MLR Alarms Generated";
       }
       leaf mdi-mlr-threshold-exceed-alarms {
         type uint32;
         description
           " MLR Alarms Suppressed due to threshold exceed";
       }
       leaf mdi-mlr-same-level-alarms {
         type uint32;
         description
           " MLR Alarms Suppressed due to same level";
       }
       leaf mdi-mlr-template-missing-alarms {
         type uint32;
         description
           " MLR Alarms Suppressed due to template missing";
       }
       leaf mdi-mlr-alarm-syslog-generated {
         type uint32;
         description
           " MLR Alarm Syslog Generated ";
       }
       leaf mdi-mlr-total-alarms {
         type uint32;
         description
           "Total MLR Alarms Generated";
       }
       leaf mdi-mrv-successful-alarms {
         type uint32;
         description
           "Successful MRV Alarms Generated";
       }
       leaf mdi-mrv-threshold-exceed-alarms {
         type uint32;
         description
           " MRV Alarms Suppressed due to threshold exceed";
       }
       leaf mdi-mrv-same-level-alarms {
         type uint32;
         description
           " MRV Alarms Suppressed due to same level";
       }
       leaf mdi-mrv-template-missing-alarms {
         type uint32;
         description
           " MRV Alarms Suppressed due to template missing";
       }
       leaf mdi-mrv-alarm-syslog-generated {
         type uint32;
         description
           " MRV Alarm Syslog Generated ";
       }
       leaf mdi-mrv-total-alarms {
         type uint32;
         description
           "Total MRV Alarms Generated";
       }
       leaf mdi-new-flow-successful-alarms {
         type uint32;
         description
           "Successful New Flow Alarms Generated";
       }
       leaf mdi-new-flow-threshold-exceed-alarms {
         type uint32;
         description
           "New Flow Alarms Suppressed due to threshold exceed";
       }
       leaf mdi-new-flow-same-level-alarms {
         type uint32;
         description
           "New Flow Alarms Suppressed due to same level";
       }
       leaf mdi-new-flow-template-missing-alarms {
         type uint32;
         description
           "New Flow Alarms Suppressed due to template missing";
       }
       leaf mdi-new-flow-alarm-syslog-generated {
         type uint32;
         description
           " NEW FLOW Alarm Syslog Generated ";
       }
       leaf mdi-new-flow-total-alarms {
         type uint32;
         description
           "Total New Flow Alarms Generated";
       }
       leaf mdi-flow-delete-successful-alarms {
         type uint32;
         description
           "Successful Flow Delete Alarms Generated";
       }
       leaf mdi-flow-delete-threshold-exceed-alarms {
         type uint32;
         description
           "Flow Delete Alarms Suppressed due to threshold exceed";
       }
       leaf mdi-flow-delete-same-level-alarms {
         type uint32;
         description
           "Flow Delete Alarms Suppressed due to same level";
       }
       leaf mdi-flow-delete-template-missing-alarms {
         type uint32;
         description
           "Flow Delete Alarms Suppressed due to template missing";
       }
       leaf mdi-flow-delete-alarm-syslog-generated {
         type uint32;
         description
           " Flow Delete Alarm Syslog Generated ";
       }
       leaf mdi-flow-delete-total-alarms {
         type uint32;
         description
           "Total Flow Delete Alarms Generated";
       }
       leaf fpc-slot {
         type int32;
         description
           "FPC Slot";
       }
       leaf tfeb-slot {
         type int32;
         description
           "TFEB Slot";
       }
       leaf afeb-slot {
         type int32;
         description
           "AFEB Slot";
       }
       leaf mdi-invalid-alarms {
         type uint32;
         description
           "Invalid Alarms Generated";
       }
     }
     container inline-jflow-template-version-information {
       description
         "Inline jflow version information";
       leaf template-version {
         type string;
         description
           "MX Inline Jflow template version information";
       }
       leaf sparks-jflow-template-version {
         type string;
         description
           "Sparks Jflow template version information";
       }
       leaf pic-jflow-template-version {
         type string;
         description
           "PIC based Jflow template version information";
       }
       leaf ptx-inline-jflow-template-version {
         type string;
         description
           "PTX Inline Jflow template version information";
       }
       leaf evo-inline-jflow-template-version {
         type string;
         description
           "EVO Inline Jflow template version information";
       }
       leaf mx-imon-template-version {
         type string;
         description
           "Internal Modified MX IMON Template Version";
       }
     }
     container inline-jflow-flow-information {
       description
         "Service accounting flow information";
       leaf fpc-slot {
         type int32;
         description
           "FPC Slot";
       }
       leaf tfeb-slot {
         type int32;
         description
           "TFEB Slot";
       }
       leaf pic-slot {
         type int32;
         description
           "PIC Slot";
       }
       leaf afeb-slot {
         type int32;
         description
           "AFEB Slot";
       }
       leaf inline-flow-packets {
         type int32;
         description
           "Flow packets";
       }
       leaf inline-flow-bytes {
         type int32;
         description
           "Flow bytes";
       }
       leaf inline-active-flows {
         type int32;
         description
           "Active flows";
       }
       leaf inline-flows {
         type int32;
         description
           "Flows";
       }
       leaf inline-flows-exported {
         type int32;
         description
           "Flows exported";
       }
       leaf inline-flow-packets-exported {
         type int32;
         description
           "Flows packets exported";
       }
       leaf inline-flows-expired {
         type int32;
         description
           "Flows inactive timed out";
       }
       leaf inline-flows-aged {
         type int32;
         description
           "Flows active timed out";
       }
       leaf inline-flow-insert-count {
         type int32;
         description
           "Flow Insert Count";
       }
       leaf inline-ipv4-flow-packets {
         type int32;
         description
           "IPv4 Flow packets";
       }
       leaf inline-ipv4-flow-bytes {
         type int32;
         description
           "IPv4 Flow bytes";
       }
       leaf inline-ipv4-active-flows {
         type int32;
         description
           "IPv4 Active flows";
       }
       leaf inline-ipv4-total-flows {
         type int32;
         description
           "IPv4 Flows";
       }
       leaf inline-ipv4-flows-exported {
         type int32;
         description
           "IPv4 Flows exported";
       }
       leaf inline-ipv4-flow-packets-exported {
         type int32;
         description
           "IPv4 Flows packets exported";
       }
       leaf inline-ipv4-flows-expired {
         type int32;
         description
           "IPv4 Flows inactive timed out";
       }
       leaf inline-ipv4-flows-aged {
         type int32;
         description
           "IPv4 Flows active timed out";
       }
       leaf inline-ipv4-flow-insert-count {
         type int32;
         description
           "IPv4 Flow Insert Count";
       }
       leaf inline-ipv6-flow-packets {
         type int32;
         description
           "IPv6 Flow packets";
       }
       leaf inline-ipv6-flow-bytes {
         type int32;
         description
           "IPv6 Flow bytes";
       }
       leaf inline-ipv6-active-flows {
         type int32;
         description
           "IPv6 Active flows";
       }
       leaf inline-ipv6-total-flows {
         type int32;
         description
           "IPv6 Flows";
       }
       leaf inline-ipv6-flows-exported {
         type int32;
         description
           "IPv6 Flows exported";
       }
       leaf inline-ipv6-flow-packets-exported {
         type int32;
         description
           "IPv6 Flows packets exported";
       }
       leaf inline-ipv6-flows-expired {
         type int32;
         description
           "IPv6 Flows inactive timed out";
       }
       leaf inline-ipv6-flows-aged {
         type int32;
         description
           "IPv6 Flows active timed out";
       }
       leaf inline-ipv6-flow-insert-count {
         type int32;
         description
           "IPv6 Flow Insert Count";
       }
       leaf inline-vpls-flow-packets {
         type int32;
         description
           "VPLS Flow packets";
       }
       leaf inline-vpls-flow-bytes {
         type int32;
         description
           "VPLS Flow bytes";
       }
       leaf inline-vpls-active-flows {
         type int32;
         description
           "VPLS Active flows";
       }
       leaf inline-vpls-total-flows {
         type int32;
         description
           "VPLS Flows";
       }
       leaf inline-vpls-flows-exported {
         type int32;
         description
           "VPLS Flows exported";
       }
       leaf inline-vpls-flow-packets-exported {
         type int32;
         description
           "VPLS Flows packets exported";
       }
       leaf inline-vpls-flows-expired {
         type int32;
         description
           "VPLS Flows inactive timed out";
       }
       leaf inline-vpls-flows-aged {
         type int32;
         description
           "VPLS Flows active timed out";
       }
       leaf inline-vpls-flow-insert-count {
         type int32;
         description
           "VPLS Flow Insert Count";
       }
       leaf inline-bridge-flow-packets {
         type int32;
         description
           "BRIDGE Flow packets";
       }
       leaf inline-bridge-flow-bytes {
         type int32;
         description
           "BRIDGE Flow bytes";
       }
       leaf inline-bridge-active-flows {
         type int32;
         description
           "BRIDGE Active flows";
       }
       leaf inline-bridge-total-flows {
         type int32;
         description
           "BRIDGE Flows";
       }
       leaf inline-bridge-flows-exported {
         type int32;
         description
           "BRIDGE Flows exported";
       }
       leaf inline-bridge-flow-packets-exported {
         type int32;
         description
           "BRIDGE Flows packets exported";
       }
       leaf inline-bridge-flows-expired {
         type int32;
         description
           "BRIDGE Flows inactive timed out";
       }
       leaf inline-bridge-flows-aged {
         type int32;
         description
           "BRIDGE Flows active timed out";
       }
       leaf inline-bridge-flow-insert-count {
         type int32;
         description
           "BRIDGE Flow Insert Count";
       }
       leaf inline-mpls-flow-packets {
         type int32;
         description
           "MPLS Flow packets";
       }
       leaf inline-mpls-flow-bytes {
         type int32;
         description
           "MPLS Flow bytes";
       }
       leaf inline-mpls-active-flows {
         type int32;
         description
           "MPLS Active flows";
       }
       leaf inline-mpls-total-flows {
         type int32;
         description
           "MPLS Flows";
       }
       leaf inline-mpls-flows-exported {
         type int32;
         description
           "MPLS Flows exported";
       }
       leaf inline-mpls-flow-packets-exported {
         type int32;
         description
           "MPLS Flows packets exported";
       }
       leaf inline-mpls-flows-expired {
         type int32;
         description
           "MPLS Flows inactive timed out";
       }
       leaf inline-mpls-flows-aged {
         type int32;
         description
           "MPLS Flows active timed out";
       }
       leaf inline-mpls-flow-insert-count {
         type int32;
         description
           "MPLS Flow Insert Count";
       }
       leaf inline-ipv4-flows {
         type int32;
         description
           "IPv4 Flows";
       }
       leaf inline-ipv6-flows {
         type int32;
         description
           "IPv6 Flows";
       }
       leaf inline-vpls-flows {
         type int32;
         description
           "VPLS Flows";
       }
       leaf inline-bridge-flows {
         type int32;
         description
           "BRIDGE Flows";
       }
       leaf inline-mpls-flows {
         type int32;
         description
           "MPLS Flows";
       }
     }
     container packet-distribution-information {
       description
         "Service accounting packet distribution information";
       leaf packet-size-range-start {
         type int32;
         description
           "Start of packet size range";
       }
       leaf packet-size-range-end {
         type int32;
         description
           "End of packet size range";
       }
       leaf range-number-packets {
         type int32;
         description
           "Number of packets in range";
       }
       leaf range-percentage-packets {
         type string;
         description
           "Percentage of packets in range";
       }
     }
     container error-information {
       description
         "Service accounting error information";
       leaf error-packets-dropped-no-memory {
         type int32;
         description
           "Number of packets dropped because memory is exhausted";
       }
       leaf error-packets-dropped-not-ip {
         type int32;
         description
           "Number of packets dropped because they are not IP";
       }
       leaf error-packets-dropped-not-ipv4 {
         type int32;
         description
           "Number of packets dropped because they are not IPv4";
       }
       leaf error-packets-too-small {
         type int32;
         description
           "Number of packets dropped because their header is too small";
       }
       leaf error-allocation-failures {
         type int32;
         description
           "Number of failed attempts to allocate memory";
       }
       leaf error-free-failures {
         type int32;
         description
           "Number of failed attempts to free memory";
       }
       leaf error-free-list-failures {
         type int32;
         description
           "Number of operations that failed because free list memory is 
           exhausted";
       }
       leaf error-memory-warning {
         type string;
         description
           "Reached low memory condition";
       }
       leaf error-memory-overload {
         type string;
         description
           "Whether memory is exhausted";
       }
       leaf error-packets-per-second-overload {
         type string;
         description
           "Whether the number of incoming packets exceeds the designed 
           per-second limit";
       }
       leaf error-bytes-per-second-overload {
         type string;
         description
           "Whether the number of incoming bytes exceeds the designed 
           per-second limit";
       }
     }
     container inline-jflow-error-information {
       description
         "Inline  Jflow accounting error information";
       leaf fpc-slot {
         type int32;
         description
           "FPC Slot";
       }
       leaf tfeb-slot {
         type int32;
         description
           "TFEB Slot";
       }
       leaf afeb-slot {
         type int32;
         description
           "AFEB Slot";
       }
       leaf pic-slot {
         type int32;
         description
           "PIC Slot";
       }
       leaf inline-flow-creation-failures {
         type int32;
         description
           "Number of flow creation failures";
       }
       leaf inline-route-record-lookup-failure {
         type int32;
         description
           "Number of Route record lookup failures";
       }
       leaf inline-as-lookup-failures {
         type int32;
         description
           "Number of AS lookup Failures";
       }
       leaf inline-export-packet-failures {
         type int32;
         description
           "Number of export packet failures";
       }
       leaf inline-memory-overload {
         type string;
         description
           "Memory overload status";
       }
       leaf inline-memory-alloc-fail-count {
         type int32;
         description
           "Count of memory alloc failures";
       }
       leaf inline-ipv4-flow-creation-failures {
         type int32;
         description
           "Number of IPv4 flow creation failures";
       }
       leaf inline-ipv4-route-record-lookup-failure {
         type int32;
         description
           "Number of IPv4 Route record lookup failures";
       }
       leaf inline-ipv4-as-lookup-failures {
         type int32;
         description
           "Number of IPv4 AS lookup Failures";
       }
       leaf inline-ipv4-export-packet-failures {
         type int32;
         description
           "IPv4 Number of export packet failures";
       }
       leaf inline-ipv6-flow-creation-failures {
         type int32;
         description
           "Number of IPv6 flow creation failures";
       }
       leaf inline-ipv6-route-record-lookup-failure {
         type int32;
         description
           "Number of IPv6 Route record lookup failures";
       }
       leaf inline-ipv6-as-lookup-failures {
         type int32;
         description
           "Number of IPv6 AS lookup Failures";
       }
       leaf inline-ipv6-export-packet-failures {
         type int32;
         description
           "IPv6 Number of export packet failures";
       }
       leaf inline-vpls-flow-creation-failures {
         type int32;
         description
           "Number of VPLS flow creation failures";
       }
       leaf inline-vpls-route-record-lookup-failure {
         type int32;
         description
           "Number of VPLS Route record lookup failures";
       }
       leaf inline-vpls-as-lookup-failures {
         type int32;
         description
           "Number of VPLS AS lookup Failures";
       }
       leaf inline-vpls-export-packet-failures {
         type int32;
         description
           "VPLS Number of export packet failures";
       }
       leaf inline-bridge-flow-creation-failures {
         type int32;
         description
           "Number of BRIDGE flow creation failures";
       }
       leaf inline-bridge-export-packet-failures {
         type int32;
         description
           "BRIDGE Number of export packet failures";
       }
       leaf inline-mpls-flow-creation-failures {
         type int32;
         description
           "Number of MPLS flow creation failures";
       }
       leaf inline-mpls-route-record-lookup-failure {
         type int32;
         description
           "Number of MPLS Route record lookup failures";
       }
       leaf inline-mpls-as-lookup-failures {
         type int32;
         description
           "Number of MPLS AS lookup Failures";
       }
       leaf inline-mpls-export-packet-failures {
         type int32;
         description
           "MPLS Number of export packet failures";
       }
       leaf ring-buffer-failures {
         type int32;
         description
           "Number of Ring Buffer Enque Failures";
       }
       leaf inline-ipv4-errors {
         type int32;
         description
           "IPv4 Errors";
       }
       leaf inline-ipv6-errors {
         type int32;
         description
           "IPv6 Errors";
       }
       leaf inline-vpls-errors {
         type int32;
         description
           "VPLS Errors";
       }
       leaf inline-bridge-errors {
         type int32;
         description
           "BRIDGE Errors";
       }
       leaf inline-mpls-errors {
         type int32;
         description
           "MPLS Errors";
       }
     }
     container v9-error-information {
       description
         "Jflow-v9 accounting error information";
       leaf interface-name {
         type string;
         description
           "Physical interface name";
       }
       leaf service-set-dropped {
         type int32;
         description
           "Number of service set drops";
       }
       leaf active-timeout-failures {
         type int32;
         description
           "Number of active timeout failures";
       }
       leaf export-packet-failures {
         type int32;
         description
           "Number of export packet failures";
       }
       leaf flow-creation-failures {
         type int32;
         description
           "Number of flow creation failures";
       }
       leaf memory-overload {
         type string;
         description
           "Memory overload status";
       }
     }
     container status-information {
       description
         "Service accounting status information";
       leaf status-service-id {
         type int32;
         description
           "Service ID";
       }
       leaf status-export-interval {
         type int32;
         description
           "Export interval, in seconds";
       }
       leaf status-export-format {
         type int32;
         description
           "Export format";
       }
       leaf status-proto {
         type string;
         description
           "Protocol";
       }
       leaf status-engine-type {
         type int32;
         description
           "Engine type";
       }
       leaf status-engine-id {
         type int32;
         description
           "Engine ID";
       }
       leaf status-route-record-count {
         type int32;
         description
           "Route record count";
       }
       leaf status-ifl-snmp-map-count {
         type int32;
         description
           "Local index to SNMP index count";
       }
       leaf status-as-count {
         type int32;
         description
           "Autonomous system number count";
       }
       leaf status-monitor-time-set {
         type string;
         description
           "Time set on PIC";
       }
       leaf status-monitor-config-set {
         type string;
         description
           "Configuration set on PIC";
       }
       leaf status-monitor-route-record-set {
         type string;
         description
           "Route records set on PIC";
       }
       leaf status-monitor-ifl-snmp-set {
         type string;
         description
           "Local index to SNMP index map set on PIC";
       }
       leaf interface-name {
         type string;
         description
           "Physical interface name";
       }
     }
     container inline-jflow-status-information {
       description
         "Service accounting status information";
       leaf fpc-slot {
         type int32;
         description
           "FPC Slot";
       }
       leaf tfeb-slot {
         type int32;
         description
           "TFEB Slot";
       }
       leaf afeb-slot {
         type int32;
         description
           "AFEB Slot";
       }
       leaf pic-slot {
         type int32;
         description
           "PIC Slot";
       }
       leaf hw-assisted {
         type int32;
         description
           "HW based Jflow";
       }
       leaf inline-status-ipv4-export-format {
         type string;
         description
           "IPV4 export format";
       }
       leaf inline-status-ipv6-export-format {
         type string;
         description
           "IPV6 export format";
       }
       leaf inline-status-vpls-export-format {
         type string;
         description
           "VPLS export format";
       }
       leaf inline-status-bridge-export-format {
         type string;
         description
           "BRIDGE export format";
       }
       leaf inline-status-mpls-export-format {
         type string;
         description
           "MPLS export format";
       }
       leaf inline-status-route-record-count {
         type int32;
         description
           "Route record count";
       }
       leaf inline-status-as-count {
         type int32;
         description
           "Autonomous system number count";
       }
       leaf inline-status-ipv4-route-record-count {
         type int32;
         description
           "IPv4 Route record count";
       }
       leaf inline-status-ipv6-route-record-count {
         type int32;
         description
           "IPv6 Route record count";
       }
       leaf inline-status-mpls-route-record-count {
         type int32;
         description
           "MPLS Route record count";
       }
       leaf ring-buffer-entries {
         type int32;
         description
           "Ring Buffer Entries Count";
       }
       leaf inline-status-route-record-set {
         type string;
         description
           "Route records set on FPC";
       }
       leaf inline-status-config-set {
         type string;
         description
           "Configuration set on FPC";
       }
       leaf inline-status-service-status {
         type string;
         description
           "Service Status on FPC";
       }
       leaf inline-status-use-extended-flow-memory {
         type string;
         description
           "Using extended flow memory";
       }
       leaf inline-status-flex-flow-sizing {
         type string;
         description
           "Flex flow sizing enabled";
       }
       leaf inline-status-ipv4-max-flow-count {
         type int32;
         description
           "IPv4 MAX FLOW count";
       }
       leaf inline-status-ipv6-max-flow-count {
         type int32;
         description
           "IPv6 MAX FLOW count";
       }
       leaf inline-status-vpls-max-flow-count {
         type int32;
         description
           "VPLS MAX FLOW count";
       }
       leaf inline-status-bridge-max-flow-count {
         type int32;
         description
           "BRIDGE MAX FLOW count";
       }
       leaf inline-status-mpls-max-flow-count {
         type int32;
         description
           "MPLS MAX FLOW count";
       }
       leaf inline-status-max-supported-flow-table-size {
         type int32;
         description
           "MAX supported Flow Table size";
       }
     }
     container flow-detail {
       description
         "Service accounting flow record detail";
       container detail-entry {
         description
           "Detail entry";
         leaf tos {
           type int32;
           description
             "Type of service";
         }
         leaf protocol {
           type int32;
           description
             "Protocol";
         }
         leaf tcp-flags {
           type int32;
           description
             "TCP flags";
         }
         leaf source-address {
           type jt:ipaddr;
           description
             "Source address of flow";
         }
         leaf source-prefix-length {
           type string;
           description
             "Source prefix length";
         }
         leaf source-port {
           type int32;
           description
             "Source port";
         }
         leaf destination-address {
           type jt:ipaddr;
           description
             "Destination address of flow";
         }
         leaf destination-prefix-length {
           type string;
           description
             "Destination prefix length";
         }
         leaf destination-port {
           type int32;
           description
             "Destination port";
         }
         leaf input-snmp-interface-index {
           type int32;
           description
             "Input SNMP interface index";
         }
         leaf output-snmp-interface-index {
           type int32;
           description
             "Output SNMP interface index";
         }
         leaf input-interface-name {
           type string;
           description
             "Input interface name";
         }
         leaf output-interface-name {
           type string;
           description
             "Output interface name";
         }
         leaf source-as {
           type int32;
           description
             "Source autonomous system number";
         }
         leaf destination-as {
           type int32;
           description
             "Destination autonomous system number";
         }
         leaf start-time {
           type string;
           description
             "System uptime at start of flow";
         }
         leaf end-time {
           type string;
           description
             "System uptime at end of flow";
         }
         leaf packet-count {
           type int32;
           description
             "Number of packets in the flow";
         }
         leaf byte-count {
           type int32;
           description
             "Number of bytes in the flow";
         }
         leaf icmp-type {
           type int32;
           description
             "ICMP type";
         }
         container last-active-timeout {
           description
             "Last active timeout data";
           leaf time-delta {
             type string;
             description
               "Time since last active timeout";
           }
           leaf last-packet-count {
             type int32;
             description
               "Packets exported in last active timeout";
           }
           leaf last-byte-count {
             type int32;
             description
               "Bytes exported in last active timeout";
           }
         }
       }
     }
     container flow-aggregate-template-detail {
       description
         "Service accounting template aggregate record detail";
       container flow-aggregate-template-detail-ipv4 {
         container detail-entry {
           description
             "Detail entry";
           leaf source-address {
             type jt:ipaddr;
             description
               "Source address of flow";
           }
           leaf destination-address {
             type jt:ipaddr;
             description
               "Destination address of flow";
           }
           leaf source-port {
             type int32;
             description
               "Source port";
           }
           leaf destination-port {
             type int32;
             description
               "Destination port";
           }
           leaf protocol {
             type int32;
             description
               "Protocol";
           }
           leaf tos {
             type int32;
             description
               "Type of service";
           }
           leaf tcp-flags {
             type int32;
             description
               "TCP flags";
           }
           leaf source-mask {
             type jt:ipaddr;
             description
               "Source mask";
           }
           leaf destination-mask {
             type jt:ipaddr;
             description
               "Destination mask";
           }
           leaf input-snmp-interface-index {
             type int32;
             description
               "Input SNMP interface index";
           }
           leaf output-snmp-interface-index {
             type int32;
             description
               "Output SNMP interface index";
           }
           leaf start-time {
             type string;
             description
               "System uptime at start of flow";
           }
           leaf end-time {
             type string;
             description
               "System uptime at end of flow";
           }
           leaf packet-count {
             type int32;
             description
               "Number of packets in the flow";
           }
           leaf byte-count {
             type int32;
             description
               "Number of bytes in the flow";
           }
           leaf icmp-type {
             type int32;
             description
               "ICMP type";
           }
         }
       }
       container flow-aggregate-template-detail-mpls {
         container detail-entry {
           description
             "Detail entry";
           leaf mpls-label-1 {
             type int32;
             description
               "MPLS label 1";
           }
           leaf mpls-label-2 {
             type int32;
             description
               "MPLS label 2";
           }
           leaf mpls-label-3 {
             type int32;
             description
               "MPLS label 3";
           }
           leaf input-snmp-interface-index {
             type int32;
             description
               "Input SNMP interface index";
           }
           leaf output-snmp-interface-index {
             type int32;
             description
               "Output SNMP interface index";
           }
           leaf start-time {
             type string;
             description
               "System uptime at start of flow";
           }
           leaf end-time {
             type string;
             description
               "System uptime at end of flow";
           }
           leaf packet-count {
             type int32;
             description
               "Number of packets in the flow";
           }
           leaf byte-count {
             type int32;
             description
               "Number of bytes in the flow";
           }
           leaf icmp-type {
             type int32;
             description
               "ICMP type";
           }
         }
       }
       container flow-aggregate-template-detail-mpls-ipv4 {
         container detail-entry {
           description
             "Detail entry";
           leaf mpls-label-1 {
             type int32;
             description
               "MPLS label 1";
           }
           leaf mpls-label-2 {
             type int32;
             description
               "MPLS label 2";
           }
           leaf mpls-label-3 {
             type int32;
             description
               "MPLS label 3";
           }
           leaf source-address {
             type jt:ipaddr;
             description
               "Source address of flow";
           }
           leaf destination-address {
             type jt:ipaddr;
             description
               "Destination address of flow";
           }
           leaf top-label-address {
             type jt:ipaddr;
             description
               "MPLS Top Label IPv4 Address";
           }
           leaf source-port {
             type int32;
             description
               "Source port";
           }
           leaf destination-port {
             type int32;
             description
               "Destination port";
           }
           leaf protocol {
             type int32;
             description
               "Protocol";
           }
           leaf tos {
             type int32;
             description
               "Type of service";
           }
           leaf tcp-flags {
             type int32;
             description
               "TCP flags";
           }
           leaf source-mask {
             type jt:ipaddr;
             description
               "Source mask";
           }
           leaf destination-mask {
             type jt:ipaddr;
             description
               "Destination mask";
           }
           leaf input-snmp-interface-index {
             type int32;
             description
               "Input SNMP interface index";
           }
           leaf output-snmp-interface-index {
             type int32;
             description
               "Output SNMP interface index";
           }
           leaf start-time {
             type string;
             description
               "System uptime at start of flow";
           }
           leaf end-time {
             type string;
             description
               "System uptime at end of flow";
           }
           leaf packet-count {
             type int32;
             description
               "Number of packets in the flow";
           }
           leaf byte-count {
             type int32;
             description
               "Number of bytes in the flow";
           }
           leaf icmp-type {
             type int32;
             description
               "ICMP type";
           }
         }
       }
       container flow-aggregate-template-detail-ipv6 {
         container detail-entry {
           description
             "Detail entry";
           leaf source-ipv6-address {
             type string;
             description
               "Source address of flow";
           }
           leaf destination-ipv6-address {
             type string;
             description
               "Destination address of flow";
           }
           leaf source-port {
             type int32;
             description
               "Source port";
           }
           leaf destination-port {
             type int32;
             description
               "Destination port";
           }
           leaf protocol {
             type int32;
             description
               "Protocol";
           }
           leaf tos {
             type int32;
             description
               "Type of service";
           }
           leaf tcp-flags {
             type int32;
             description
               "TCP flags";
           }
           leaf source-mask {
             type jt:ipaddr;
             description
               "Source mask";
           }
           leaf destination-mask {
             type jt:ipaddr;
             description
               "Destination mask";
           }
           leaf input-snmp-interface-index {
             type int32;
             description
               "Input SNMP interface index";
           }
           leaf output-snmp-interface-index {
             type int32;
             description
               "Output SNMP interface index";
           }
           leaf start-time {
             type string;
             description
               "System uptime at start of flow";
           }
           leaf end-time {
             type string;
             description
               "System uptime at end of flow";
           }
           leaf packet-count {
             type int32;
             description
               "Number of packets in the flow";
           }
           leaf byte-count {
             type int32;
             description
               "Number of bytes in the flow";
           }
           leaf icmp-type {
             type int32;
             description
               "ICMP type";
           }
         }
       }
       container flow-aggregate-template-detail-peer-as-billing {
         container detail-entry {
           description
             "Detail entry";
           leaf tos {
             type int32;
             description
               "Type of service";
           }
           leaf input-snmp-interface-index {
             type int32;
             description
               "Input SNMP interface index";
           }
           leaf start-time {
             type string;
             description
               "System uptime at start of flow";
           }
           leaf end-time {
             type string;
             description
               "System uptime at end of flow";
           }
           leaf packet-count {
             type int32;
             description
               "Number of packets in the flow";
           }
           leaf byte-count {
             type int32;
             description
               "Number of bytes in the flow";
           }
           leaf destination-peer-as {
             type int32;
             description
               "Peer Destination autonomous system number";
           }
           leaf bgp-nexthop {
             type jt:ipaddr;
             description
               "Bgp nexthop";
           }
           leaf icmp-type {
             type int32;
             description
               "ICMP type";
           }
         }
       }
     }
     container flow-aggregate-as-detail {
       description
         "Service accounting AS flow aggregate record detail";
       container detail-entry {
         description
           "Detail entry";
         leaf source-as {
           type int32;
           description
             "Source autonomous system number";
         }
         leaf destination-as {
           type int32;
           description
             "Destination autonomous system number";
         }
         leaf input-snmp-interface-index {
           type int32;
           description
             "Input SNMP interface index";
         }
         leaf output-snmp-interface-index {
           type int32;
           description
             "Output SNMP interface index";
         }
         leaf input-interface-name {
           type string;
           description
             "Input interface name";
         }
         leaf output-interface-name {
           type string;
           description
             "Output interface name";
         }
         leaf start-time {
           type string;
           description
             "System uptime at start of flow";
         }
         leaf end-time {
           type string;
           description
             "System uptime at end of flow";
         }
         leaf flow-count {
           type int32;
           description
             "Number of flows in the aggregate";
         }
         leaf packet-count {
           type int32;
           description
             "Number of packets in the flow";
         }
         leaf byte-count {
           type int32;
           description
             "Number of bytes in the flow";
         }
         leaf icmp-type {
           type int32;
           description
             "ICMP type";
         }
       }
     }
     container flow-aggregate-protocol-port-detail {
       description
         "Service accounting protocol-port aggregate record detail";
       container detail-entry {
         description
           "Detail entry";
         leaf protocol {
           type int32;
           description
             "Protocol";
         }
         leaf source-port {
           type int32;
           description
             "Source port";
         }
         leaf destination-port {
           type int32;
           description
             "Destination port";
         }
         leaf start-time {
           type string;
           description
             "System uptime at start of flow";
         }
         leaf end-time {
           type string;
           description
             "System uptime at end of flow";
         }
         leaf flow-count {
           type int32;
           description
             "Number of flows in the aggregate";
         }
         leaf packet-count {
           type int32;
           description
             "Number of packets in the flow";
         }
         leaf byte-count {
           type int32;
           description
             "Number of bytes in the flow";
         }
         leaf icmp-type {
           type int32;
           description
             "ICMP type";
         }
       }
     }
     container flow-aggregate-source-prefix-detail {
       description
         "Service accounting source prefix aggregate record detail";
       container detail-entry {
         description
           "Detail entry";
         leaf source-address {
           type jt:ipaddr;
           description
             "Source address of flow";
         }
         leaf source-prefix-length {
           type string;
           description
             "Source prefix length";
         }
         leaf input-snmp-interface-index {
           type int32;
           description
             "Input SNMP interface index";
         }
         leaf input-interface-name {
           type string;
           description
             "Input interface name";
         }
         leaf source-as {
           type int32;
           description
             "Source autonomous system number";
         }
         leaf start-time {
           type string;
           description
             "System uptime at start of flow";
         }
         leaf end-time {
           type string;
           description
             "System uptime at end of flow";
         }
         leaf flow-count {
           type int32;
           description
             "Number of flows in the aggregate";
         }
         leaf packet-count {
           type int32;
           description
             "Number of packets in the flow";
         }
         leaf byte-count {
           type int32;
           description
             "Number of bytes in the flow";
         }
         leaf icmp-type {
           type int32;
           description
             "ICMP type";
         }
       }
     }
     container flow-aggregate-destination-prefix-detail {
       description
         "Service accounting destination prefix aggregate record detail";
       container detail-entry {
         description
           "Detail entry";
         leaf destination-address {
           type jt:ipaddr;
           description
             "Destination address of flow";
         }
         leaf destination-prefix-length {
           type string;
           description
             "Destination prefix length";
         }
         leaf output-snmp-interface-index {
           type int32;
           description
             "Output SNMP interface index";
         }
         leaf output-interface-name {
           type string;
           description
             "Output interface name";
         }
         leaf destination-as {
           type int32;
           description
             "Destination autonomous system number";
         }
         leaf start-time {
           type string;
           description
             "System uptime at start of flow";
         }
         leaf end-time {
           type string;
           description
             "System uptime at end of flow";
         }
         leaf flow-count {
           type int32;
           description
             "Number of flows in the aggregate";
         }
         leaf packet-count {
           type int32;
           description
             "Number of packets in the flow";
         }
         leaf byte-count {
           type int32;
           description
             "Number of bytes in the flow";
         }
         leaf icmp-type {
           type int32;
           description
             "ICMP type";
         }
       }
     }
     container flow-aggregate-source-destination-prefix-detail {
       description
         "Service accounting source-destination prefix aggregate record 
         detail";
       container detail-entry {
         description
           "Detail entry";
         leaf source-address {
           type jt:ipaddr;
           description
             "Source address of flow";
         }
         leaf source-prefix-length {
           type string;
           description
             "Source prefix length";
         }
         leaf destination-address {
           type jt:ipaddr;
           description
             "Destination address of flow";
         }
         leaf destination-prefix-length {
           type string;
           description
             "Destination prefix length";
         }
         leaf input-snmp-interface-index {
           type int32;
           description
             "Input SNMP interface index";
         }
         leaf output-snmp-interface-index {
           type int32;
           description
             "Output SNMP interface index";
         }
         leaf input-interface-name {
           type string;
           description
             "Input interface name";
         }
         leaf output-interface-name {
           type string;
           description
             "Output interface name";
         }
         leaf source-as {
           type int32;
           description
             "Source autonomous system number";
         }
         leaf destination-as {
           type int32;
           description
             "Destination autonomous system number";
         }
         leaf start-time {
           type string;
           description
             "System uptime at start of flow";
         }
         leaf end-time {
           type string;
           description
             "System uptime at end of flow";
         }
         leaf flow-count {
           type int32;
           description
             "Number of flows in the aggregate";
         }
         leaf packet-count {
           type int32;
           description
             "Number of packets in the flow";
         }
         leaf byte-count {
           type int32;
           description
             "Number of bytes in the flow";
         }
         leaf icmp-type {
           type int32;
           description
             "ICMP type";
         }
       }
     }
     container imon-flowgroup-stats {
       description
         "Inline stats information";
       leaf fpc-slot {
         type int32;
         description
           "FPC Slot";
       }
       leaf imon-instance-flowgroup-name {
         type string;
         description
           "Instance name";
       }
       leaf imon-instance-flowgroup-index {
         type uint32;
         description
           "Instance index";
       }
       leaf imon-inst-flow-exceeded-count {
         type uint32;
         description
           "Flow exceeded count";
       }
       leaf imon-inst-flow-missed-count {
         type uint32;
         description
           "Flow missed count";
       }
       leaf imon-inst-flow-aged-out-count {
         type uint32;
         description
           "Flow aged out count";
       }
       leaf imon-inst-flow-learnt-count {
         type uint32;
         description
           "Flow learnt count";
       }
       leaf imon-inst-flow-meter-exceeded-count {
         type uint32;
         description
           "Flow meter exceeded count";
       }
     }
     container imon-sw-stats {
       description
         "Inline stats information";
       leaf fpc-slot {
         type int32;
         description
           "FPC Slot";
       }
       leaf imon-sw-instance-name {
         type string;
         description
           "Instance name";
       }
       leaf imon-sw-inst-flow-aged-out-count {
         type uint32;
         description
           "Flow aged out count";
       }
       leaf imon-sw-inst-flow-learnt-count {
         type uint32;
         description
           "Flow learnt count";
       }
     }
     container imon-stats {
       description
         "Inline stats information";
       leaf fpc-slot {
         type int32;
         description
           "FPC Slot";
       }
       leaf imon-fpc-packets {
         type uint32;
         description
           "Total packets at FPC level";
       }
       leaf imon-fpc-bytes {
         type uint32;
         description
           "Total bytes at FPC level";
       }
       leaf imon-collector-name {
         type string;
         description
           "Collector name";
       }
       leaf imon-collector-index {
         type uint32;
         description
           "Collector index";
       }
       leaf imon-collector-packets {
         type uint32;
         description
           "Total packets at collector level";
       }
       leaf imon-collector-bytes {
         type uint32;
         description
           "Total bytes at collector level";
       }
       leaf imon-instance-name {
         type string;
         description
           "Instance name";
       }
       leaf imon-instance-index {
         type uint32;
         description
           "Instance index";
       }
       leaf imon-export-format {
         type string;
         description
           "Sample Export Format";
       }
       leaf imon-instance-packets {
         type uint32;
         description
           "Total packets at instance level";
       }
       leaf imon-instance-bytes {
         type uint32;
         description
           "Total bytes at instance level";
       }
     }
     container imon-flow-ctr-map {
       description
         "Inline flow counters mapping information";
       leaf fpc-slot {
         type int32;
         description
           "FPC Slot";
       }
       leaf imon-flow-ctr-instance-name {
         type string;
         description
           "Flow counter instance name";
       }
       leaf imon-counter-name {
         type string;
         description
           "Counter name";
       }
       leaf imon-min-value {
         type uint32;
         description
           "Minimum Value";
       }
       leaf imon-max-value {
         type uint32;
         description
           "Maximum Value";
       }
       leaf imon-entp-elem-id {
         type uint32;
         description
           "Enterprise element id";
       }
       leaf imon-counter-type {
         type string;
         description
           "Counter type";
       }
     }
     container imon-flow-feature-map {
       description
         "Inline flow features mapping information";
       leaf fpc-slot {
         type int32;
         description
           "FPC Slot";
       }
       leaf imon-flow-feature-instance-name {
         type string;
         description
           "Flow Feature instance name";
       }
       leaf imon-feature-name {
         type string;
         description
           "Feature name";
       }
       leaf imon-feature-entp-elem-id {
         type uint32;
         description
           "Flow feature Enterprise element id";
       }
     }
   }
   grouping dnssnoop-cache-block {
     list dnssnoop-fpc-entry {
       leaf-list dnssnoop-fpc-name {
         type string;
         description
           "FPC";
       }
       list dnssnoop-cache-entry {
         leaf dnssnoop-cache-fqdn {
           type string;
           description
             "FQDN enrty name";
         }
         leaf dnssnoop-cache-ip {
           type jt:ipaddr;
           description
             "FQDN entry IP";
         }
         leaf dnssnoop-cache-ttl {
           type uint32;
           description
             "FQDN entry TTL";
         }
       }
     }
   }
   grouping dnssnoop-counters-block {
     leaf-list logical-system-name {
       type string;
       description
         "Name of the logical system";
     }
     list dnssnoop-counter-fpc-entry {
       leaf-list dnssnoop-fpc-name {
         type string;
         description
           "FPC";
       }
       leaf dnssnoop-counter-sess-ignored {
         type uint32;
       }
       leaf dnssnoop-counter-sess-interest {
         type uint32;
       }
       leaf dnssnoop-counter-sess-created {
         type uint32;
       }
       leaf dnssnoop-counter-sess-destroyed {
         type uint32;
       }
       leaf dnssnoop-counter-dns-contexts {
         type uint32;
       }
       leaf dnssnoop-counter-cache-fqdn-insert {
         type uint32;
       }
       leaf dnssnoop-counter-cache-fqdn-del {
         type uint32;
       }
       leaf dnssnoop-counter-cache-ip-insert {
         type uint32;
       }
       leaf dnssnoop-counter-cache-ip-del {
         type uint32;
       }
       leaf dnssnoop-counter-reports-gen {
         type uint32;
       }
       leaf dnssnoop-counter-reports-sent {
         type uint32;
       }
       leaf dnssnoop-counter-mem-alloc {
         type uint32;
       }
       leaf dnssnoop-counter-mem-alloc-fail {
         type uint32;
       }
       leaf dnssnoop-counter-mem-freed {
         type uint32;
       }
       leaf dnssnoop-counter-mem-freed-error {
         type uint32;
       }
       leaf dnssnoop-counter-appid-error {
         type uint32;
       }
       leaf dnssnoop-counter-ha-msg-sent {
         type uint32;
       }
       leaf dnssnoop-counter-ha-msg-recv {
         type uint32;
       }
       leaf dnssnoop-counter-category {
         type string;
       }
       leaf dnssnoop-counter-profile {
         type string;
       }
     }
   }
   grouping icap-redir-statistics-block {
     list icap-redir-statistics-ldom {
       description
         "Show ICAP redirect statistics of a logical-system or tenant";
       leaf icap-redir-statistics-msg-redirected {
         type uint64;
       }
       leaf icap-redir-statistics-msg-reqmod-redirected {
         type uint64;
       }
       leaf icap-redir-statistics-msg-respmod-redirected {
         type uint64;
       }
       leaf icap-redir-statistics-msg-received {
         type uint64;
       }
       leaf icap-redir-statistics-msg-reqmod-received {
         type uint64;
       }
       leaf icap-redir-statistics-msg-respmod-received {
         type uint64;
       }
       leaf icap-redir-statistics-fb-tmo-permit {
         type uint64;
       }
       leaf icap-redir-statistics-fb-tmo-log-permit {
         type uint64;
       }
       leaf icap-redir-statistics-fb-tmo-reject {
         type uint64;
       }
       leaf icap-redir-statistics-fb-conn-permit {
         type uint64;
       }
       leaf icap-redir-statistics-fb-conn-log-permit {
         type uint64;
       }
       leaf icap-redir-statistics-fb-conn-reject {
         type uint64;
       }
       leaf icap-redir-statistics-fb-deft-permit {
         type uint64;
       }
       leaf icap-redir-statistics-fb-deft-log-permit {
         type uint64;
       }
       leaf icap-redir-statistics-fb-deft-reject {
         type uint64;
       }
       leaf icap-redir-statistics-clear {
         type string;
         description
           "Clear ICAP redirect statistics";
       }
       leaf icap-redir-logical-system {
         type string;
         description
           "Logical system name";
       }
       leaf icap-redir-tenant {
         type string;
         description
           "Tenant name";
       }
     }
   }
   grouping icap-redir-status-block {
     list icap-redir-status-ldom {
       description
         "Show ICAP redirect profile status of a logical-system or tenant";
       leaf icap-redir-profile-status {
         type string;
       }
       leaf icap-redir-logical-system {
         type string;
         description
           "Logical system name";
       }
       leaf icap-redir-tenant {
         type string;
         description
           "Tenant name";
       }
     }
   }
   grouping policy-hit-count-service-router-block {
     leaf-list policy-hit-count-num {
       type uint32;
       description
         "Number of policy";
     }
     list policy-hit-count-service-router-entry {
       description
         "Information about policy hit-count";
       leaf policy-hit-count-service-router-index {
         type uint32;
         description
           "Index";
       }
       leaf policy-hit-count-service-router-service-set {
         type string;
         description
           "Service set";
       }
       leaf policy-hit-count-service-router-interface {
         type string;
         description
           "Service set interface";
       }
       leaf policy-hit-count-service-router-policy-name {
         type string;
         description
           "Policy name";
       }
       leaf policy-hit-count-service-router-sfw-rule-name {
         type string;
         description
           "Sfw-rule name";
       }
       leaf policy-hit-count-service-router-direction {
         type string;
         description
           "Direction";
       }
       leaf policy-hit-count-service-router-count {
         type uint32;
         description
           "Policy hit-count ";
       }
     }
   }
   grouping secintel-recommended-action-block {
     leaf secintel-recommended-action-name {
       type string;
     }
     leaf secintel-recommended-action-property {
       type string;
     }
     leaf secintel-recommended-action-value {
       type string;
     }
     leaf secintel-recommended-action-action {
       type string;
     }
   }
   grouping secintel-redirect-files-block {
     leaf secintel-redirect-files-name {
       type string;
     }
     leaf secintel-redirect-files-size {
       type uint64;
     }
     leaf secintel-redirect-files-time {
       type string;
     }
     leaf secintel-redirect-file-content {
       type string;
     }
   }
   grouping secintel-statistics-block {
     leaf secintel-statistics-category {
       type string;
     }
     leaf secintel-statistics-profile {
       type string;
     }
     leaf secintel-statistics-total {
       type uint32;
     }
     leaf secintel-statistics-permit {
       type uint32;
     }
     leaf secintel-statistics-block-drop {
       type uint32;
     }
     leaf secintel-statistics-block-close {
       type uint32;
     }
     leaf secintel-statistics-close-redirect {
       type uint32;
     }
     leaf secintel-statistics-rs-permit {
       type uint32;
     }
     leaf-list logical-system-name {
       type string;
       description
         "Name of the logical system";
     }
     leaf-list dns-logical-system {
       type string;
       description
         "Logical system name";
     }
     leaf-list sm-dns-logical-system {
       type string;
       description
         "Logical system name";
     }
     leaf-list sm-dns-wl-logical-system {
       type string;
       description
         "Logical system name";
     }
   }
   grouping dns-statistics-block {
     leaf dns-statistics-white-category {
       type string;
     }
     leaf dns-statistics-udp-requests {
       type uint64;
     }
     leaf dns-statistics-udp-permit {
       type uint64;
     }
     leaf dns-statistics-tcp-requests {
       type uint64;
     }
     leaf dns-statistics-tcp-permit {
       type uint64;
     }
     leaf dns-statistics-space {
       type string;
     }
     leaf dns-statistics-tls-tcp-requests {
       type uint64;
     }
     leaf dns-statistics-tls-tcp-permit {
       type uint64;
     }
     leaf dns-tls-statistics-space {
       type string;
     }
     leaf dns-statistics-https-tcp-requests {
       type uint64;
     }
     leaf dns-statistics-https-tcp-permit {
       type uint64;
     }
     leaf dns-https-statistics-space {
       type string;
     }
     leaf dns-statistics-category {
       type string;
     }
     leaf dns-statistics-profile {
       type string;
     }
     leaf dns-statistics-proto {
       type string;
     }
     leaf dns-statistics-tcp-proto {
       type string;
     }
     leaf dns-statistics-tls-tcp-proto {
       type string;
     }
     leaf dns-statistics-https-tcp-proto {
       type string;
     }
     leaf dns-statistics-querytype {
       type string;
     }
     leaf dns-statistics-requests {
       type uint64;
     }
     leaf dns-statistics-sinkhole {
       type uint64;
     }
     leaf dns-statistics-drop {
       type uint64;
     }
     leaf dns-statistics-permit {
       type uint64;
     }
     leaf dns-statistics-log {
       type uint64;
     }
     leaf dns-statistics-total {
       type string;
     }
     leaf dns-statistics-total-requests {
       type uint64;
     }
     leaf dns-statistics-total-sinkhole {
       type uint64;
     }
     leaf dns-statistics-total-drop {
       type uint64;
     }
     leaf dns-statistics-total-permit {
       type uint64;
     }
     leaf dns-statistics-total-log {
       type uint64;
     }
     leaf-list logical-system-name {
       type string;
       description
         "Name of the logical system";
     }
     leaf-list dns-logical-system {
       type string;
       description
         "Logical system name";
     }
     leaf-list sm-dns-logical-system {
       type string;
       description
         "Logical system name";
     }
     leaf-list sm-dns-wl-logical-system {
       type string;
       description
         "Logical system name";
     }
     leaf dns-statistics-udp-proto {
       type string;
     }
   }
   grouping dns-filtering-cache-block {
     leaf dns-cache-refresh-rate {
       type uint32;
     }
     leaf dns-cache-lsys-name {
       type string;
     }
     leaf dns-cache-entry-name {
       type string;
     }
     leaf dns-cache-entry-ttl {
       type uint32;
     }
     leaf dns-cache-entry-prevalence {
       type uint32;
     }
     leaf dns-cache-entry-verdict {
       type string;
     }
     leaf dns-cache-entry-hitcount {
       type uint32;
     }
   }
   grouping dns-filtering-cache-summary-block {
     leaf dns-cache-summary-refresh-rate {
       type uint32;
     }
     leaf dns-cache-summary-lsys-name {
       type string;
     }
     leaf dns-cache-total-count {
       type string;
     }
     leaf dns-cache-benign-count {
       type uint32;
     }
     leaf dns-cache-c2-count {
       type uint32;
     }
   }
   grouping dns-filtering-cache-c2-block {
     leaf dns-cache-refresh-rate-c2 {
       type uint32;
     }
     leaf dns-cache-lsys-name-c2 {
       type string;
     }
     leaf dns-cache-entry-name-c2 {
       type string;
     }
     leaf dns-cache-entry-ttl-c2 {
       type uint32;
     }
     leaf dns-cache-entry-prevalence-c2 {
       type uint32;
     }
     leaf dns-cache-entry-verdict-c2 {
       type string;
     }
     leaf dns-cache-entry-hitcount-c2 {
       type uint32;
     }
   }
   grouping dns-filtering-cache-benign-block {
     leaf dns-cache-refresh-rate-benign {
       type uint32;
     }
     leaf dns-cache-lsys-name-benign {
       type string;
     }
     leaf dns-cache-entry-name-benign {
       type string;
     }
     leaf dns-cache-entry-ttl-benign {
       type uint32;
     }
     leaf dns-cache-entry-prevalence-benign {
       type uint32;
     }
     leaf dns-cache-entry-verdict-benign {
       type string;
     }
     leaf dns-cache-entry-hitcount-benign {
       type uint32;
     }
   }
   grouping web-transparent-proxy-session-information-block {
     list web-transparent-proxy-session {
       leaf client-session-identifier {
         type uint64;
         description
           "Session identifier";
       }
       leaf proxy-session-identifier {
         type uint64;
         description
           "Session identifier";
       }
       leaf client-src-address {
         type jt:ipaddr;
         description
           "Source address";
       }
       leaf client-src-port {
         type uint32;
         description
           "Source port";
       }
       leaf client-dst-address {
         type jt:ipaddr;
         description
           "Destination address";
       }
       leaf client-dst-port {
         type uint32;
         description
           "Destination port";
       }
       leaf proxy-src-address {
         type jt:ipaddr;
         description
           "Source address";
       }
       leaf proxy-src-port {
         type uint32;
         description
           "Source port";
       }
       leaf proxy-dst-address {
         type jt:ipaddr;
         description
           "Destination address";
       }
       leaf proxy-dst-port {
         type uint32;
         description
           "Destination port";
       }
       leaf proxy-http-request {
         type string;
         description
           "Http request";
       }
       leaf proxy-dyn-app-name {
         type string;
         description
           "App requestd";
       }
     }
   }
   grouping web-transparent-proxy-statistics-block {
     leaf active-transparent-proxy-sessions {
       type uint64;
       description
         "Active transparent proxy sessions";
     }
     leaf active-passthru-sessions {
       type uint64;
       description
         "Active passthrough sessions";
     }
     leaf active-http-passthru-sessions {
       type uint64;
       description
         "Active HTTP passthrough sessions";
     }
     leaf active-https-passthru-sessions {
       type uint64;
       description
         "Active HTTPS passthrough sessions";
     }
     leaf active-dns-cache-size {
       type uint64;
       description
         "Active DNS cache size";
     }
     leaf total-transparent-proxy-sessions {
       type uint64;
       description
         "Total transparent proxy sessions";
     }
     leaf total-passthru-sessions {
       type uint64;
       description
         "Total passthrough sessions";
     }
     leaf total-http-passthru-sessions {
       type uint64;
       description
         "Total HTTP passthrough sessions";
     }
     leaf total-https-passthru-sessions {
       type uint64;
       description
         "Total HTTPS passthrough sessions";
     }
   }
   grouping web-explicit-proxy-session-information-block {
     list web-explicit-proxy-session {
       leaf client-session-identifier {
         type uint64;
         description
           "Session identifier";
       }
       leaf proxy-session-identifier {
         type uint64;
         description
           "Session identifier";
       }
       leaf client-src-address {
         type jt:ipaddr;
         description
           "Source address";
       }
       leaf client-src-port {
         type uint32;
         description
           "Source port";
       }
       leaf client-dst-address {
         type jt:ipaddr;
         description
           "Destination address";
       }
       leaf client-dst-port {
         type uint32;
         description
           "Destination port";
       }
       leaf proxy-src-address {
         type jt:ipaddr;
         description
           "Source address";
       }
       leaf proxy-src-port {
         type uint32;
         description
           "Source port";
       }
       leaf proxy-dst-address {
         type jt:ipaddr;
         description
           "Destination address";
       }
       leaf proxy-dst-port {
         type uint32;
         description
           "Destination port";
       }
       leaf proxy-http-request {
         type string;
         description
           "Http request";
       }
       leaf proxy-dyn-app-name {
         type string;
         description
           "App requestd";
       }
       leaf client-tcp-status {
         type string;
         description
           "TCP 3-way handshake status";
       }
       leaf client-timeout {
         type uint32;
         description
           "Session timeout";
       }
       leaf client-sess-state {
         type string;
         description
           "Client session state";
       }
       leaf client-in-pkt-cnt {
         type uint64;
         description
           "In Packet count";
       }
       leaf client-in-byte-cnt {
         type uint64;
         description
           "In Byte count";
       }
       leaf client-out-pkt-cnt {
         type uint64;
         description
           "Out Packet count";
       }
       leaf client-out-byte-cnt {
         type uint64;
         description
           "Out Byte count";
       }
       leaf proxy-tcp-status {
         type string;
         description
           "TCP 3-way handshake status";
       }
       leaf proxy-syn-sent-status {
         type string;
         description
           "TCP SYN message sent status";
       }
       leaf proxy-syn-ack-recvd-status {
         type string;
         description
           "TCP SYN-ACK message received status";
       }
       leaf proxy-ack-sent-status {
         type string;
         description
           "TCP ACK message sent status";
       }
       leaf proxy-timeout {
         type uint32;
         description
           "Session timeout";
       }
       leaf proxy-sess-state {
         type string;
         description
           "Proxy session state";
       }
       leaf proxy-in-pkt-cnt {
         type uint64;
         description
           "In Packet count";
       }
       leaf proxy-in-byte-cnt {
         type uint64;
         description
           "In Byte count";
       }
       leaf proxy-out-pkt-cnt {
         type uint64;
         description
           "Out Packet count";
       }
       leaf proxy-out-byte-cnt {
         type uint64;
         description
           "Out Byte count";
       }
       leaf ssl-proxy-status {
         type string;
         description
           "SSL proxy status";
       }
       leaf dns-resolve-status {
         type string;
         description
           "DNS resolve status";
       }
       leaf proxy-flags-one {
         type uint32;
         description
           "First set of flags";
       }
       leaf proxy-flags-two {
         type uint32;
         description
           "Second set of flags";
       }
     }
   }
   grouping web-explicit-proxy-statistics-block {
     leaf active-explicit-https-proxy-sessions {
       type uint64;
       description
         "Total HTTPS passthrough sessions";
     }
     leaf active-explicit-http-proxy-sessions {
       type uint64;
       description
         "Total HTTPS passthrough sessions";
     }
     leaf total-explicit-https-proxy-sessions {
       type uint64;
       description
         "Total HTTPS passthrough sessions";
     }
     leaf total-explicit-http-proxy-sessions {
       type uint64;
       description
         "Total HTTPS passthrough sessions";
     }
     leaf explicit-proxy-rate-limit-session-drops {
       type uint64;
       description
         "Total explicit proxy sessions dropped due to rate limit";
     }
     leaf explicit-proxy-system-port-conflict {
       type uint64;
       description
         "Explicit proxy system port conflicts";
     }
   }
   grouping web-proxy-dns-fc-entries-block {
     list web-proxy-dns-fc {
       description
         "DNS cache of a DNS name";
       leaf web-proxy-dns-fc-dns-name {
         type string;
         description
           "DNS name";
       }
       list web-proxy-dns-fc-address {
         description
           "DNS address";
         leaf web-proxy-dns-fc-address-family {
           type string;
           description
             "IP address family";
         }
         leaf web-proxy-dns-fc-address-ttl {
           type int32;
           description
             "TTL value of this address";
         }
         container web-proxy-dns-fc-address-table {
           description
             "DNS address table";
           leaf-list web-proxy-dns-fc-address-entry {
             type string;
             description
               "IP address entry";
           }
         }
       }
     }
   }
   grouping web-proxy-dns-fc-statistics-block {
     leaf dns-fc-active-status {
       type string;
       description
         "DNS status";
     }
     leaf dns-fc-active-entries {
       type uint64;
       description
         "Active DNS Forwarding Cache Entries";
     }
     leaf dns-fc-total {
       type uint64;
       description
         "Total DNS Entries";
     }
     leaf dns-fc-cache-hits {
       type uint64;
       description
         "Total DNS Cache hits";
     }
     leaf dns-fc-cache-miss {
       type uint64;
       description
         "Total DNS Cache miss";
     }
     leaf dns-fc-add-failed {
       type uint64;
       description
         "Total DNS Cache Add failed";
     }
   }
   grouping web-proxy-dns-gc-statistics-block {
     leaf dns-gc-active-status {
       type string;
       description
         "DNS status";
     }
     leaf dns-gc-active-entries {
       type uint32;
       description
         "Active DNS Forwarding Cache Entries";
     }
     leaf dns-gc-total {
       type uint32;
       description
         "Total DNS Entries";
     }
     leaf dns-gc-cache-hits {
       type uint32;
       description
         "Total DNS Cache hits";
     }
     leaf dns-gc-cache-miss {
       type uint32;
       description
         "Total DNS Cache miss";
     }
     leaf dns-gc-res-req-fail {
       type uint32;
       description
         "Total DNS resolve req send fail";
     }
     leaf dns-gc-res-req-timeout {
       type uint32;
       description
         "Total DNS resolve req timeout";
     }
   }
   grouping analytics-agent-information-block {
     list analytics-service-agent-information {
       leaf analytics-service-agent-name {
         type string;
         description
           "Service agent ID";
       }
       leaf analytics-service-agent-output-plugin-count {
         type int32;
         description
           "Number of output plugins configured";
       }
       leaf analytics-service-agent-input-plugin-count {
         type int32;
         description
           "Number of input plugins configured";
       }
       leaf analytics-service-agent-process-id {
         type int32;
         description
           "Service agent process id(PID)";
       }
       leaf analytics-service-agent-input-plugins {
         type string;
         description
           "Service agent input plugin list";
       }
       leaf analytics-service-agent-output-plugins {
         type string;
         description
           "Service agent output plugin list";
       }
     }
     container analytics-controller-information {
       leaf analytics-controller-process-id {
         type int32;
         description
           "Analytics agent process id(PID)";
       }
       leaf analytics-controller-conf-file {
         type string;
         description
           "Analytics agent configuration file";
       }
       leaf analytics-controller-log-file {
         type string;
         description
           "Analytics agent log file";
       }
       leaf analytics-controller-service-agent-count {
         type int32;
         description
           "Number of service agents";
       }
     }
   }
   grouping services-analytics-dialout-statistics-block {
     list session {
       key "streaming-server export-profile";
       leaf streaming-server {
         type string;
       }
       leaf export-profile {
         type string;
       }
       leaf source-address {
         type string;
       }
       leaf destination-address {
         type string;
       }
       leaf dialout-type {
         type string;
       }
       leaf session-type {
         type string;
       }
       leaf packets-sent {
         type int32;
       }
       leaf session-duration {
         type string;
       }
       leaf session-begin-time {
         type string;
       }
     }
   }
   grouping probe-results-block {
     list probe-results-terse {
       leaf test-name {
         type string;
         description
           "Name of test";
       }
       leaf destination-interface {
         type string;
         description
           "Name of output interface for probes";
       }
       leaf target-address {
         type string;
         description
           "Target address of test";
       }
       leaf last-status {
         type string;
         description
           "Status";
       }
       leaf last-status-changed {
         type string;
         description
           "Last time when status updated";
       }
       leaf twl-local-link {
         type string;
         description
           "Name of local link for TWAMP-Light probes";
       }
       leaf last-probe-status {
         type string;
         description
           "Probe status";
       }
     }
     list probe-test-results {
       leaf owner {
         type string;
         description
           "Test owner name";
       }
       leaf test-name {
         type string;
         description
           "Name of test";
       }
       leaf target-address {
         type string;
         description
           "Target address of test";
       }
       leaf target-url {
         type string;
         description
           "Target URL of test";
       }
       leaf target-fqdn {
         type string;
         description
           "Target FQDN of test";
       }
       leaf source-address {
         type string;
         description
           "Source address of test";
       }
       leaf probe-type {
         type string;
         description
           "Name of the probe";
       }
       leaf icmp-id {
         type uint32;
         description
           "Icmp id for icmp-ping probes";
       }
       leaf test-size {
         type uint32;
         description
           "Number of probes in test";
       }
       leaf server-status {
         type string;
         description
           "TWAMP server is Connected or Not";
       }
       leaf twamp-client-retries {
         type uint32;
         description
           "Retries to connect TWAMP server at every test-interval";
       }
       leaf server-address {
         type jt:ipaddr;
         description
           "Server address";
       }
       leaf server-port {
         type uint32;
         description
           "Server port";
       }
       leaf client-address {
         type jt:ipaddr;
         description
           "Client address";
       }
       leaf client-port {
         type uint32;
         description
           "Client port";
       }
       leaf reflector-address {
         type jt:ipaddr;
         description
           "Reflector address";
       }
       leaf reflector-port {
         type uint32;
         description
           "Reflector port";
       }
       leaf sender-address {
         type jt:ipaddr;
         description
           "Sender address";
       }
       leaf sender-port {
         type uint32;
         description
           "Sender port";
       }
       leaf routing-instance-name {
         type string;
         description
           "Routing Instance Name";
       }
       leaf destination-interface {
         type string;
         description
           "Name of output interface for probes";
       }
       leaf twl-local-link {
         type string;
         description
           "Name of local link for TWAMP-Light probes";
       }
       leaf http-status {
         type uint32;
         description
           "HTTP Status Code";
       }
       leaf loss-thresh-total {
         type uint32;
         description
           "Maximum number of all lost probes";
       }
       leaf loss-thresh-succ {
         type uint32;
         description
           "Maximum number of successive lost probes";
       }
       leaf delay-thresh {
         type uint32;
         description
           "Maximum delay threshold";
       }
       leaf jitter-thresh {
         type uint32;
         description
           "Maximum jitter threshold";
       }
       leaf stddev-thresh {
         type uint32;
         description
           "Maximum standard deviation threshold";
       }
       leaf egress-thresh {
         type uint32;
         description
           "Maximum egress delay threshold";
       }
       leaf egress-jitter-thresh {
         type uint32;
         description
           "Maximum egress jitter threshold";
       }
       leaf egress-stddev-thresh {
         type uint32;
         description
           "Maximum egress standard deviation threshold";
       }
       leaf ingress-thresh {
         type uint32;
         description
           "Maximum ingress delay threshold";
       }
       leaf ingress-jitter-thresh {
         type uint32;
         description
           "Maximum ingress jitter threshold";
       }
       leaf ingress-stddev-thresh {
         type uint32;
         description
           "Maximum ingress standard deviation threshold";
       }
       container probe-single-results {
         leaf probe-sent-time {
           type string;
           description
             "Time at which probe was sent";
         }
         leaf probe-status {
           type string;
           description
             "Operation response status from probes";
         }
         leaf probe-time {
           type string;
           description
             "Time at which probe response was received or timed out";
         }
         leaf hardware-timestamp-status {
           type string;
           description
             "Use of hardware timestamps in probes";
         }
         leaf http-status {
           type uint32;
           description
             "HTTP Status Code";
         }
         leaf rtt {
           type uint32;
           description
             "Round trip time of probes";
         }
         leaf ingress {
           type uint32;
           description
             "Ingress trip time of probes";
         }
         leaf egress {
           type uint32;
           description
             "Egress trip time of probes";
         }
         leaf egress-jitter {
           type int32;
           description
             "Egress jitter of probes";
         }
         leaf ingress-jitter {
           type int32;
           description
             "Ingress jitter of probes";
         }
         leaf round-trip-jitter {
           type int32;
           description
             "Round trip jitter of probes";
         }
         leaf egress-interarrival-jitter {
           type int32;
           description
             "Egress interarrival jitter of probes";
         }
         leaf ingress-interarrival-jitter {
           type int32;
           description
             "Ingress interarrival jitter of probes";
         }
         leaf round-trip-interarrival-jitter {
           type int32;
           description
             "Round trip interarrival jitter of probes";
         }
         leaf owner {
           type string;
           description
             "Test owner name";
         }
         leaf test-name {
           type string;
           description
             "Name of test";
         }
       }
       container probe-test-current-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-last-test-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-moving-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-global-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
       container probe-test-hwts-err-stats {
         leaf invalid-client-recv-ts-cntr {
           type uint32;
           description
             "Client recv timestamp less than Client send timestamp";
         }
         leaf invalid-client-nots-cntr {
           type uint32;
           description
             "Client timestamps (T1, T4) are marked as deadbeef";
         }
         leaf invalid-server-send-ts-cntr {
           type uint32;
           description
             "Server send timestamp less than Server recv timestamp";
         }
         leaf invalid-server-spent-time-cntr {
           type uint32;
           description
             "Server side spent time greater than RTT";
         }
         leaf pkt-rcvd-after-timeout-cntr {
           type uint32;
           description
             "RTT is greater than probe-interval";
         }
       }
     }
   }
   grouping history-results-block {
     list history-test-results {
       leaf owner {
         type string;
         description
           "Test owner name";
       }
       leaf test-name {
         type string;
         description
           "Name of test";
       }
       leaf probe-type {
         type string;
         description
           "Name of the probe";
       }
       leaf icmp-id {
         type uint32;
         description
           "Icmp id for icmp-ping probes";
       }
       leaf target-address {
         type string;
         description
           "Target address of test";
       }
       leaf target-url {
         type string;
         description
           "Target URL of test";
       }
       leaf target-fqdn {
         type string;
         description
           "Target FQDN of test";
       }
       leaf source-address {
         type string;
         description
           "Source address of test";
       }
       leaf destination-interface {
         type string;
         description
           "Name of output interface for probes";
       }
       leaf twl-local-link {
         type string;
         description
           "Name of local link for TWAMP-Light probes";
       }
       leaf loss-thresh-total {
         type uint32;
         description
           "Maximum number of all lost probes";
       }
       leaf loss-thresh-succ {
         type uint32;
         description
           "Maximum number of successive lost probes";
       }
       leaf delay-thresh {
         type uint32;
         description
           "Maximum delay threshold";
       }
       leaf jitter-thresh {
         type uint32;
         description
           "Maximum jitter threshold";
       }
       leaf stddev-thresh {
         type uint32;
         description
           "Maximum standard deviation threshold";
       }
       leaf egress-thresh {
         type uint32;
         description
           "Maximum egress delay threshold";
       }
       leaf egress-jitter-thresh {
         type uint32;
         description
           "Maximum egress jitter threshold";
       }
       leaf ingress-thresh {
         type uint32;
         description
           "Maximum ingress delay threshold";
       }
       leaf ingress-jitter-thresh {
         type uint32;
         description
           "Maximum ingress jitter threshold";
       }
       container probe-single-results {
         leaf probe-sent-time {
           type string;
           description
             "Time at which probe was sent";
         }
         leaf probe-status {
           type string;
           description
             "Operation response status from probes";
         }
         leaf probe-time {
           type string;
           description
             "Time at which probe response was received or timed out";
         }
         leaf hardware-timestamp-status {
           type string;
           description
             "Use of hardware timestamps in probes";
         }
         leaf http-status {
           type uint32;
           description
             "HTTP Status Code";
         }
         leaf rtt {
           type uint32;
           description
             "Round trip time of probes";
         }
         leaf ingress {
           type uint32;
           description
             "Ingress trip time of probes";
         }
         leaf egress {
           type uint32;
           description
             "Egress trip time of probes";
         }
         leaf egress-jitter {
           type int32;
           description
             "Egress jitter of probes";
         }
         leaf ingress-jitter {
           type int32;
           description
             "Ingress jitter of probes";
         }
         leaf round-trip-jitter {
           type int32;
           description
             "Round trip jitter of probes";
         }
         leaf egress-interarrival-jitter {
           type int32;
           description
             "Egress interarrival jitter of probes";
         }
         leaf ingress-interarrival-jitter {
           type int32;
           description
             "Ingress interarrival jitter of probes";
         }
         leaf round-trip-interarrival-jitter {
           type int32;
           description
             "Round trip interarrival jitter of probes";
         }
         leaf owner {
           type string;
           description
             "Test owner name";
         }
         leaf test-name {
           type string;
           description
             "Name of test";
         }
       }
       container probe-test-current-results {
         container probe-test-generic-results {
           leaf results-scope {
             type string;
             description
               "Scope of results";
           }
           leaf probes-sent {
             type uint32;
             description
               "Number of probes sent";
           }
           leaf probe-responses {
             type uint32;
             description
               "Responses from probes";
           }
           leaf loss-percentage {
             type string;
             description
               "Percentage of probes lost (no response)";
           }
           container probe-last-test-info {
             leaf last-test-time {
               type string;
               description
                 "Time at which last test was completed";
             }
           }
           container probe-test-rtt {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-egress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-ingress-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-positive-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-negative-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container probe-test-round-trip-jitter {
             container probe-summary-results {
               leaf probe-results-type {
                 type string;
                 description
                   "Results type";
               }
               leaf samples {
                 type uint32;
                 description
                   "Number of samples";
               }
               leaf min-delay {
                 type uint32;
                 description
                   "Minimum delay time";
               }
               leaf max-delay {
                 type uint32;
                 description
                   "Maximum delay time";
               }
               leaf avg-delay {
                 type uint32;
                 description
                   "Average delay time";
               }
               leaf jitter-delay {
                 type uint32;
                 description
                   "Difference between maximum and minimum delay times";
               }
               leaf stddev-delay {
                 type uint64;
                 description
                   "Standard deviation of delay time";
               }
               leaf sum-delay {
                 type uint64;
                 description
                   "Sum of delay times";
               }
             }
           }
           container rpm-results-thresh {
             leaf rtt-thresh {
               type uint32;
               description
                 "Round trip time thresh";
             }
             leaf rtt-jitter-thresh {
               type uint32;
               description
                 "Round trip jitter threshold";
             }
             leaf rtt-stddev-thresh {
               type uint32;
               description
                 "Round trip standard deviaion thresh";
             }
             leaf igr-thresh {
               type uint32;
               description
                 "Ingress threshold";
             }
             leaf igr-jitter-thresh {
               type uint32;
               description
                 "Ingress jitter threshold";
             }
             leaf igr-stddev-thresh {
               type uint32;
               description
                 "Ingress standard deviation threshold";
             }
             leaf egr-thresh {
               type uint32;
               description
                 "Egress threshold";
             }
             leaf egr-jitter-thresh {
               type uint32;
               description
                 "Egress jitter threshold";
             }
             leaf egr-stddev-thresh {
               type uint32;
               description
                 "Egress standared deviation threshold";
             }
           }
         }
       }
     }
   }
   grouping active-servers-block {
     list configured-servers {
       leaf protocol {
         type string;
         description
           "Protocol";
       }
       leaf port {
         type uint32;
         description
           "Port";
       }
       leaf destination-interface {
         type string;
         description
           "Name of output interface for probes";
       }
     }
   }
   grouping twamp-client-information-block {
     list client-connection {
       description
         "Client connection information";
       leaf connection-name {
         type string;
         description
           "TWAMP Client control connection name";
       }
       leaf client-address {
         type jt:ipaddr;
         description
           "Client address";
       }
       leaf client-port {
         type uint32;
         description
           "Client port";
       }
       leaf server-address {
         type jt:ipaddr;
         description
           "Server address";
       }
       leaf server-port {
         type uint32;
         description
           "Server port";
       }
       leaf session-count {
         type uint32;
         description
           "Number of sessions";
       }
       leaf authentication-mode {
         type string;
         description
           "Authentication mode";
       }
     }
     list twamp-test-session {
       description
         "TWAMP Test Session information";
       leaf connection-name {
         type string;
         description
           "TWAMP Client control connection name";
       }
       leaf session-name {
         type string;
         description
           "TWAMP Client test session name";
       }
       leaf sender-address {
         type jt:ipaddr;
         description
           "Sender address";
       }
       leaf sender-port {
         type uint32;
         description
           "Sender port";
       }
       leaf reflector-address {
         type jt:ipaddr;
         description
           "Reflector address";
       }
       leaf reflector-port {
         type uint32;
         description
           "Reflector port";
       }
     }
   }
   grouping twamp-server-information-block {
     list connection {
       description
         "Server connection";
       leaf connection-id {
         type uint32;
         description
           "Connection ID";
       }
       leaf client-address {
         type jt:ipaddr;
         description
           "Client address";
       }
       leaf client-port {
         type uint32;
         description
           "Client port";
       }
       leaf server-address {
         type jt:ipaddr;
         description
           "Server address";
       }
       leaf server-port {
         type uint32;
         description
           "Server port";
       }
       leaf session-count {
         type uint32;
         description
           "Number of sessions";
       }
       leaf authentication-mode {
         type string;
         description
           "Authentication mode";
       }
     }
     container server {
       description
         "Server information";
       list session {
         description
           "Server session";
         leaf session-id {
           type uint32;
           description
             "Session ID";
         }
         leaf connection-id {
           type uint32;
           description
             "Connection ID";
         }
         leaf sender-address {
           type jt:ipaddr;
           description
             "Sender address";
         }
         leaf sender-port {
           type uint32;
           description
             "Sender port";
         }
         leaf reflector-address {
           type jt:ipaddr;
           description
             "Reflector address";
         }
         leaf reflector-port {
           type uint32;
           description
             "Reflector port";
         }
         leaf session-state {
           type string;
           description
             "Session state";
         }
         leaf authentication-mode {
           type string;
           description
             "Authentication mode";
         }
         leaf ip-version {
           type uint32;
           description
             "IP version";
         }
         leaf padding-length {
           type uint32;
           description
             "Padding length";
         }
         leaf start-time {
           type string;
           description
             "Starting time";
         }
         leaf timeout {
           type uint32;
           description
             "Timeout";
         }
         container packet-statistics {
           description
             "Test session packet statistics";
           leaf request-sessions-received {
             type uint32;
             description
               "Request sessions received";
           }
           leaf accept-sessions-sent {
             type uint32;
             description
               "Accept sessions sent";
           }
           leaf start-sessions-received {
             type uint32;
             description
               "Start sessions received";
           }
           leaf stop-sessions-received {
             type uint32;
             description
               "Stop sessions received";
           }
           leaf test-packets-received {
             type uint32;
             description
               "Test packets received";
           }
           leaf test-packets-reflected {
             type uint32;
             description
               "Test packets reflected";
           }
           leaf last-sequence-number-received {
             type uint32;
             description
               "Last sequence number received";
           }
           leaf last-sequence-number-sent {
             type uint32;
             description
               "Last sequence number sent";
           }
           leaf test-packets-dropped {
             type uint32;
             description
               "Test packets dropped";
           }
           container test-packets-dropped-details {
             description
               "Test packets dropped details";
             leaf session-nonexist {
               type uint32;
               description
                 "Test packets dropped because session does not exist";
             }
             leaf session-notactive {
               type uint32;
               description
                 "Test packets dropped because session is not active";
             }
             leaf packet-unsupported {
               type uint32;
               description
                 "Packet unsupported";
             }
             leaf packet-malformed {
               type uint32;
               description
                 "Packet malformed";
             }
             leaf internal-error {
               type uint32;
               description
                 "Internal error";
             }
           }
         }
       }
     }
     container server-statistics {
       description
         "Server statistics";
       container packet-statistics {
         description
           "Test session packet statistics";
         container test-packets-dropped-details {
           description
             "Test packets dropped details";
           leaf session-nonexist {
             type uint32;
             description
               "Test packets dropped because session does not exist";
           }
           leaf session-notactive {
             type uint32;
             description
               "Test packets dropped because session is not active";
           }
           leaf packet-unsupported {
             type uint32;
             description
               "Packet unsupported";
           }
           leaf packet-malformed {
             type uint32;
             description
               "Packet malformed";
           }
           leaf internal-error {
             type uint32;
             description
               "Internal error";
           }
         }
       }
     }
   }
   grouping service-crtp-flow-table-information-block {
     list crtp-per-interface-flow-table {
       description
         "CRTP flows sorted by interface";
       leaf interface-name {
         type string;
         description
           "Name of the adaptive services interface";
       }
       list service-crtp-flow-table {
         description
           "CRTP flows";
         list crtp-flow-entry {
           description
             "CRTP flow information";
           leaf crtp-flow-type {
             type string;
             description
               "Flow type";
           }
           leaf crtp-flow-source-info {
             type string;
             description
               "Flow source information (IP address and UDP port)";
           }
           leaf crtp-flow-destination-info {
             type string;
             description
               "Flow destination information (IP address and UDP port)";
           }
           leaf crtp-flow-rtp-id {
             type int32;
             description
               "RTP SSRC identifier";
           }
           leaf crtp-flow-context-id {
             type int32;
             description
               "Context identifier";
           }
         }
       }
     }
   }
   grouping ssl-statistics-block {
     leaf ssl-statistics-lsys-name {
       type string;
     }
     container ssl-statistics-pic {
       leaf ssl-statistics-pic-info {
         type string;
       }
       leaf ssl-statistics-sessions-matched {
         type uint32;
       }
       leaf ssl-statistics-sessions-bypassed-non-ssl {
         type uint32;
       }
       leaf ssl-statistics-sessions-bypassed-mem-overflow {
         type uint32;
       }
       leaf ssl-statistics-sessions-bypassed-low-memory {
         type uint32;
       }
       leaf ssl-statistics-sessions-created {
         type uint32;
       }
       leaf ssl-statistics-sessions-ignored {
         type uint32;
       }
       leaf ssl-statistics-sessions-active {
         type uint32;
       }
       leaf ssl-statistics-sessions-dropped {
         type uint32;
       }
       leaf ssl-statistics-sessions-whitelisted {
         type uint32;
       }
       leaf ssl-statistics-whitelisted-url-category-match {
         type uint32;
       }
       leaf ssl-statistics-sessions-default-profile-hit {
         type uint32;
       }
       leaf ssl-statistics-sessions-dropped-no-default-profile {
         type uint32;
       }
       leaf ssl-statistics-sessions-potential-policy-conflict {
         type uint32;
       }
     }
   }
   grouping ssl-status-block {
     container ssl-status-pic {
       leaf ssl-status-pic-info {
         type string;
       }
       leaf ssl-status-one-crypto {
         type string;
       }
       leaf ssl-status-async-crypto {
         type string;
       }
       leaf ssl-status-proxy-activation {
         type string;
       }
       leaf ssl-status-force-enable-jdpi-service {
         type string;
       }
       leaf ssl-status-local-logging {
         type string;
       }
       leaf ssl-status-sslfp-pkid-link-status {
         type string;
       }
       leaf ssl-status-deferred-profile-selection {
         type string;
       }
       leaf ssl-status-cert-cache-activated {
         type string;
       }
       leaf ssl-status-invalidate-cert-cache-on-crl-update {
         type string;
       }
       leaf ssl-status-max-cert-cache-nodes {
         type uint32;
       }
       leaf ssl-status-cert-nodes-in-use {
         type uint32;
       }
       leaf ssl-status-sess-cache-activated {
         type string;
       }
       leaf ssl-status-max-sess-cache-nodes {
         type uint32;
       }
       leaf ssl-status-sess-nodes-in-use {
         type uint32;
       }
       leaf ssl-status-alpn-extension-support {
         type string;
       }
       leaf ssl-status-strip-h2-alpn-extension {
         type string;
       }
     }
   }
   grouping ssl-counters-block {
     leaf ssl-counters-lsys-name {
       type string;
     }
     list ssl-counters-pic {
       leaf ssl-counters-pic-info {
         type string;
       }
       container ssl-counters-info {
         leaf ssl-counters-name {
           type string;
         }
         leaf ssl-counters-value {
           type uint32;
         }
       }
     }
   }
   grouping ssl-profile-list-block {
     leaf ssl-profile-list-lsys-name {
       type string;
     }
     container ssl-profile-list-pic {
       leaf ssl-profile-list-pic-info {
         type string;
       }
       container ssl-profile-list-info {
         leaf ssl-profile-id {
           type uint32;
         }
         leaf ssl-profile-name {
           type string;
         }
       }
     }
   }
   grouping ssl-profile-detail-block {
     leaf ssl-profile-detail-lsys-name {
       type string;
     }
     container ssl-profile-detail-pic {
       leaf ssl-profile-detail-pic-info {
         type string;
       }
       leaf ssl-profile-profile {
         type string;
       }
       leaf ssl-profile-trace {
         type string;
       }
       leaf ssl-profile-root-ca {
         type string;
       }
       leaf ssl-profile-allow-non-ssl-session {
         type string;
       }
       leaf ssl-profile-termination-profile-id {
         type uint32;
       }
       leaf ssl-profile-initiation-profile-id {
         type uint32;
       }
       leaf ssl-profile-nof-whitelist-entries {
         type uint32;
       }
       leaf ssl-profile-supported-protocol-version {
         type string;
       }
     }
   }
   grouping ssl-proxy-sess-cache-entries-block {
     leaf ssl-proxy-sess-cache-entries-lsys-name {
       type string;
     }
     container ssl-proxy-sess-cache-entries-pic {
       leaf ssl-proxy-sess-cache-entries-pic-info {
         type string;
       }
       leaf ssl-proxy-sess-cache-hash-entry {
         type uint32;
       }
       leaf ssl-proxy-sess-cache-status {
         type string;
       }
       leaf ssl-proxy-sess-cache-key {
         type string;
       }
       leaf ssl-proxy-sess-cache-sess-id-len {
         type uint32;
       }
       leaf ssl-proxy-sess-cache-sess-id {
         type string;
       }
       leaf ssl-proxy-sess-cache-dest-ip {
         type string;
       }
       leaf ssl-proxy-sess-cache-dest-port {
         type uint32;
       }
       leaf ssl-proxy-sess-cache-term-profile-id {
         type uint32;
       }
       leaf ssl-proxy-sess-cache-init-profile-id {
         type uint32;
       }
       leaf ssl-proxy-ssl-t-resumption-type {
         type string;
       }
       leaf ssl-proxy-ssl-i-resumption-type {
         type string;
       }
       leaf ssl-proxy-sess-cache-interdicted-cert-type {
         type string;
       }
       leaf ssl-proxy-sess-cache-server-cert-verification-result {
         type string;
       }
       leaf ssl-proxy-sess-cache-server-name-extn-len {
         type uint32;
       }
       leaf ssl-proxy-sess-cache-server-name-extn-name {
         type string;
       }
       leaf ssl-proxy-sess-cache-server-cert-chain-hash {
         type string;
       }
       leaf ssl-proxy-sess-cache-term-ssl-version {
         type uint32;
       }
       leaf ssl-proxy-sess-cache-term-compression-method {
         type int32;
       }
       leaf ssl-proxy-sess-cache-term-cipher-id {
         type uint32;
       }
       leaf ssl-proxy-sess-cache-term-master-key-len {
         type uint32;
       }
       leaf ssl-proxy-sess-cache-init-ssl-version {
         type uint32;
       }
       leaf ssl-proxy-sess-cache-init-compression-method {
         type uint32;
       }
       leaf ssl-proxy-sess-cache-init-cipher-id {
         type uint32;
       }
       leaf ssl-proxy-sess-cache-init-master-key-len {
         type uint32;
       }
       leaf ssl-proxy-ssli-tick-validity {
         type string;
       }
       leaf ssl-proxy-ssli-tick-lifetime-hint {
         type uint32;
       }
       leaf ssl-proxy-ssli-tick-age-add {
         type uint32;
       }
       leaf ssl-proxy-ssli-tick-len {
         type uint32;
       }
       leaf ssl-proxy-sess-cache-stale-entries {
         type uint32;
       }
     }
   }
   grouping ssl-proxy-sess-cache-statistics-block {
     leaf ssl-proxy-sess-cache-statistics-lsys-name {
       type string;
     }
     container ssl-proxy-sess-cache-statistics-pic {
       leaf ssl-proxy-sess-cache-statistics-pic-info {
         type string;
       }
       leaf ssl-proxy-sess-cache-statistics-sess-cache-hit {
         type uint32;
       }
       leaf ssl-proxy-sess-cache-statistics-sess-cache-miss {
         type uint32;
       }
       leaf ssl-proxy-sess-cache-statistics-sess-cache-activation-flr {
         type uint32;
       }
       leaf ssl-proxy-sess-cache-statistics-sess-cache-full {
         type uint32;
       }
     }
   }
   grouping ssl-proxy-cert-cache-entries-block {
     leaf ssl-proxy-cert-cache-entries-lsys-name {
       type string;
     }
     container ssl-proxy-cert-cache-entries-pic {
       leaf ssl-proxy-cert-cache-entries-pic-info {
         type string;
       }
       leaf ssl-proxy-cert-cache-entry {
         type uint32;
       }
       leaf ssl-proxy-cert-cache-key {
         type string;
       }
       leaf ssl-proxy-cert-cache-serial-number {
         type string;
       }
       leaf ssl-proxy-cert-cache-init-profile-id {
         type uint32;
       }
       leaf ssl-proxy-cert-cache-num-of-crl-update {
         type uint32;
       }
       leaf ssl-proxy-cert-cache-status {
         type string;
       }
       leaf ssl-proxy-cert-cache-interdicted-cert-type {
         type string;
       }
       leaf ssl-proxy-cert-cache-server-cert-verification-result {
         type string;
       }
       leaf ssl-proxy-cert-cache-cert-ref-count {
         type uint32;
       }
       leaf ssl-proxy-cert-cache-subject {
         type string;
       }
       leaf ssl-proxy-cert-cache-issuer {
         type string;
       }
     }
   }
   grouping ssl-proxy-cert-cache-statistics-block {
     leaf ssl-proxy-cert-cache-statistics-lsys-name {
       type string;
     }
     container ssl-proxy-cert-cache-statistics-pic {
       leaf ssl-proxy-cert-cache-statistics-pic-info {
         type string;
       }
       leaf ssl-proxy-cert-cache-statistics-sess-cache-hit {
         type uint32;
       }
       leaf ssl-proxy-cert-cache-statistics-sess-cache-miss {
         type uint32;
       }
       leaf ssl-proxy-cert-cache-statistics-sess-cache-activation-flr {
         type uint32;
       }
       leaf ssl-proxy-cert-cache-statistics-sess-cache-full {
         type uint32;
       }
     }
   }
   grouping ssl-certificate-block {
     leaf ssl-certificate-lsys-name {
       type string;
     }
     container ssl-certificate-pic {
       leaf ssl-certificate-pic-info {
         type string;
       }
       leaf ssl-cert-id {
         type uint32;
       }
     }
   }
   grouping ssl-certificate-id-detail-block {
     leaf ssl-certificate-id-detail-lsys-name {
       type string;
     }
     container ssl-certificate-id-detail-pic {
       leaf ssl-certificate-id-detail-pic-info {
         type string;
       }
       container ssl-certificate-id-detail-info {
         leaf ssl-certificate-id {
           type string;
         }
         leaf ssl-cert-type {
           type string;
         }
         leaf ssl-issuer {
           type string;
         }
         leaf ssl-subject {
           type string;
         }
         leaf ssl-validity {
           type string;
         }
         leaf ssl-validity-not-before {
           type string;
         }
         leaf ssl-validity-not-after {
           type string;
         }
         leaf ssl-public-key-algorithm {
           type string;
         }
         leaf ssl-cert-modify-time {
           type string;
         }
         leaf ssl-key-modify-time {
           type string;
         }
         leaf ssl-certificate-version {
           type uint32;
         }
         leaf ssl-serial-number {
           type string;
         }
         leaf ssl-signature-algorithm {
           type string;
         }
         leaf ssl-crl {
           type string;
         }
         leaf ssl-crl-present {
           type string;
         }
         leaf ssl-crl-check {
           type string;
         }
         leaf ssl-crl-download-failed {
           type string;
         }
         leaf ssl-crl-check-on-download-failed {
           type string;
         }
       }
     }
   }
   grouping ssl-term-profile-detail-block {
     leaf ssl-term-profile-detail-lsys-name {
       type string;
     }
     container ssl-term-profile-detail-pic {
       leaf ssl-term-profile-detail-pic-info {
         type string;
       }
       leaf ssl-term-profile-detail-profile {
         type string;
       }
       leaf ssl-term-profile-detail-allow-non-ssl-sess {
         type string;
       }
       leaf ssl-term-profile-detail-preferred-ciphers {
         type string;
       }
       leaf ssl-term-profile-detail-nof-url-categories-conf {
         type uint32;
       }
       leaf ssl-term-profile-detail-protocol-version {
         type string;
       }
       leaf ssl-term-profile-detail-client-auth {
         type string;
       }
       leaf ssl-term-profile-detail-server-auth {
         type string;
       }
       leaf ssl-term-profile-detail-crypto-mode {
         type string;
       }
       leaf ssl-term-profile-detail-sess-resumption {
         type string;
       }
       leaf ssl-term-profile-detail-crl-check {
         type string;
       }
       leaf ssl-term-profile-detail-cert-rsa {
         type string;
       }
       leaf ssl-term-profile-detail-cert-ecdsa {
         type string;
       }
       leaf ssl-term-profile-detail-renegotiation {
         type string;
       }
       leaf ssl-term-profile-detail-custom-ciphers {
         type string;
       }
       leaf ssl-term-profile-detail-server-cert {
         type string;
       }
       leaf ssl-term-profile-detail-decrypt-mirror {
         type string;
       }
       leaf ssl-term-profile-detail-trusted-ca {
         type string;
       }
       leaf ssl-term-profile-detail-cert-chain-rsa-cert {
         type string;
       }
       leaf ssl-term-profile-detail-chain-ca-of-rsa-cert {
         type uint32;
       }
       leaf ssl-term-profile-detail-cert-chain-ecc-cert {
         type string;
       }
       leaf ssl-term-profile-detail-chain-ca-of-ecc-cert {
         type uint32;
       }
       list ssl-term-profile-detail-status {
         leaf ssl-term-profile-detail-status-counter-name {
           type string;
         }
         leaf ssl-term-profile-detail-status-counter-value {
           type uint32;
         }
       }
     }
   }
   grouping ssl-session-block {
     leaf ssl-session-lsys-name {
       type string;
     }
     leaf ssl-session-pic-info {
       type string;
     }
     leaf ssl-session-session-id {
       type uint32;
     }
     leaf ssl-session-connection-type {
       type string;
     }
     leaf ssl-session-ssl-profile {
       type string;
     }
     leaf ssl-session-early-dynapp-profile {
       type string;
     }
     leaf ssl-session-http-proxy-session {
       type string;
     }
     leaf ssl-session-swg-session {
       type string;
     }
     leaf ssl-session-init-sni {
       type string;
     }
     leaf ssl-session-resumed-session {
       type string;
     }
     leaf ssl-session-one-crypto {
       type string;
     }
     leaf ssl-session-async-crypto {
       type string;
     }
     leaf ssl-session-reneg-count {
       type uint32;
     }
     leaf ssl-session-cert {
       type string;
     }
     leaf ssl-session-cert-status {
       type string;
     }
     leaf ssl-session-cert-crl-check {
       type string;
     }
     leaf ssl-session-cert-action {
       type string;
     }
     leaf ssl-session-authentication {
       type string;
     }
     leaf ssl-session-term-key-size {
       type uint32;
     }
     leaf ssl-session-term-cipher {
       type string;
     }
     leaf ssl-session-term-tls-version {
       type uint32;
     }
     leaf ssl-session-init-key-size {
       type uint32;
     }
     leaf ssl-session-init-cipher {
       type string;
     }
     leaf ssl-session-init-tls-version {
       type uint32;
     }
   }
   grouping ssl-droplog-block {
     leaf ssl-droplog-lsys-name {
       type string;
     }
     container ssl-droplog-pic {
       leaf ssl-droplog-pic-info {
         type string;
       }
       leaf ssl-droplog-msg {
         type string;
       }
     }
   }
   grouping ip-monitoring-block {
     leaf ipmon-header {
       type string;
       description
         "Ip-monitoring header";
     }
     container policy-header {
       description
         "Ip-monitoring policy header";
       leaf policy-name {
         type string;
         description
           "Ip-monitoring policy name";
       }
     }
     container status {
       description
         "Ip-monitoring status";
       leaf probe-name {
         type string;
         description
           "RPM probe owner's name";
       }
       leaf test-name {
         type string;
         description
           "RPM test name";
       }
       leaf target-address {
         type string;
         description
           "Target address of test";
       }
       leaf probe-status {
         type string;
         description
           "RPM probe status";
       }
     }
     container status-route {
       leaf route-action-type {
         type string;
         description
           "The type of route action";
       }
       leaf instance {
         type string;
         description
           "Routing instance";
       }
       leaf route {
         type string;
         description
           "Static route";
       }
       leaf next-hop {
         type string;
         description
           "Next hop";
       }
       leaf preferred-route-state {
         type string;
         description
           "Preferred-route action state";
       }
     }
     container status-intf {
       leaf intf {
         type string;
         description
           "Interface";
       }
       leaf intf-action {
         type string;
         description
           "Interface action";
       }
       leaf intf-state {
         type string;
         description
           "Interface state";
       }
       leaf intf-action-state {
         type string;
         description
           "Interface action failover state";
       }
     }
   }
   grouping tdir-commit-status-block {
     leaf tdir-config-status {
       type string;
       description
         "Prints config status of previous commit";
     }
   }
   grouping uac-debug-counters-block {
     leaf uac-debug-counters-title {
       type string;
       description
         "Uac debug counters";
     }
     list uac-debug-counter-info {
       description
         "Uac debug counter info";
       leaf uac-debug-counter-name {
         type string;
       }
       leaf uac-debug-counter-value {
         type uint32;
       }
     }
   }
   grouping uac-counters-block {
     list uac-counter {
       description
         "UAC counter for the PFE";
       leaf pfe-name {
         type string;
         description
           "PFE";
       }
       leaf allowed-policy-action {
         type uint32;
         description
           "Sessions allowed due to policy action";
       }
       leaf allowed-timeout-action {
         type uint32;
         description
           "Sessions allowed due to timeout action";
       }
       leaf denied-unauthenticated {
         type uint32;
         description
           "Sessions denied due to lack of authentication";
       }
       leaf denied-policy-action {
         type uint32;
         description
           "Sessions denied due to policy action";
       }
       leaf denied-policy-unmatched {
         type uint32;
         description
           "Sessions denied due to unmatched policy";
       }
       leaf denied-timeout-action {
         type uint32;
         description
           "Sessions denied due to timeout action";
       }
       leaf terminated-reevaluation {
         type uint32;
         description
           "Sessions terminated due to reevaluation";
       }
       leaf terminated-signout {
         type uint32;
         description
           "Sessions terminated due to user signout";
       }
       leaf auth-added {
         type uint32;
         description
           "Auth entry added to PFE";
       }
       leaf auth-deleted {
         type uint32;
         description
           "Auth entry deleted from PFE";
       }
       leaf current-auth-cnt {
         type uint32;
         description
           "UAC total auth count";
       }
     }
   }
   grouping swgauth-profile-statistics-block {
     leaf swgauth-profile-name {
       type string;
     }
     leaf swgauth-profile-total-sessions {
       type uint32;
     }
     leaf swgauth-profile-current-sessions {
       type uint32;
     }
     leaf swgauth-profile-http-sessions {
       type uint32;
     }
     leaf swgauth-profile-https-sessions {
       type uint32;
     }
     leaf swgauth-profile-not-supported-sessions {
       type uint32;
     }
     leaf swgauth-profile-on-prem-captive-portal-redirect {
       type uint32;
     }
     leaf swgauth-profile-roaming-captive-portal-redirect {
       type uint32;
     }
     leaf swgauth-profile-roaming-uid-not-rcvd-redirect {
       type uint32;
     }
     leaf swgauth-profile-roaming-uid-reset-redirect {
       type uint32;
     }
     leaf swgauth-profile-roaming-sessions-processed {
       type uint32;
     }
     leaf swgauth-profile-preflight-sessions-handled {
       type uint32;
     }
     leaf swgauth-profile-cors-sessions-handled {
       type uint32;
     }
     leaf swgauth-profile-nocors-sessions-handled {
       type uint32;
     }
     leaf swgauth-profile-sessions-rejected {
       type uint32;
     }
     leaf swgauth-profile-denied-pkts {
       type uint32;
     }
     leaf swgauth-profile-sessions-denied {
       type uint32;
     }
     leaf swgauth-profile-sessions-destroyed {
       type uint32;
     }
   }
   grouping swgauth-captiveportal-redirect-statistics-block {
     leaf swgauth-auth-entries-lru-evicted {
       type uint32;
     }
     leaf swgauth-session-dropped-max-limit {
       type uint32;
     }
     leaf swgauth-auth-entries {
       type uint32;
     }
     leaf swgauth-avg-enc-time {
       type uint32;
     }
     leaf swgauth-avg-dec-time {
       type uint32;
     }
   }
   grouping swgauth-captiveportal-connection-statistics-block {
     leaf swgauth-certificate-status {
       type string;
     }
     leaf swgauth-certificate-fetch-failed {
       type uint32;
     }
     leaf swgauth-certificate-fetched {
       type uint32;
     }
   }
   grouping user-group-debug-counters-block {
     leaf user-group-debug-counters-title {
       type string;
       description
         "User group debug counters";
     }
     list user-group-debug-counters-list {
       description
         "User group debug counters list";
       leaf user-group-debug-counter-name {
         type string;
       }
       leaf user-group-debug-counter-value {
         type uint32;
       }
     }
   }
   grouping authentication-table-counter-block {
     leaf total-auth-count {
       type uint32;
       description
         "Total count of authentication table records";
     }
     list domain_counter {
       leaf logical-domain {
         type string;
         description
           "Logical System";
       }
       leaf total-lsys-auth-count {
         type uint32;
         description
           "Total count of authentication table records in lsys";
       }
       leaf domain-name {
         type string;
         description
           "Domain name of auth entry";
       }
       leaf total-domain-count {
         type uint32;
         description
           "Num of auth entry for some domain";
       }
       leaf ad-count {
         type uint32;
         description
           "Num of ad auth entry for some domain";
       }
       leaf cp-count {
         type uint32;
         description
           "Num of cp auth entry for some domain";
       }
       leaf jims-count {
         type uint32;
         description
           "Num of jims auth entry for some domain";
       }
       leaf valid-count {
         type uint32;
         description
           "Num of valid state auth entry for some domain";
       }
       leaf pending-count {
         type uint32;
         description
           "Num of pending state auth entry for some domain";
       }
       leaf invalid-count {
         type uint32;
         description
           "Num of invalid state auth entry for some domain";
       }
       leaf init-count {
         type uint32;
         description
           "Num of init staste auth entry for some domain";
       }
     }
   }
   grouping authentication-table-by-address-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-all-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-all-by-group-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-all-by-user-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-cp-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-cp-by-group-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-cp-by-user-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ad-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ad-by-group-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ad-by-user-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ims-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ims-by-group-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping authentication-table-ims-by-user-block {
     list ad-auth-table {
       description
         "Information of the ad authentication table";
       leaf logical-domain {
         type string;
         description
           "Logical System";
       }
       leaf domain {
         type string;
         description
           "Domain name";
       }
       leaf total-count {
         type uint32;
         description
           "Total count of ad authentication table records";
       }
       list ad-authentication-info {
         leaf source-ip {
           type jt:ipaddr;
           description
             "Source address";
         }
         leaf-list user-name {
           type string;
           description
             "Name of the user";
         }
         leaf state {
           type string;
           description
             "State";
         }
         container ref-group-name-list {
           description
             "Information of all interested group name";
           leaf-list ref-group-name {
             type string;
             description
               "Name of the interested group";
           }
         }
         leaf src-type {
           type string;
           description
             "Source";
         }
         leaf start-date {
           type string;
           description
             "Date user gained access";
         }
         leaf start-time {
           type string;
           description
             "Time user gained access";
         }
         leaf last-time {
           type string;
           description
             "Last updated timestamp(local display)";
         }
         leaf age-time {
           type string;
           description
             "Age time of user's access";
         }
         leaf forced-age-time {
           type string;
           description
             "Forced Age time of user's access";
         }
         container group-name-list {
           description
             "Information of all group name";
           leaf-list group-name {
             type string;
             description
               "Name of the group";
           }
         }
       }
     }
   }
   grouping domain-controller-status-block {
     list domain-controller-info {
       description
         "Domain controller info";
       leaf domain {
         type string;
         description
           "Domain name";
       }
       list domain-controller {
         description
           "Domain-controller information";
         leaf dc-name {
           type string;
         }
         leaf address {
           type jt:ipaddr;
           description
             "Name of the address";
         }
         leaf status {
           type string;
           description
             "Status";
         }
         leaf reason {
           type string;
           description
             "Reason";
         }
       }
     }
   }
   grouping ip-user-mapping-statistics-block {
     list ip-user-mapping-statistics-per-domain {
       description
         "Ip-user-mapping statistics per domain";
       leaf domain {
         type string;
         description
           "Domain name";
       }
       list ip-user-mapping-statistics-per-dc {
         description
           "Ip-user-mapping statistics per domain controller";
         leaf host {
           type jt:ipaddr;
           description
             "Address of host";
         }
         leaf initial-eventlog-timespan {
           type uint32;
           description
             "Event log timespan";
         }
         leaf eventlog-scan-interval {
           type uint32;
           description
             "Event log scan interval";
         }
         leaf total-log-query-number {
           type uint32;
           description
             "Total log query number";
         }
         leaf failed-log-query-number {
           type uint32;
           description
             "Failed log query number";
         }
         leaf log-read-number {
           type uint32;
           description
             "Log read number";
         }
         leaf latest-timestamp {
           type string;
           description
             "Latest timestamp";
         }
       }
     }
   }
   grouping ip-user-probe-statistics-block {
     list ip-user-probe-statistics-per-domain {
       description
         "Ip-user-probe-statistics-per-domain";
       leaf domain {
         type string;
         description
           "Domain name";
       }
       leaf total-user-probe-number {
         type uint32;
         description
           "Total user probe number";
       }
       leaf failed-user-probe-number {
         type uint32;
         description
           "Failed user probe number";
       }
     }
   }
   grouping user-group-mapping-statistics-block {
     list user-group-mapping-statistics-per-domain {
       description
         "User-group-mapping statistics per domain";
       leaf domain {
         type string;
         description
           "Domain name";
       }
       list user-group-mapping-statistics-per-server {
         description
           "User-group-mapping status per server";
         leaf host {
           type jt:ipaddr;
           description
             "Address of host";
         }
         leaf port {
           type uint32;
           description
             "Port of server";
         }
         leaf total-query-number {
           type uint32;
           description
             "Total query number";
         }
         leaf failed-query-number {
           type uint32;
           description
             "Failed query number";
         }
       }
     }
   }
   grouping users-by-group-block {
     list domain-user-list {
       description
         "User list in AD";
       leaf domain {
         type string;
         description
           "Domain name";
       }
       leaf total-num {
         type uint32;
         description
           "Total num";
       }
       leaf user {
         type string;
         description
           "User";
       }
     }
   }
   grouping groups-by-user-block {
     list domain-group-list {
       description
         "Group list in AD";
       leaf domain {
         type string;
         description
           "Domain name";
       }
       leaf total-num {
         type uint32;
         description
           "Total num";
       }
       container domain-group {
         leaf group {
           type string;
           description
             "Group";
         }
       }
       container domain-interested-group {
         leaf interested-group {
           type string;
           description
             "Group referenced by policy";
         }
       }
     }
   }
   grouping user-group-mapping-status-block {
     list user-group-mapping-status-per-domain {
       description
         "User-group-mapping status per domain";
       leaf domain {
         type string;
         description
           "Domain name";
       }
       list user-group-mapping-status-per-server {
         description
           "User-group-mapping status per server";
         leaf host {
           type jt:ipaddr;
           description
             "Address of host";
         }
         leaf port {
           type uint32;
           description
             "Port of server";
         }
         leaf last-query-status {
           type string;
           description
             "Last query status";
         }
         leaf last-query-time {
           type string;
           description
             "Last query time";
         }
       }
     }
   }
   grouping fetching-status-block {
     leaf status {
       type string;
       description
         "Status";
     }
   }
   grouping periodic-fetching-status-block {
     leaf information {
       type string;
       description
         "Periodic fetching inforamtion";
     }
     list domain-group-list-status {
       description
         "Domain group list";
       leaf domain-name {
         type string;
         description
           "Domain name of auth entry";
       }
       leaf group {
         type string;
         description
           "Group";
       }
       leaf status {
         type string;
         description
           "Status";
       }
     }
   }
   grouping periodic-fetching-configuration-block {
     leaf timestamp {
       type string;
       description
         "Periodic fetching timestamp";
     }
     list domain-group-list-configuration {
       description
         "Fetch domain group list configuration";
       leaf domain-name {
         type string;
         description
           "Domain name of auth entry";
       }
       leaf group {
         type string;
         description
           "Group";
       }
     }
   }
   grouping refreshing-status-block {
     leaf status {
       type string;
       description
         "Status";
     }
   }
   grouping cp-user-query-statistics-block {
     leaf authentication-source {
       type string;
       description
         "Authentication source";
     }
     leaf web-server {
       type string;
       description
         "Web server address";
     }
     leaf access-token {
       type string;
       description
         "Access token";
     }
     leaf query-sent-number {
       type uint32;
       description
         "CleaPass query sent number";
     }
     leaf response-recv-number {
       type uint32;
       description
         "Total query response received number";
     }
     leaf error-response-number {
       type uint32;
       description
         "Error query response received number";
     }
     leaf last-response-time {
       type string;
       description
         "Last response time";
     }
   }
   grouping cp-user-query-status-block {
     leaf authentication-source {
       type string;
       description
         "Authentication source";
     }
     leaf web-server {
       type string;
       description
         "Web server address";
     }
     leaf server-status {
       type string;
       description
         "Web server status";
     }
     leaf connection-number {
       type uint32;
       description
         "Current connection number";
     }
   }
   grouping device-identity-table-all-block {
     list device-id-table {
       description
         "Information of the device identity table";
       leaf logical-domain {
         type string;
         description
           "Logical System";
       }
       leaf domain {
         type string;
         description
           "Domain name";
       }
       leaf total-device-count {
         type uint32;
         description
           "Total count of device identity table records";
       }
       list device-info {
         leaf device-source-ip {
           type string;
           description
             "Source ip address";
         }
         leaf-list device-name {
           type string;
           description
             "Name of the device";
         }
         container device-group-name-list {
           description
             "Device group list";
           leaf-list device-group-name {
             type string;
             description
               "Name of the device group";
           }
         }
         container ref-profile-list {
           description
             "Information of referred profiles";
           leaf-list ref-profile {
             type string;
             description
               "Name of the profile";
           }
         }
         container dev-param-list {
           description
             "Information of other attributes";
           leaf-list dev-param {
             type string;
             description
               "Device parameters";
           }
         }
       }
     }
   }
   grouping device-identity-table-by-address-block {
     list device-id-table {
       description
         "Information of the device identity table";
       leaf logical-domain {
         type string;
         description
           "Logical System";
       }
       leaf domain {
         type string;
         description
           "Domain name";
       }
       leaf total-device-count {
         type uint32;
         description
           "Total count of device identity table records";
       }
       list device-info {
         leaf device-source-ip {
           type string;
           description
             "Source ip address";
         }
         leaf-list device-name {
           type string;
           description
             "Name of the device";
         }
         container device-group-name-list {
           description
             "Device group list";
           leaf-list device-group-name {
             type string;
             description
               "Name of the device group";
           }
         }
         container ref-profile-list {
           description
             "Information of referred profiles";
           leaf-list ref-profile {
             type string;
             description
               "Name of the profile";
           }
         }
         container dev-param-list {
           description
             "Information of other attributes";
           leaf-list dev-param {
             type string;
             description
               "Device parameters";
           }
         }
       }
     }
   }
   grouping device-identity-table-by-device-id-block {
     list device-id-table {
       description
         "Information of the device identity table";
       leaf logical-domain {
         type string;
         description
           "Logical System";
       }
       leaf domain {
         type string;
         description
           "Domain name";
       }
       leaf total-device-count {
         type uint32;
         description
           "Total count of device identity table records";
       }
       list device-info {
         leaf device-source-ip {
           type string;
           description
             "Source ip address";
         }
         leaf-list device-name {
           type string;
           description
             "Name of the device";
         }
         container device-group-name-list {
           description
             "Device group list";
           leaf-list device-group-name {
             type string;
             description
               "Name of the device group";
           }
         }
         container ref-profile-list {
           description
             "Information of referred profiles";
           leaf-list ref-profile {
             type string;
             description
               "Name of the profile";
           }
         }
         container dev-param-list {
           description
             "Information of other attributes";
           leaf-list dev-param {
             type string;
             description
               "Device parameters";
           }
         }
       }
     }
   }
   grouping device-identity-table-by-group-block {
     list device-id-table {
       description
         "Information of the device identity table";
       leaf logical-domain {
         type string;
         description
           "Logical System";
       }
       leaf domain {
         type string;
         description
           "Domain name";
       }
       leaf total-device-count {
         type uint32;
         description
           "Total count of device identity table records";
       }
       list device-info {
         leaf device-source-ip {
           type string;
           description
             "Source ip address";
         }
         leaf-list device-name {
           type string;
           description
             "Name of the device";
         }
         container device-group-name-list {
           description
             "Device group list";
           leaf-list device-group-name {
             type string;
             description
               "Name of the device group";
           }
         }
         container ref-profile-list {
           description
             "Information of referred profiles";
           leaf-list ref-profile {
             type string;
             description
               "Name of the profile";
           }
         }
         container dev-param-list {
           description
             "Information of other attributes";
           leaf-list dev-param {
             type string;
             description
               "Device parameters";
           }
         }
       }
     }
   }
   grouping jims-query-statistics-block {
     list jims-query-statistics-per-server {
       description
         "Identity management query statistics per server";
       leaf server-type {
         type string;
         description
           "Identity management server type";
       }
       leaf server-address {
         type string;
         description
           "Identity management server address";
       }
       leaf batch-queries-sent {
         type uint32;
         description
           "Batch queries sent";
       }
       leaf batch-queries-returned {
         type uint32;
         description
           "Total number of received batch query responses";
       }
       leaf batch-query-error-received {
         type uint32;
         description
           "Error number of received batch query responses";
       }
       leaf batch-last-response {
         type string;
         description
           "Last response time of batch query";
       }
       leaf auth-entry-lookup-queries-sent {
         type uint32;
         description
           "Total number of batch queries sent";
       }
       leaf auth-entry-lookup-queries-returned {
         type uint32;
         description
           "Total number of received ip query responses";
       }
       leaf auth-entry-lookup-query-errors-encountered {
         type uint32;
         description
           "Error number of received ip query responses";
       }
       leaf auth-entry-lookup-last-response {
         type string;
         description
           "Last response time of ip query";
       }
       leaf auth-entry-lookup-time-avg {
         type uint32;
         description
           "Auth entry lookup time, average";
       }
       leaf auth-entry-lookup-time-max {
         type uint32;
         description
           "Auth entry lookup time, max";
       }
       leaf cert-revocation-req-sent {
         type uint32;
         description
           "Certificate revocation requests sent";
       }
       leaf cert-revocation-resp-recvd {
         type uint32;
         description
           "Certificate revocation responses received";
       }
       leaf certs-revoked {
         type uint32;
         description
           "Certificates revoked";
       }
     }
   }
   grouping jims-query-status-block {
     list jims-query-status-per-server {
       description
         "Identity management query status per server";
       leaf server-type {
         type string;
         description
           "Identity management server type";
       }
       leaf fqdn-name {
         type string;
         description
           "Identity management FQDN name";
       }
       leaf server-address {
         type string;
         description
           "Identity management server address";
       }
       leaf server-port {
         type uint32;
         description
           "Identity management server port";
       }
       leaf source {
         type string;
         description
           "Source address";
       }
       leaf interface-name {
         type string;
         description
           "Interface name";
       }
       leaf routing-instance {
         type string;
         description
           "Routing instance name";
       }
       leaf connect-method {
         type string;
         description
           "Connection method";
       }
       leaf connect-status {
         type string;
         description
           "Server status";
       }
       leaf recv-status-msg {
         type string;
         description
           "Last received status message";
       }
       leaf token-string {
         type string;
         description
           "Access token";
       }
       leaf token-expire-time {
         type string;
         description
           "Token expire time";
       }
     }
   }
   grouping jims-more-info-block {
     list jims-more-info-per-server {
       description
         "Identity management query status per server";
       leaf server-type {
         type string;
         description
           "Identity management server type";
       }
       leaf server-address {
         type string;
         description
           "Identity management server address";
       }
       leaf online-to-offline-number {
         type uint32;
         description
           "Number of switching from online to offline";
       }
     }
   }
   grouping jims-validator-query-statistics-block {
     list jims-validator-query-statistics-per-server {
       description
         "Identity management jims validator query statistics per server";
       leaf server-address {
         type string;
         description
           "Identity management server address";
       }
       leaf validator-query-sent-number {
         type uint32;
         description
           "Validator query sent number";
       }
       leaf validator-query-response-recv-number {
         type uint32;
         description
           "Total number of received validator query responses";
       }
       leaf validator-query-error-response-number {
         type uint32;
         description
           "Error number of received validator query responses";
       }
       leaf group-query-sent-number {
         type uint32;
         description
           "Group query sent number";
       }
       leaf group-query-response-recv-number {
         type uint32;
         description
           "Total number of received group query responses";
       }
       leaf group-query-error-response-number {
         type uint32;
         description
           "Error number of received group query responses";
       }
     }
   }
   grouping jims-validator-query-status-block {
     list jims-validator-query-status-per-server {
       description
         "Identity management jims validator query status per server";
       leaf server-address {
         type string;
         description
           "Identity management server address";
       }
       leaf server-port {
         type uint32;
         description
           "Identity management server port";
       }
       leaf connect-method {
         type string;
         description
           "Connection method";
       }
       leaf connect-status {
         type string;
         description
           "Server status";
       }
       leaf recv-status-msg {
         type string;
         description
           "Last received status message";
       }
       leaf token-string {
         type string;
         description
           "Access token";
       }
       leaf token-expire-time {
         type string;
         description
           "Token expire time";
       }
     }
   }
   grouping ld-jims-query-statistics-block {
     leaf ld-jims-query-server-name {
       type string;
       description
         "Logical domain server name inforamtion";
     }
     list ld-jims-query-statistics-per-server {
       description
         "Logical domain identity management query statistics per server";
       leaf server-type {
         type string;
         description
           "Identity management server type";
       }
       leaf server-address {
         type string;
         description
           "Identity management server address";
       }
       leaf batch-queries-sent {
         type uint32;
         description
           "Batch queries sent";
       }
       leaf batch-queries-returned {
         type uint32;
         description
           "Total number of received batch query responses";
       }
       leaf batch-query-error-received {
         type uint32;
         description
           "Error number of received batch query responses";
       }
       leaf batch-last-response {
         type string;
         description
           "Last response time of batch query";
       }
       leaf auth-entry-lookup-queries-sent {
         type uint32;
         description
           "Total number of batch queries sent";
       }
       leaf auth-entry-lookup-queries-returned {
         type uint32;
         description
           "Total number of received ip query responses";
       }
       leaf auth-entry-lookup-query-errors-encountered {
         type uint32;
         description
           "Error number of received ip query responses";
       }
       leaf auth-entry-lookup-last-response {
         type string;
         description
           "Last response time of ip query";
       }
       leaf auth-entry-lookup-time-avg {
         type uint32;
         description
           "Auth entry lookup time, average";
       }
       leaf auth-entry-lookup-time-max {
         type uint32;
         description
           "Auth entry lookup time, max";
       }
       leaf cert-revocation-req-sent {
         type uint32;
         description
           "Certificate revocation requests sent";
       }
       leaf cert-revocation-resp-recvd {
         type uint32;
         description
           "Certificate revocation responses received";
       }
       leaf certs-revoked {
         type uint32;
         description
           "Certificates revoked";
       }
     }
   }
   grouping ld-jims-query-status-block {
     leaf ld-query-server-name {
       type string;
       description
         "Logical domain server name inforamtion";
     }
     list ld-jims-query-status-per-server {
       description
         "Logical domain identity management query status per server";
       leaf server-type {
         type string;
         description
           "Identity management server type";
       }
       leaf server-address {
         type string;
         description
           "Identity management server address";
       }
       leaf server-port {
         type uint32;
         description
           "Identity management server port";
       }
       leaf connect-method {
         type string;
         description
           "Connection method";
       }
       leaf connect-status {
         type string;
         description
           "Server status";
       }
       leaf recv-status-msg {
         type string;
         description
           "Last received status message";
       }
       leaf token-string {
         type string;
         description
           "Access token";
       }
       leaf token-expire-time {
         type string;
         description
           "Token expire time";
       }
     }
   }
   grouping forward-header-lookup-statistics-block {
     leaf ffhl-sessions-engaged {
       type uint32;
       description
         "Forward header lookup sessions engaged";
     }
     leaf ffhl-sessions-with-ffh {
       type uint32;
       description
         "Forward header lookup sessions with forward header";
     }
     leaf ffhl-sessions-with-untrusted-ffh {
       type uint32;
       description
         "Forward header lookup sessions with untrusted forward header";
     }
     leaf ffhl-sessions-used-ffh-for-identity {
       type uint32;
       description
         "Forward header lookup sessions used forward header for identity";
     }
   }
 }
