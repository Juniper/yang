/*
 * Copyright (c) 2026 Juniper Networks, Inc.
 * All rights reserved.
 */
 module junos-es-rpc-firewall {
   namespace "http://yang.juniper.net/junos-es/rpc/firewall";

   prefix firewall;

   import junos-common-types {
     prefix jt;
     revision-date 2026-01-01;
   }

   organization "Juniper Networks, Inc.";

   contact "yang-support@juniper.net";

   description "Junos RPC YANG module for firewall command(s)";

   revision 2026-01-01 {
     description "Junos: 26.2R1.7";
   }

   rpc get-firewall-information {
     description "Show firewall information";
     input {
       uses command-forwarding;
       leaf get-firewall-information {
         description "Display extensive firewall output";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
       leaf terse {
         description "Show filter names only";
         type empty;
       }
       leaf detailed {
         description "Show all filters with their errorred bindpoints";
         type empty;
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-counter-information {
     description "Counter name";
     input {
       uses command-forwarding;
       leaf countername {
         description "Counter name";
         type string;
         mandatory true;
       }
       leaf filter {
         description "Filter name";
         type string;
         mandatory true;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-filter-information {
     description "Filter name";
     input {
       uses command-forwarding;
       leaf filtername {
         description "Filter name";
         type string;
         mandatory true;
       }
       leaf counter {
         description "Counter name";
         type string;
       }
       leaf detailed {
         description "Show all filters with their errorred bindpoints";
         type empty;
       }
       leaf application {
         description "Owner application";
         type enumeration {
           enum "cfm" {
             description "Statistics for implicit filters for CFM";
           }
           enum "rmps" {
             description "Statistics for implicit filters for RMPS";
           }
           enum "eswd" {
             description "Statistics for implicit filters for eswd";
           }
           enum "lsp" {
             description "Statistics for implicit filters for lsp";
           }
           enum "routing" {
             description "Statistics for implicit bgp flowspec filters for routing";
           }
           enum "ecmp-tracer" {
             description "Statistics for implicit filters for ecmp-tracer debug tool";
           }
           enum "ecmp-tracer-server" {
             description "Statistics for implicit filters for ecmp-tracer JET clients";
           }
           enum "dot1xd" {
             description "Statistics for implicit filters for dot1xd";
           }
           enum "ppmd" {
             description "Statistics for implicit filters for Periodic packet Management Daemon";
           }
           enum "cosd" {
             description "Statistics for implicit filters for cosd";
           }
           enum "l2cpd" {
             description "Statistics for implicit filters for l2cpd";
           }
           enum "p4-switch" {
             description "Statistics for implicit filters for p4-switch";
           }
           enum "jdhcpd" {
             description "Statistics for implicit filters for jdhcpd";
           }
         }
       }
       choice daemon-select {
         case logical-system {
         }
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-filter-version {
     description "Show filter version installed";
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-filter-regex-information {
     description "Show filter using regular expression";
     input {
       leaf filtername {
         description "Regular expression of filter names";
         type jt:regular-expression;
       }
       choice daemon-select {
         case logical-system {
           leaf logical-system {
             description "Name of logical system, or 'all'";
             type string {
             }
           }
         }
       }
     }
     output {
       choice output-tags {
         case actual-tag {
           container firewall-information {
             uses firewall-information-block;
           }
         }
         case multichassis-tag {
           container multi-routing-engine-results {
             list multi-routing-engine-item {
               leaf re-name {
                 type string;
               }
               choice output-tags {
                 case actual-tag {
                   container firewall-information {
                     uses firewall-information-block;
                   }
                 }
               }
             }
           }
         }
       }
     }
   }
   rpc get-firewall-log-information {
     description "Show log entries for firewall activity";
     input {
       leaf get-firewall-log-detailed-information {
         description "Display detailed output";
         type empty;
       }
       leaf interface {
         description "Interface name";
         type string;
       }
       choice daemon-select {
         case logical-system {
           leaf logical-system {
             description "Name of logical system, or 'all'";
             type string {
             }
           }
         }
       }
     }
     output {
       choice output-tags {
         case actual-tag {
           container firewall-log-information {
             uses firewall-log-information-block;
           }
         }
         case multichassis-tag {
           container multi-routing-engine-results {
             list multi-routing-engine-item {
               leaf re-name {
                 type string;
               }
               choice output-tags {
                 case actual-tag {
                   container firewall-log-information {
                     uses firewall-log-information-block;
                   }
                 }
               }
             }
           }
         }
       }
     }
   }
   rpc get-firewall-prefix-action-information {
     description "Show prefix-action statistics for a filter";
     input {
       leaf filter {
         description "Filter name";
         type string;
         mandatory true;
       }
       leaf prefix-action {
         description "Prefix-action name";
         type string;
         mandatory true;
       }
       leaf from {
         description "Starting counter or policer";
         default "0";
         type union {
           type string {
             pattern "<.*>|$.*";
           }
           type uint32 {
             range "0 .. 65535";
           }
         }
       }
       leaf to {
         description "Ending counter or policer";
         default "65535";
         type union {
           type string {
             pattern "<.*>|$.*";
           }
           type uint32 {
             range "0 .. 65535";
           }
         }
       }
       choice daemon-select {
         case logical-system {
           leaf logical-system {
             description "Name of logical system, or 'all'";
             type string {
             }
           }
         }
       }
     }
     output {
       choice output-tags {
         case actual-tag {
           container firewall-prefix-action-information {
             uses firewall-prefix-action-information-block;
           }
         }
         case multichassis-tag {
           container multi-routing-engine-results {
             list multi-routing-engine-item {
               leaf re-name {
                 type string;
               }
               choice output-tags {
                 case actual-tag {
                   container firewall-prefix-action-information {
                     uses firewall-prefix-action-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping firewall-information-block {
     list filter-information {
       key "filter-name";
       description
         "Details of a firewall filter";
       leaf filter-name {
         type string;
         description
           "Name of filter";
       }
       leaf user-plane-name {
         type string;
         description
           "Name of the User Plane";
       }
       container error-status {
         leaf status {
           type string;
           description
             "Error status of the filter";
         }
       }
       list bind-error-status {
         leaf-list bind-name {
           type string;
           description
             "Error status of the filter bind point";
         }
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list policer {
         key "policer-name";
         description
           "Policer information";
         leaf policer-name {
           type string;
           description
             "Name of this policer";
         }
         leaf byte-count {
           type uint64;
           description
             "Bytes counted";
         }
         leaf packet-count {
           type uint64;
           description
             "Packets counted";
         }
       }
       list enhanced-hierarchical-policer {
         description
           "Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list user-plane-filter-information {
       key "filter-name";
       description
         "Details of a user-plane firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
     list subscribers-filter-information {
       key "filter-name";
       description
         "Details of subscribers firewall filter";
       leaf filter-name {
         type string;
         description
           "Name of filter";
       }
       leaf user-plane-name {
         type string;
         description
           "Name of the User Plane";
       }
       list counter {
         key "counter-name";
         description
           "Counter information";
         leaf counter-name {
           type string;
           description
             "Counter name";
         }
         leaf byte-count {
           type uint64;
           description
             "Bytes counted";
         }
         leaf packet-count {
           type uint64;
           description
             "Packets counted";
         }
       }
       list enhanced-hierarchical-policer-userplane {
         description
           "Enhanced Hierarchical Policer information";
         leaf policer-name {
           type string;
           description
             "Name of this policer";
         }
         leaf byte-count-high {
           type uint64;
           description
             "Bytes counted";
         }
         leaf packet-count-high {
           type uint64;
           description
             "Packets counted";
         }
         leaf byte-count-medium-high {
           type uint64;
           description
             "Bytes counted";
         }
         leaf packet-count-medium-high {
           type uint64;
           description
             "Packets counted";
         }
         leaf byte-count-medium-low {
           type uint64;
           description
             "Bytes counted";
         }
         leaf packet-count-medium-low {
           type uint64;
           description
             "Packets counted";
         }
         leaf byte-count-low {
           type uint64;
           description
             "Bytes counted";
         }
         leaf packet-count-low {
           type uint64;
           description
             "Packets counted";
         }
         leaf packet-count {
           type uint64;
           description
             "Packets counted";
         }
         leaf byte-count {
           type uint64;
           description
             "Bytes counted";
         }
       }
       list filter-version {
         key "filter-name";
         description
           "Filter version information";
         leaf filter-name {
           type string;
           description
             "Name of filter";
         }
         leaf version {
           type uint32;
           description
             "Filter version";
         }
       }
     }
   }
   grouping firewall-log-information-block {
     list log-information {
       key "filter-name";
       description
         "Details of a single firewall log entry";
       leaf time {
         type string;
         description
           "Time of log";
       }
       leaf filter-name {
         type string;
         description
           "Name of filter";
       }
       leaf action-name {
         type string;
         description
           "Filter action";
       }
       leaf interface-name {
         type string;
         description
           "Name of interface";
       }
       leaf protocol-name {
         type string;
         description
           "Name of protocol";
       }
       leaf source-address {
         type string;
         description
           "Source address";
       }
       leaf destination-address {
         type string;
         description
           "Destination address";
       }
       leaf packet-length {
         type int32;
         description
           "Packet length";
       }
       leaf icmp-type {
         type int32;
         description
           "ICMP type";
       }
       leaf icmp-code {
         type int32;
         description
           "ICMP code";
       }
       leaf hex-dump-line {
         type string;
         description
           "Packet in Hex format";
       }
       leaf hex-dump-line1 {
         type string;
         description
           "Packet in Hex format";
       }
       leaf hex-dump-line2 {
         type string;
         description
           "Packet in Hex format";
       }
       leaf hex-dump-line3 {
         type string;
         description
           "Packet in Hex format";
       }
       leaf hex-dump-line4 {
         type string;
         description
           "Packet in Hex format";
       }
       leaf hex-dump-line5 {
         type string;
         description
           "Packet in Hex format";
       }
       leaf hex-dump-line6 {
         type string;
         description
           "Packet in Hex format";
       }
       leaf hex-dump-line7 {
         type string;
         description
           "Packet in Hex format";
       }
     }
   }
   grouping firewall-prefix-action-information-block {
     leaf filter-name {
       type string;
       description
         "Name of filter";
     }
     list counter {
       key "counter-name";
       description
         "Counter information";
       leaf counter-name {
         type string;
         description
           "Counter name";
       }
       leaf byte-count {
         type uint64;
         description
           "Bytes counted";
       }
       leaf packet-count {
         type uint64;
         description
           "Packets counted";
       }
     }
     list policer {
       key "policer-name";
       description
         "Policer information";
       leaf policer-name {
         type string;
         description
           "Name of this policer";
       }
       leaf byte-count {
         type uint64;
         description
           "Bytes counted";
       }
       leaf packet-count {
         type uint64;
         description
           "Packets counted";
       }
     }
   }
 }
