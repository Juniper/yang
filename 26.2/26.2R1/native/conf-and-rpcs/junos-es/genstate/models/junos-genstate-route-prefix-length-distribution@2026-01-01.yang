module junos-genstate-route-prefix-length-distribution {
   yang-version 1;
   namespace "http://yang.juniper.net/junos/genstate/route-prefix-length-distribution";
   prefix jgrpld;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for route-prefix-length-distribution.

      Copyright (c) 2026 Juniper Networks, Inc.
      All rights reserved.";

   revision 2026-01-01 {
     description "Junos: 26.2R1.7";
   }

   grouping route-prefix-length-distribution-top {
     description
       "Top-level grouping";
     container route-prefix-length-distribution {
       description
         "Top-level container";
       list route-table {
         key "table-name";
         leaf table-name {
           type string;
           description
             "Unicast routing table";
         }
         list rt-prefix-dist {
           key "rt-prefix-length";
           leaf rt-prefix-length {
             type string;
           }
           leaf rt-prefix-count {
             type int32;
           }
         }
       }
     }
   }
   augment "/jgs:genstate" {
     description
       "Adds route-prefix-length-distribution container to top-level 
       genstate container";
     uses route-prefix-length-distribution-top;
   }
 }
