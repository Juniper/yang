module junos-genstate-mpls-abstract-hop-membership-information {
   yang-version 1;
   namespace "http://yang.juniper.net/junos/genstate/mpls-abstract-hop-membership-information";
   prefix jgmahmi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mpls-abstract-hop-membership-information.

      Copyright (c) 2026 Juniper Networks, Inc.
      All rights reserved.";

   revision 2026-01-01 {
     description "Junos: 26.2R1.7";
   }

   grouping mpls-abstract-hop-membership-information-top {
     description
       "Top-level grouping";
     container mpls-abstract-hop-membership-information {
       description
         "Top-level container";
       list mpls-abstract-hop-membership {
         key "abstract-hop-name";
         leaf abstract-hop-name {
           type string;
         }
         container mpls-abstract-hop-credibility-table {
           list mpls-abstract-hop-credibility-info {
             key "abstract-hop-credibility";
             leaf abstract-hop-credibility {
               type int32;
             }
             container mpls-abstract-hop-member-table {
               leaf-list member-address {
                 type jt:ipaddr;
               }
             }
           }
         }
       }
     }
   }
   augment "/jgs:genstate" {
     description
       "Adds mpls-abstract-hop-membership-information container to top-level
       genstate container";
     uses mpls-abstract-hop-membership-information-top;
   }
 }
