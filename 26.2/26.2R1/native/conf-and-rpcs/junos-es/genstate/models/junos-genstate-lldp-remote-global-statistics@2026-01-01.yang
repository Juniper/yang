module junos-genstate-lldp-remote-global-statistics {
   yang-version 1;
   namespace "http://yang.juniper.net/junos/genstate/lldp-remote-global-statistics";
   prefix jglrgs;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for lldp-remote-global-statistics.

      Copyright (c) 2026 Juniper Networks, Inc.
      All rights reserved.";

   revision 2026-01-01 {
     description "Junos: 26.2R1.7";
   }

   grouping lldp-remote-global-statistics-top {
     description
       "Top-level grouping";
     container lldp-remote-global-statistics {
       description
         "Top-level container";
       leaf lldp-last-change-time {
         type string;
         description
           "LLDP last change time";
       }
       leaf lldp-inserts {
         type uint32;
         description
           "LLDP inserts";
       }
       leaf lldp-deletes {
         type uint32;
         description
           "LLDP deletes";
       }
       leaf lldp-drops {
         type uint32;
         description
           "LLDP drops";
       }
       leaf lldp-ageouts {
         type uint32;
         description
           "LLDP ageouts";
       }
       list lldp-remote-global-stats {
         leaf lldp-last-change-time {
           type uint32;
           description
             "LLDP last change time";
         }
         leaf lldp-inserts {
           type uint32;
           description
             "LLDP inserts";
         }
         leaf lldp-deletes {
           type uint32;
           description
             "LLDP deletes";
         }
         leaf lldp-drops {
           type uint32;
           description
             "LLDP drops";
         }
         leaf lldp-ageouts {
           type uint32;
           description
             "LLDP ageouts";
         }
       }
     }
   }
   augment "/jgs:genstate" {
     description
       "Adds lldp-remote-global-statistics container to top-level genstate 
       container";
     uses lldp-remote-global-statistics-top;
   }
 }
