module junos-genstate-igmp-output-group-information {
   yang-version 1;
   namespace "http://yang.juniper.net/junos/genstate/igmp-output-group-information";
   prefix jgiogi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for igmp-output-group-information.

      Copyright (c) 2026 Juniper Networks, Inc.
      All rights reserved.";

   revision 2026-01-01 {
     description "Junos: 26.2R1.7";
   }

   grouping igmp-output-group-information-top {
     description
       "Top-level grouping";
     container igmp-output-group-information {
       description
         "Top-level container";
       list mgm-interface-output-groups {
         key "interface-name";
         leaf interface-name {
           type string;
           description
             "Name of interface";
         }
         list mgm-output-group {
           key "multicast-group-address";
           leaf multicast-group-address {
             type jt:ipaddr;
             description
               "Group address";
           }
           leaf mgm-group-mode-type {
             type string;
             description
               "Group operational mode (Include/Exclude).";
           }
           leaf multicast-source-address {
             type jt:ipaddr;
             description
               "Source address";
           }
           leaf mgm-group-input-interface {
             type string;
             description
               "Group input interface";
           }
         }
       }
     }
   }
   augment "/jgs:genstate" {
     description
       "Adds igmp-output-group-information container to top-level genstate 
       container";
     uses igmp-output-group-information-top;
   }
 }
