module junos-genstate-spring-te-lsp-information {
   yang-version 1;
   namespace "http://yang.juniper.net/junos/genstate/spring-te-lsp-information";
   prefix jgstli;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for spring-te-lsp-information.

      Copyright (c) 2026 Juniper Networks, Inc.
      All rights reserved.";

   revision 2026-01-01 {
     description "Junos: 26.2R1.7";
   }

   grouping spring-te-lsp-information-top {
     description
       "Top-level grouping";
     container spring-te-lsp-information {
       description
         "Top-level container";
       list spring-te-lsp {
         key "stl-lsp-name";
         description
           "SPRING Traffic-Engineered LSP";
         leaf stl-lsp-name {
           type string;
         }
         leaf stl-dest-address {
           type jt:ipaddr;
         }
         leaf stl-lsp-state {
           type string;
         }
       }
       container spring-te-lsp-counts {
         leaf stl-total {
           type uint32;
         }
         leaf stl-up {
           type uint32;
         }
         leaf stl-down {
           type uint32;
         }
         leaf stl-initializing {
           type uint32;
         }
       }
     }
   }
   augment "/jgs:genstate" {
     description
       "Adds spring-te-lsp-information container to top-level genstate 
       container";
     uses spring-te-lsp-information-top;
   }
 }
