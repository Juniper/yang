module junos-genstate-ospf3-interface-information {
   yang-version 1;
   namespace "http://yang.juniper.net/junos/genstate/ospf3-interface-information";
   prefix jgoii;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ospf3-interface-information.

      Copyright (c) 2026 Juniper Networks, Inc.
      All rights reserved.";

   revision 2026-01-01 {
     description "Junos: 26.2R1.7";
   }

   grouping ospf3-interface-information-top {
     description
       "Top-level grouping";
     container ospf3-interface-information {
       description
         "Top-level container";
       list ospf3-interface {
         key "interface-name ospf-area";
         leaf interface-name {
           type string;
           description
             "Name of interface";
         }
         leaf ospf-interface-state {
           type string;
         }
         leaf ospf-area {
           type string;
           description
             "Area ID";
         }
         leaf dr-id {
           type jt:ipaddr;
         }
         leaf bdr-id {
           type jt:ipaddr;
         }
         leaf neighbor-count {
           type int32;
           description
             "Number of neighbors on PIM interface";
         }
         leaf interface-address {
           type jt:ipaddr;
         }
         leaf prefix-length {
           type int32;
         }
         leaf virtual-link-transit-area {
           type jt:ipaddr;
           description
             "Virtual link transit area";
         }
         leaf virtual-link-destination {
           type string;
           description
             "Virtual link destination address";
         }
         leaf ospf3-interface-index {
           type int32;
         }
         leaf interface-type {
           type string;
         }
         leaf mtu {
           type int32;
           description
             "MTU along an interface";
         }
         leaf interface-cost {
           type int32;
           description
             "Cost associated with this interface";
         }
         leaf router-priority {
           type int32;
           description
             "Router priority used in DR election on broadcast or NBMA 
             interface";
         }
         leaf adj-count {
           type int32;
           description
             "Count of fully adjacent neighbors";
         }
         leaf ospf3-router-lsa-id {
           type int32;
         }
         leaf interface-secondary {
           type empty;
           description
             "OSPF interface is secondary";
         }
         leaf interface-flood-reduction {
           type empty;
           description
             "Flood reduction is enabled";
         }
         leaf passive {
           type string;
         }
         leaf dr-address {
           type jt:ipaddr;
           description
             "IP address of DR";
         }
         leaf bdr-address {
           type jt:ipaddr;
           description
             "IP address of BDR";
         }
         leaf hello-interval {
           type int32;
           description
             "Interval between two successive hellos";
         }
         leaf poll-interval {
           type int32;
         }
         leaf dead-interval {
           type int32;
         }
         leaf retransmit-interval {
           type int32;
         }
         leaf ospf-stub-type {
           type string;
           description
             "Stub type of area";
         }
         leaf ipsec-sa {
           type string;
         }
         leaf ospf-interface-protection-type {
           type string;
         }
         leaf ospf-interface-no-eligible-backup {
           type empty;
         }
         leaf igp-ldp-sync-state {
           type string;
           description
             "State of synchronization between Label Distribution Protocol 
             (LDP) and the interior gateway protocol (IGP)";
         }
         leaf igp-ldp-sync-last-change {
           type string;
           description
             "Time since the state of synchronization between Label 
             Distribution Protocol (LDP) and the interior gateway protocol 
             (IGP) last changed";
         }
         leaf igp-ldp-sync-reason {
           type string;
           description
             "Reason for the change in the state of synchronization between 
             Label Distribution Protocol (LDP) and the interior gateway 
             protocol (IGP)";
         }
         leaf igp-ldp-sync-holdtime {
           type string;
           description
             "Length of time during which the maximum metric is advertised 
             for an interface that is in the hold-down state because 
             synchronization was lost between Label Distribution Protocol 
             (LDP) and the interior gateway protocol (IGP)";
         }
         leaf igp-ldp-sync-timeleft {
           type int32;
           description
             "Remaining amount of time the interface will remain in the 
             hold-down state because synchronization was lost between Label
             Distribution Protocol (LDP) and the interior gateway protocol 
             (IGP)";
         }
         leaf interface-flood-list-count {
           type int32;
         }
         leaf flood-list-count {
           type int32;
         }
       }
     }
   }
   augment "/jgs:genstate" {
     description
       "Adds ospf3-interface-information container to top-level genstate 
       container";
     uses ospf3-interface-information-top;
   }
 }
