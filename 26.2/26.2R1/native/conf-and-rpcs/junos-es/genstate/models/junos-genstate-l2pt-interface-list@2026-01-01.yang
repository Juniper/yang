module junos-genstate-l2pt-interface-list {
   yang-version 1;
   namespace "http://yang.juniper.net/junos/genstate/l2pt-interface-list";
   prefix jglil;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for l2pt-interface-list.

      Copyright (c) 2026 Juniper Networks, Inc.
      All rights reserved.";

   revision 2026-01-01 {
     description "Junos: 26.2R1.7";
   }

   grouping l2pt-interface-list-top {
     description
       "Top-level grouping";
     container l2pt-interface-list {
       description
         "L2PT interface infomration";
       leaf tunnel-destination-mac {
         type string;
         description
           "DMAC of the tunneled packets";
       }
       list l2pt-interface-entry {
         key "interface-name";
         leaf interface-name {
           type string;
           description
             "Name of interface";
         }
         leaf protocols {
           type string;
           description
             "Protocols for which tunelling is enabled";
         }
       }
     }
   }
   augment "/jgs:genstate" {
     description
       "Adds l2pt-interface-list container to top-level genstate container";
     uses l2pt-interface-list-top;
   }
 }
