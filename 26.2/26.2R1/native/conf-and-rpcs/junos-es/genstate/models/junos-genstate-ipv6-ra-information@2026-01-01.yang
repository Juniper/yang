module junos-genstate-ipv6-ra-information {
   yang-version 1;
   namespace "http://yang.juniper.net/junos/genstate/ipv6-ra-information";
   prefix jgiri;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ipv6-ra-information.

      Copyright (c) 2026 Juniper Networks, Inc.
      All rights reserved.";

   revision 2026-01-01 {
     description "Junos: 26.2R1.7";
   }

   grouping ipv6-ra-information-top {
     description
       "Top-level grouping";
     container ipv6-ra-information {
       description
         "Top-level container";
       list ipv6-ra-interface {
         key "interface-name";
         leaf interface-name {
           type string;
           description
             "Name of interface";
         }
         leaf ipv6-ra-advertisements-sent {
           type int32;
           description
             "Number of router advertisements sent";
         }
         leaf ipv6-ra-advertisement-sent-time {
           type string;
           description
             "How long since the last router advertisement was sent";
         }
         leaf ipv6-ra-solicits-received {
           type int32;
           description
             "Number of router solicitations received";
         }
         leaf ipv6-ra-solicit-receive-time {
           type string;
           description
             "How long since the last router solicitation was received";
         }
         leaf ipv6-ra-solicits-sent {
           type int32;
           description
             "Number of router solicitations sent";
         }
         leaf ipv6-ra-solicit-sent-time {
           type string;
           description
             "How long since the last router solicitation was sent";
         }
         leaf ipv6-ra-advertisements-received {
           type int32;
           description
             "Number of router advertisements received";
         }
         leaf ipv6-ra-solicit-router-advertisement-unicast {
           type string;
           description
             "Enable forwarding IPv6 Solicited Router Advert as unicast";
         }
         leaf ipv6-ra-solicit-router-advertisement-preference {
           type string;
           description
             "Preference for Router Selection based on RA";
         }
         leaf ipv6-ra-passive-mode {
           type string;
           description
             "Passive mode";
         }
         container vrrp-group {
           leaf vrrp-group-id {
             type int32;
             description
               "Group ID of the configured VRRP group";
           }
           leaf vrrp-advertisements-sent {
             type int32;
             description
               "Number of advertisements sent";
           }
           leaf vrrp-advertisement-sent-time {
             type string;
             description
               "How long since the last advertisement was sent";
           }
           leaf vrrp-solicits-received {
             type int32;
             description
               "Number of router solicitations received";
           }
           leaf vrrp-advertisements-received {
             type int32;
             description
               "Number of advertisements received";
           }
         }
         list ipv6-ra-advertisement {
           key "ipv6-source-address";
           leaf ipv6-source-address {
             type jt:ipv6addr;
             description
               "Sender of the advertisement";
           }
           leaf ipv6-ra-time-since {
             type string;
             description
               "How long since the advertisement was received";
           }
           leaf ipv6-ra-managed-flag {
             type int32;
             description
               "Advertised managed flag";
           }
           leaf ipv6-ra-managed-flag-conflict {
             type int32;
             description
               "Conflict with the advertised managed flag";
           }
           leaf ipv6-ra-other-config-flag {
             type int32;
             description
               "Advertised other configuration flag";
           }
           leaf ipv6-ra-other-config-flag-conflict {
             type int32;
             description
               "Conflict with the advertised other configuration flag";
           }
           leaf ipv6-ra-link-mtu {
             type int32;
             description
               "Advertised link MTU";
           }
           leaf ipv6-ra-reachable-time {
             type int32;
             description
               "Advertised reachable time";
           }
           leaf ipv6-ra-reachable-time-conflict {
             type int32;
             description
               "Conflict with the advertised reachable time";
           }
           leaf ipv6-ra-default-lifetime {
             type int32;
             description
               "Advertised default lifetime flag";
           }
           leaf ipv6-ra-default-lifetime-conflict {
             type int32;
             description
               "Conflict with the advertised default lifetime flag";
           }
           leaf ipv6-ra-retransmit-timer {
             type int32;
             description
               "Advertised retransmit timer flag";
           }
           leaf ipv6-ra-retransmit-timer-conflict {
             type int32;
             description
               "Conflict with the advertised retransmit timer flag";
           }
           leaf ipv6-ra-current-hop-limit {
             type int32;
             description
               "Advertised current hop limit flag";
           }
           leaf ipv6-ra-current-hop-limit-conflict {
             type int32;
             description
               "Conflict with the advertised current hop limit flag";
           }
           list ipv6-ra-rdnss {
             key "ipv6-ra-rdnss-address";
             leaf ipv6-ra-rdnss-address {
               type jt:ipv6addr;
               description
                 "Advertised RDNSS address";
             }
             leaf ipv6-ra-rdnss-lifetime {
               type int32;
               description
                 "Advertised lifetime of the RDNSS address";
             }
             leaf ipv6-ra-rdnss-lifetime-conflict {
               type int32;
               description
                 "Conflict with the advertised lifetime of the RDNSS address";
             }
           }
           list ipv6-ra-prefix {
             key "ipv6-ra-prefix-address";
             leaf ipv6-ra-prefix-address {
               type jt:ipv6prefix;
               description
                 "Advertised prefix";
             }
             leaf ipv6-ra-prefix-valid-lifetime {
               type int32;
               description
                 "Advertised valid lifetime of the prefix";
             }
             leaf ipv6-ra-prefix-valid-lifetime-conflict {
               type int32;
               description
                 "Conflict with the advertised valid lifetime of the prefix";
             }
             leaf ipv6-ra-prefix-preferred-lifetime {
               type int32;
               description
                 "Advertised preferred lifetime of the prefix";
             }
             leaf ipv6-ra-prefix-preferred-lifetime-conflict {
               type int32;
               description
                 "Conflict with the advertised preferred lifetime of the 
                 prefix";
             }
             leaf ipv6-ra-prefix-on-link {
               type int32;
               description
                 "Advertised on-link flag of the prefix";
             }
             leaf ipv6-ra-prefix-on-link-conflict {
               type int32;
               description
                 "Conflict with the advertised on-link flag of the prefix";
             }
             leaf ipv6-ra-prefix-autonomous {
               type int32;
               description
                 "Advertised autonomous flag of the prefix";
             }
             leaf ipv6-ra-prefix-autonomous-conflict {
               type int32;
               description
                 "Conflict with the advertised autonomous flag of the prefix";
             }
           }
           list ipv6-ra-heard-dnssl {
             key "ipv6-ra-heard-dnssl-name";
             leaf ipv6-ra-heard-dnssl-name {
               type string;
               description
                 "Heard DNSSL suffix";
             }
             leaf ipv6-ra-heard-dnssl-lifetime {
               type int32;
               description
                 "Heard DNSSL lifetime";
             }
           }
           list ipv6-ra-route {
             key "ipv6-ra-route-address";
             leaf ipv6-ra-route-address {
               type string;
               description
                 "Route information received in router advertisements";
             }
             leaf ipv6-ra-route-prefix-length {
               type int32;
               description
                 "Prefix length";
             }
             leaf ipv6-ra-route-preference {
               type string;
               description
                 "Route preference received in router advertisements";
             }
             leaf ipv6-ra-route-lifetime {
               type string;
               description
                 "Route lifetime received in router advertisements";
             }
           }
         }
         list ipv6-ra-dnssl {
           key "ipv6-ra-dnssl-name";
           leaf ipv6-ra-dnssl-name {
             type string;
             description
               "Advertised DNSSL suffix";
           }
           leaf ipv6-ra-dnssl-lifetime {
             type int32;
             description
               "Advertised DNSSL lifetime";
           }
         }
         list ipv6-ra-configured-rdnss {
           key "ipv6-ra-configured-rdnss-address";
           leaf ipv6-ra-configured-rdnss-address {
             type jt:ipv6addr;
             description
               "Advertised RDNSS address";
           }
           leaf ipv6-ra-configured-rdnss-lifetime {
             type int32;
             description
               "Advertised lifetime of the RDNSS address";
           }
         }
         list ipv6-ra-config-route {
           key "ipv6-ra-config-route-address";
           leaf ipv6-ra-config-route-address {
             type string;
             description
               "Route information received in router advertisements";
           }
           leaf ipv6-ra-config-route-prefix-length {
             type int32;
             description
               "Prefix length";
           }
           leaf ipv6-ra-config-route-preference {
             type string;
             description
               "Route preference configured";
           }
           leaf ipv6-ra-config-route-lifetime {
             type string;
             description
               "Route lifetime configured";
           }
         }
         list ipv6-ra-config-nat {
           key "ipv6-ra-config-nat-address";
           leaf ipv6-ra-config-nat-address {
             type string;
             description
               "NAT prefix";
           }
           leaf ipv6-ra-config-nat-prefix-length {
             type int32;
             description
               "NAT prefix length";
           }
           leaf ipv6-ra-config-nat-lifetime {
             type string;
             description
               "NAT prefix lifetime";
           }
         }
       }
     }
   }
   augment "/jgs:genstate" {
     description
       "Adds ipv6-ra-information container to top-level genstate container";
     uses ipv6-ra-information-top;
   }
 }
