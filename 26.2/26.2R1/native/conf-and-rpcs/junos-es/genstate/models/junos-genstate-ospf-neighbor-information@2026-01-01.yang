module junos-genstate-ospf-neighbor-information {
   yang-version 1;
   namespace "http://yang.juniper.net/junos/genstate/ospf-neighbor-information";
   prefix jgoni;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ospf-neighbor-information.

      Copyright (c) 2026 Juniper Networks, Inc.
      All rights reserved.";

   revision 2026-01-01 {
     description "Junos: 26.2R1.7";
   }

   grouping ospf-neighbor-information-top {
     description
       "Top-level grouping";
     container ospf-neighbor-information {
       description
         "Information about OSPF neighbors in a routing instance";
       list ospf-neighbor {
         key "interface-name neighbor-id ospf-area";
         leaf neighbor-address {
           type jt:ipaddr;
           description
             "IP address of this neighbor";
         }
         leaf interface-name {
           type string;
           description
             "Name of interface";
         }
         leaf ospf-neighbor-state {
           type string;
         }
         leaf neighbor-id {
           type jt:ipaddr;
         }
         leaf neighbor-priority {
           type int32;
         }
         leaf activity-timer {
           type int32;
         }
         leaf ospf-area {
           type string;
           description
             "Area ID";
         }
         leaf options {
           type int32;
         }
         leaf dr-address {
           type jt:ipaddr;
           description
             "IP address of DR";
         }
         leaf bdr-address {
           type jt:ipaddr;
           description
             "IP address of BDR";
         }
         leaf neighbor-secondary {
           type empty;
           description
             "OSPF neighbor is on secondary interface";
         }
         leaf neighbor-up-time {
           type string;
           description
             "Time when neighbor came up";
         }
         leaf neighbor-adjacency-time {
           type string;
           description
             "Time when neighbor became adjacent";
         }
         leaf neighbor-last-out-of-band-resync-time {
           type string;
           description
             "Time since last successful oob-resync";
         }
         leaf neighbor-suppress-hello {
           type int32;
           description
             "Time when neighbor suppressed hellos";
         }
         leaf master-slave {
           type string;
         }
         leaf sequence-number {
           type int64;
           description
             "History event number";
         }
         leaf dbd-retransmit-time {
           type int32;
           description
             "Seconds until DBD is retransmitted";
         }
         leaf lsreq-retransmit-time {
           type int32;
           description
             "Seconds until LSREQ is retransmitted";
         }
         leaf lsreq-enqueued {
           type empty;
         }
         leaf lsreq-active {
           type empty;
         }
         list ospf-neighbor-topology {
           key "ospf-topology-name";
           description
             "OSPF topology specific neighbor information";
           leaf ospf-topology-name {
             type string;
             description
               "OSPF topology name";
           }
           leaf ospf-topology-id {
             type int32;
             description
               "OSPF topology id";
           }
           leaf ospf-neighbor-topology-state {
             type string;
             description
               "State of the neighbor in a topology";
           }
         }
       }
     }
   }
   augment "/jgs:genstate" {
     description
       "Adds ospf-neighbor-information container to top-level genstate 
       container";
     uses ospf-neighbor-information-top;
   }
 }
