module junos-genstate-isis-statistics-information {
   yang-version 1;
   namespace "http://yang.juniper.net/junos/genstate/isis-statistics-information";
   prefix jgisi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for isis-statistics-information.

      Copyright (c) 2026 Juniper Networks, Inc.
      All rights reserved.";

   revision 2026-01-01 {
     description "Junos: 26.2R1.7";
   }

   grouping isis-statistics-information-top {
     description
       "Top-level grouping";
     container isis-statistics-information {
       description
         "Top-level container";
       container isis-statistics {
         leaf system-name {
           type string;
           description
             "Hostname for a system";
         }
         leaf snp-queue-length {
           type int32;
         }
         leaf snp-queue-drops {
           type int32;
         }
         leaf lsp-queue-length {
           type int32;
         }
         leaf lsp-queue-drops {
           type int32;
         }
         leaf spf-runs {
           type int32;
         }
         leaf flex-full-spf-runs {
           type int32;
         }
         leaf flex-prc-spf-runs {
           type int32;
         }
         leaf fragments-rebuilt {
           type int32;
         }
         leaf lsps-regenerated {
           type int32;
         }
         leaf purges-initiated {
           type int32;
         }
         list isis-pdu-statistics {
           key "isis-pdu-type";
           leaf isis-pdu-type {
             type string;
           }
           leaf packets-received {
             type uint64;
           }
           leaf packets-processed {
             type uint64;
           }
           leaf packets-dropped {
             type uint64;
           }
           leaf packets-sent {
             type uint64;
           }
           leaf packets-retransmitted {
             type uint64;
           }
         }
         container totals-information {
           leaf packets-received {
             type uint64;
           }
           leaf packets-sent {
             type uint64;
           }
         }
       }
     }
   }
   augment "/jgs:genstate" {
     description
       "Adds isis-statistics-information container to top-level genstate 
       container";
     uses isis-statistics-information-top;
   }
 }
