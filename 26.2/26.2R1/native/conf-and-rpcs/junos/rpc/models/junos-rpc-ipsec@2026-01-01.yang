/*
 * Copyright (c) 2026 Juniper Networks, Inc.
 * All rights reserved.
 */
 module junos-rpc-ipsec {
   namespace "http://yang.juniper.net/junos/rpc/ipsec";

   prefix ipsec;

   import junos-common-types {
     prefix jt;
     revision-date 2026-01-01;
   }

   organization "Juniper Networks, Inc.";

   contact "yang-support@juniper.net";

   description "Junos RPC YANG module for ipsec command(s)";

   revision 2026-01-01 {
     description "Junos: 26.2R1.7";
   }

   rpc get-certificates-information {
     description "Show IPSec digital certificate information";
     status deprecated;
     input {
       leaf level {
         default "brief";
         type enumeration {
           enum "brief" {
             description "Display brief output";
           }
           enum "detail" {
             description "Display detailed output";
           }
         }
       }
       leaf serial-number {
         description "Serial number of certificate";
         type string {
           length "1 .. 255";
         }
       }
     }
     output {
       choice output-tags {
         case output-tag {
           leaf output {
             type string;
           }
         }
         case actual-tag {
           anyxml certificates-information;
         }
         case multichassis-tag {
           anyxml multi-routing-engine-results;
         }
       }
     }
   }
   rpc get-crl-information {
     description "Show IPSec digital certificate revocation lists";
     input {
       leaf level {
         default "brief";
         type enumeration {
           enum "brief" {
             description "Display brief output";
           }
           enum "detail" {
             description "Display detailed output";
           }
         }
       }
       leaf crl-name {
         description "Name of CRL";
         type string {
           length "1 .. 255";
         }
       }
     }
     output {
       choice output-tags {
         case actual-tag {
           container crl-information {
             uses crl-information-block;
           }
         }
         case multichassis-tag {
           container multi-routing-engine-results {
             list multi-routing-engine-item {
               leaf re-name {
                 type string;
               }
               choice output-tags {
                 case actual-tag {
                   container crl-information {
                     uses crl-information-block;
                   }
                 }
               }
             }
           }
         }
       }
     }
   }
   rpc get-re-security-associations-information {
     description "Show IPSec security association information";
     input {
       leaf level {
         default "brief";
         type enumeration {
           enum "brief" {
             description "Display brief output";
           }
           enum "detail" {
             description "Display detailed output";
           }
         }
       }
       leaf sa-name {
         description "Name of security association";
         type string {
           length "1 .. 32";
         }
       }
       leaf hex {
         description "Display SPI in hexadecimal format";
         type empty;
       }
     }
     output {
       choice output-tags {
         case actual-tag {
           container security-associations-information {
             uses security-associations-information-block;
           }
         }
         case multichassis-tag {
           container multi-routing-engine-results {
             list multi-routing-engine-item {
               leaf re-name {
                 type string;
               }
               choice output-tags {
                 case actual-tag {
                   container security-associations-information {
                     uses security-associations-information-block;
                   }
                 }
               }
             }
           }
         }
       }
     }
   }
   rpc get-ipsec-tunnel-redundancy-information {
     description "Show remote tunnel redundancy information";
     input {
       leaf security-association-name {
         description "Name of security association";
         type string;
       }
     }
     output {
       choice output-tags {
         case actual-tag {
           container ipsec-tunnel-redundancy-information {
             uses ipsec-tunnel-redundancy-information-block;
           }
         }
         case multichassis-tag {
           container multi-routing-engine-results {
             list multi-routing-engine-item {
               leaf re-name {
                 type string;
               }
               choice output-tags {
                 case actual-tag {
                   container ipsec-tunnel-redundancy-information {
                     uses ipsec-tunnel-redundancy-information-block;
                   }
                 }
               }
             }
           }
         }
       }
     }
   }
   rpc get-ipsec-pic-redundancy-information {
     description "Show ES PIC redundancy information";
     input {
       leaf interface-name {
         description "Name of ES interface";
         type string;
       }
     }
     output {
       choice output-tags {
         case actual-tag {
           container ipsec-pic-redundancy-information {
             uses ipsec-pic-redundancy-information-block;
           }
         }
         case multichassis-tag {
           container multi-routing-engine-results {
             list multi-routing-engine-item {
               leaf re-name {
                 type string;
               }
               choice output-tags {
                 case actual-tag {
                   container ipsec-pic-redundancy-information {
                     uses ipsec-pic-redundancy-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping crl-information-block {
     list crl {
       leaf cert-issuer {
         type string;
       }
       leaf cert-id {
         type int32;
       }
       leaf cert-references {
         type int32;
       }
       list crl-list {
         description
           "Information about a single CRL entry";
         leaf serial {
           type int32;
         }
         leaf revocation-date {
           type string;
         }
       }
     }
   }
   grouping security-associations-information-block {
     list security-associations-block {
       description
         "Information about a single security association block";
       leaf sa-name {
         type string;
         description
           "Name of the security association";
       }
       leaf sa-block-state {
         type string;
         description
           "Status of the SA configuration block";
       }
       container sa-tunnel-information {
         leaf sa-no-information {
           type empty;
           description
             "Output string when there are no security associations present";
         }
         leaf sa-local-gateway-interface {
           type string;
           description
             "Local gateway  interface";
         }
         leaf sa-local-gateway {
           type jt:ipaddr;
           description
             "Local gateway address";
         }
         leaf sa-remote-gateway {
           type jt:ipaddr;
           description
             "Remote gateway address";
         }
         leaf sa-local-identity {
           type string;
           description
             "Local identity information";
         }
         leaf sa-remote-identity {
           type string;
           description
             "Remote identity information";
         }
         leaf sa-inside-interface {
           type string;
           description
             "Name of IPSec interface to internal network";
         }
         leaf sa-tunnel-mtu {
           type int32;
           description
             "MTU of the IPSec Tunnel";
         }
         leaf sa-udp-encapsulate {
           type string;
           description
             "UDP encapsulation related information";
         }
         leaf sa-udp-dst-port {
           type string;
           description
             "UDP encapsulation port related information";
         }
         leaf sa-detect-natt {
           type string;
           description
             "NAT-T is detected/not detected";
         }
         leaf sa-nat-keepalive {
           type int32;
           description
             "NAT-T keepalive interval in secs";
         }
       }
       list security-associations {
         description
           "Information about a single security association";
         leaf sa-direction {
           type string;
           description
             "Direction of the security association";
         }
         leaf sa-spi {
           type string;
           description
             "Security Parameter Index";
         }
         leaf sa-aux-spi {
           type string;
           description
             "Auxiliary Security Parameter Index";
         }
         leaf sa-mode {
           type string;
           description
             "Mode of the security association";
         }
         leaf sa-type {
           type string;
         }
         leaf sa-protocol {
           type string;
           description
             "IPSec security protocol";
         }
         leaf sa-extended-seq-number {
           type string;
           description
             "Extended-Sequnce-Number";
         }
         leaf sa-state {
           type string;
           description
             "Status of the SA";
         }
         leaf sa-authentication-algorithm {
           type string;
           description
             "Authentication algorithm";
         }
         leaf sa-encryption-algorithm {
           type string;
           description
             "Encryption algorithm";
         }
         leaf sa-soft-lifetime {
           type string;
           description
             "Remaining lifetime, in seconds or kilobytes, before soft 
             lifetime expires";
         }
         leaf sa-hard-lifetime {
           type string;
           description
             "Remaining lifetime, in seconds or kilobytes, before hard 
             lifetime expires";
         }
         leaf sa-anti-replay-service {
           type string;
           description
             "Anti-replay service";
         }
         leaf sa-replay-window-size {
           type int32;
           description
             "Replay window size";
         }
         leaf sa-copy-tos-from-inner-ip-header {
           type string;
           description
             "Copy ToS from inner ip header";
         }
         leaf sa-tos-value {
           type int32;
           description
             "ToS value";
         }
         leaf sa-copy-ttl-from-inner-ip-header {
           type string;
           description
             "Copy TTL from inner ip header";
         }
         leaf sa-ttl-value {
           type int32;
           description
             "TTL value";
         }
         leaf sa-authentication-key {
           type string;
           description
             "Authentication key in hexadecimal format";
         }
         leaf sa-encryption-key {
           type string;
           description
             "Encryption key in hexadecimal format";
         }
       }
     }
     container sa-tunnel-information {
     }
     list security-associations {
       description
         "Information about a single security association";
       leaf sa-extended-seq-number {
         type string;
         description
           "Extended-Sequnce-Number";
       }
     }
   }
   grouping ipsec-tunnel-redundancy-information-block {
     list ipsec-tunnel-redundancy {
       description
         "Information about ipsec tunnel redundancy";
       leaf sa-name {
         type string;
         description
           "Name of the security association";
       }
       leaf ipsec-redundancy-counter {
         type int32;
         description
           "Failover counter";
       }
       leaf ipsec-tunnel-redundancy-local-address {
         type jt:ipaddr;
         description
           "Address of local gateway";
       }
       leaf ipsec-tunnel-redundancy-primary-remote-address {
         type jt:ipaddr;
         description
           "Address of primary remote gateway";
       }
       leaf ipsec-redundancy-primary-state {
         type string;
         description
           "State of primary remote gateway";
       }
       leaf ipsec-tunnel-redundancy-backup-remote-address {
         type jt:ipaddr;
         description
           "Address of backup remote gateway";
       }
       leaf ipsec-redundancy-backup-state {
         type string;
         description
           "State of backup remote gateway";
       }
       leaf ipsec-redundancy-tunnel-no-information {
         type empty;
         description
           "Output string when tunnel redundancy is not configured";
       }
     }
   }
   grouping ipsec-pic-redundancy-information-block {
     list ipsec-pic-redundancy {
       description
         "Information about ipsec pic redundancy";
       leaf ipsec-redundancy-counter {
         type int32;
         description
           "Failover counter";
       }
       leaf ipsec-pic-redundancy-primary-interface {
         type string;
         description
           "Primary ES interface";
       }
       leaf ipsec-redundancy-primary-state {
         type string;
         description
           "State of primary remote gateway";
       }
       leaf ipsec-pic-redundancy-backup-interface {
         type string;
         description
           "Backup ES interface";
       }
       leaf ipsec-redundancy-backup-state {
         type string;
         description
           "State of backup remote gateway";
       }
       leaf ipsec-redundancy-pic-no-information {
         type empty;
         description
           "Output string when there are no pic redundancy present";
       }
     }
   }
 }
