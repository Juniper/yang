/*
 * Copyright (c) 2026 Juniper Networks, Inc.
 * All rights reserved.
 */
 module junos-rpc-l2-learning {
   namespace "http://yang.juniper.net/junos/rpc/l2-learning";

   prefix l2-learning;

   import junos-common-types {
     prefix jt;
     revision-date 2026-01-01;
   }

   organization "Juniper Networks, Inc.";

   contact "yang-support@juniper.net";

   description "Junos RPC YANG module for l2-learning command(s)";

   revision 2026-01-01 {
     description "Junos: 26.2R1.7";
   }

   rpc get-l2ald-telemetry-statistics-information {
     description "L2ald onchange telemetry statistics information";
     input {
       leaf notification-type {
         description "Notification type";
         type string;
       }
     }
     output {
       choice output-tags {
         case actual-tag {
           container l2ald-telemetry-statistics-information {
             uses l2ald-telemetry-statistics-information-block;
           }
         }
         case multichassis-tag {
           container multi-routing-engine-results {
             list multi-routing-engine-item {
               leaf re-name {
                 type string;
               }
               choice output-tags {
                 case actual-tag {
                   container l2ald-telemetry-statistics-information {
                     uses l2ald-telemetry-statistics-information-block;
                   }
                 }
               }
             }
           }
         }
       }
     }
   }
   rpc get-l2-learning-interface-information {
     description "Show interface";
     output {
       choice output-tags {
         case actual-tag {
           container l2ald-iff-information {
             uses l2ald-iff-information-block;
           }
         }
         case multichassis-tag {
           container multi-routing-engine-results {
             list multi-routing-engine-item {
               leaf re-name {
                 type string;
               }
               choice output-tags {
                 case actual-tag {
                   container l2ald-iff-information {
                     uses l2ald-iff-information-block;
                   }
                 }
               }
             }
           }
         }
       }
     }
   }
   rpc get-l2-learning-global-mac-count {
     description "Show layer-2 global mac address count";
     output {
       choice output-tags {
         case actual-tag {
           container l2ald-global-macdb-count {
             uses l2ald-global-macdb-count-block;
           }
         }
         case multichassis-tag {
           container multi-routing-engine-results {
             list multi-routing-engine-item {
               leaf re-name {
                 type string;
               }
               choice output-tags {
                 case actual-tag {
                   container l2ald-global-macdb-count {
                     uses l2ald-global-macdb-count-block;
                   }
                 }
               }
             }
           }
         }
       }
     }
   }
   rpc get-l2-learning-global-mac-ip-count {
     description "Show global MAC+IP bindings count";
     output {
       choice output-tags {
         case actual-tag {
           container l2ald-global-mac-ip-count {
             uses l2ald-global-mac-ip-count-block;
           }
         }
         case multichassis-tag {
           container multi-routing-engine-results {
             list multi-routing-engine-item {
               leaf re-name {
                 type string;
               }
               choice output-tags {
                 case actual-tag {
                   container l2ald-global-mac-ip-count {
                     uses l2ald-global-mac-ip-count-block;
                   }
                 }
               }
             }
           }
         }
       }
     }
   }
   rpc get-l2-learning-global-information {
     description "Show process-related information";
     output {
       choice output-tags {
         case actual-tag {
           container l2ald-global-configuration {
             uses l2ald-global-configuration-block;
           }
         }
         case multichassis-tag {
           container multi-routing-engine-results {
             list multi-routing-engine-item {
               leaf re-name {
                 type string;
               }
               choice output-tags {
                 case actual-tag {
                   container l2ald-global-configuration {
                     uses l2ald-global-configuration-block;
                   }
                 }
               }
             }
           }
         }
       }
     }
   }
   rpc get-l2-learning-routing-instances {
     description "Show routing instances";
     input {
       leaf instance-name {
         description "Display information for a specified instance";
         default "all";
         type string;
       }
       leaf bridge-domain {
         description "Particular bridge-domain or 'all'";
         default "all";
         type string;
       }
       leaf ifbd {
         description "Display information for ifbds under bd";
         type enumeration {
           enum "all" {
             description "Display all IFBDs";
           }
         }
       }
     }
     output {
       choice output-tags {
         case actual-tag {
           container l2ald-routing-table-information {
             uses l2ald-routing-table-information-block;
           }
         }
         case multichassis-tag {
           container multi-routing-engine-results {
             list multi-routing-engine-item {
               leaf re-name {
                 type string;
               }
               choice output-tags {
                 case actual-tag {
                   container l2ald-routing-table-information {
                     uses l2ald-routing-table-information-block;
                   }
                 }
               }
             }
           }
         }
       }
     }
   }
   rpc get-l2-learning-irb-interface-state {
     description "Display IRB interface  state";
     input {
       leaf instance {
         description "Display IRB information under specified instance";
         default "all";
         type string;
       }
       leaf bridge-domain {
         description "Particular bridge-domain or 'all'";
         default "all";
         type string;
       }
       leaf verbosity {
         default "brief";
         type enumeration {
           enum "detail" {
             description "Display detailed output";
           }
           enum "brief" {
             description "Display brief output";
           }
           enum "extensive" {
             description "Display extensive output";
           }
         }
       }
     }
     output {
       choice output-tags {
         case actual-tag {
           container l2ald-irb-interface-state-info {
             uses l2ald-irb-interface-state-info-block;
           }
         }
         case multichassis-tag {
           container multi-routing-engine-results {
             list multi-routing-engine-item {
               leaf re-name {
                 type string;
               }
               choice output-tags {
                 case actual-tag {
                   container l2ald-irb-interface-state-info {
                     uses l2ald-irb-interface-state-info-block;
                   }
                 }
               }
             }
           }
         }
       }
     }
   }
   rpc get-l2-learning-network-isolation {
     description "Display network isolation groups information";
     input {
       leaf group-name {
         description "Particular group or 'all'";
         default "all";
         type string;
       }
       leaf verbosity {
         default "brief";
         type enumeration {
           enum "detail" {
             description "Display detailed output";
           }
           enum "brief" {
             description "Display brief output";
           }
           enum "extensive" {
             description "Display extensive output";
           }
         }
       }
     }
     output {
       choice output-tags {
         case actual-tag {
           container l2ald-network-isolation-information {
             uses l2ald-network-isolation-information-block;
           }
         }
         case multichassis-tag {
           container multi-routing-engine-results {
             list multi-routing-engine-item {
               leaf re-name {
                 type string;
               }
               choice output-tags {
                 case actual-tag {
                   container l2ald-network-isolation-information {
                     uses l2ald-network-isolation-information-block;
                   }
                 }
               }
             }
           }
         }
       }
     }
   }
   rpc get-l2-learning-provider-instance {
     description "Show provider instance (I-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
         }
       }
       leaf isid {
         description "Display Information for specified ISID or all ISID(s)";
         type string;
       }
     }
     output {
       choice output-tags {
         case actual-tag {
           container l2ald-pbn {
             uses l2ald-pbn-block;
           }
         }
         case multichassis-tag {
           container multi-routing-engine-results {
             list multi-routing-engine-item {
               leaf re-name {
                 type string;
               }
               choice output-tags {
                 case actual-tag {
                   container l2ald-pbn {
                     uses l2ald-pbn-block;
                   }
                 }
               }
             }
           }
         }
       }
     }
   }
   rpc get-l2-learning-backbone-instance {
     description "Show provider backbone instance (B-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
         }
       }
       leaf isid {
         description "Display Information for specified ISID or all ISID(s)";
         type string;
       }
     }
     output {
       choice output-tags {
         case actual-tag {
           container l2ald-pbbn {
             uses l2ald-pbbn-block;
           }
         }
         case multichassis-tag {
           container multi-routing-engine-results {
             list multi-routing-engine-item {
               leaf re-name {
                 type string;
               }
               choice output-tags {
                 case actual-tag {
                   container l2ald-pbbn {
                     uses l2ald-pbbn-block;
                   }
                 }
               }
             }
           }
         }
       }
     }
   }
   rpc get-l2-learning-remote-backbone-edge-bridges {
     description "Show remote backbone edge bridges in a PBBN network";
     input {
       leaf remote-beb-mac-address {
         description "Remote backbone edge bridge MAC address";
         default "all";
         type jt:mac-addr;
       }
       leaf logical-system {
         description "Name of logical system, or 'all'";
         default "all";
         type string {
         }
       }
       leaf instance {
         description "Display information for a specified instance";
         default "all";
         type string;
       }
     }
     output {
       choice output-tags {
         case actual-tag {
           container l2ald-rbeb-information {
             uses l2ald-rbeb-information-block;
           }
         }
         case multichassis-tag {
           container multi-routing-engine-results {
             list multi-routing-engine-item {
               leaf re-name {
                 type string;
               }
               choice output-tags {
                 case actual-tag {
                   container l2ald-rbeb-information {
                     uses l2ald-rbeb-information-block;
                   }
                 }
               }
             }
           }
         }
       }
     }
   }
   rpc get-l2-learning-redundancy-groups {
     description "Show redundancy-groups";
     input {
       choice daemon-select {
         case logical-system {
           leaf logical-system {
             description "Name of logical system";
             type string {
             }
           }
         }
       }
       leaf redundancy-group-id {
         description "Display information for a specified RG";
         default "0";
         type union {
           type string {
             pattern "<.*>|$.*";
           }
           type uint32 {
             range "0 .. 4294967294";
           }
         }
       }
       leaf options {
         description "Display information for specified RG or all RG(s)";
         type enumeration {
           enum "remote-macs" {
             description "Display MAC for all RG(s)";
           }
           enum "arp-statistics" {
             description "Show MCAE ARP Synchronization statistics";
           }
           enum "nd-statistics" {
             description "Show MCAE ND synchronization statistics";
           }
           enum "remote-irb-ifas" {
             description "Show MCLAG Remote IRB IFAs";
           }
           enum "local-irb-ifas" {
             description "Show MCLAG Locally Syned IRB IFAs";
           }
         }
       }
     }
     output {
       choice output-tags {
         case actual-tag {
           container l2ald-rg-information {
             uses l2ald-rg-information-block;
           }
         }
         case multichassis-tag {
           container multi-routing-engine-results {
             list multi-routing-engine-item {
               leaf re-name {
                 type string;
               }
               choice output-tags {
                 case actual-tag {
                   container l2ald-rg-information {
                     uses l2ald-rg-information-block;
                   }
                 }
               }
             }
           }
         }
       }
     }
   }
   rpc get-l2-learning-context-history {
     description "Print context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-mac {
     description "Mac context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
       leaf address {
         description "MAC address";
         default "all";
         type jt:mac-addr;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-irb {
     description "IRB context history";
     input {
       leaf irb-name {
         description "IRB Name";
         type union {
           type jt:interface-unit;
           type string {
             pattern "<.*>|$.*";
           }
         }
       }
       leaf irb-id {
         description "IRB Id";
         type union {
           type uint32;
           type string {
             pattern "<.*>|$.*";
           }
         }
       }
       leaf bd-id {
         description "BD Id";
         type union {
           type uint32;
           type string {
             pattern "<.*>|$.*";
           }
         }
       }
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-bd {
     description "BD context history";
     input {
       leaf bd-id {
         description "BD Id";
         type union {
           type uint32;
           type string {
             pattern "<.*>|$.*";
           }
         }
       }
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-rtt {
     description "RTT context history";
     input {
       leaf rtt-id {
         description "RTT Id";
         type union {
           type uint32;
           type string {
             pattern "<.*>|$.*";
           }
         }
       }
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-inh {
     description "INH context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxth-nh-inh {
     description "INH context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxth-nh-vlbnh {
     description "VLBNH context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxth-nh-svlbnh {
     description "SVLBNH context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxth-kernel-irb {
     description "Kernel IRB context history";
     input {
       leaf irb-name {
         description "IRB Name";
         type union {
           type jt:interface-unit;
           type string {
             pattern "<.*>|$.*";
           }
         }
       }
       leaf irb-id {
         description "IRB Id";
         type union {
           type uint32;
           type string {
             pattern "<.*>|$.*";
           }
         }
       }
       leaf bd-id {
         description "BD Id";
         type union {
           type uint32;
           type string {
             pattern "<.*>|$.*";
           }
         }
       }
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-mac-ip {
     description "Mac-ip context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
       leaf address {
         description "MAC address";
         default "all";
         type jt:mac-addr;
       }
       leaf ip-address {
         description "IP address";
         default "all";
         type string;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxt-hist-l2alm-mac {
     description "L2alm mac context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-ctxt-hist-l2alm-macip {
     description "L2alm mac-ip context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-rpd {
     description "Rpd context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
       leaf address {
         description "MAC address";
         default "all";
         type jt:mac-addr;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-rts {
     description "Rtsock context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-vtep {
     description "Vtep context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-in-mem {
     description "In memory debug logs";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-memory {
     description "Memory context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-mac-addr {
     description "Context history for mac-addr";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
       leaf address {
         description "Mac Address";
         type jt:mac-addr;
         mandatory true;
       }
       leaf bd-id {
         description "BD Id";
         default "0";
         type union {
           type string {
             pattern "<.*>|$.*";
           }
           type int32 {
             range "0 .. 65534";
           }
         }
       }
       leaf verbosity {
         default "detail";
         type enumeration {
           enum "detail" {
             description "Display detailed output";
           }
           enum "summary" {
             description "Display summary output";
           }
         }
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-ifbd {
     description "IFBD context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-fnh {
     description "Flood NH context history";
     input {
       leaf from {
         description "Display context from (YYYY-MM-DD.HH:MM:SS)";
         default "2000-01-01.00:00:00";
         type jt:time;
       }
       leaf to {
         description "Display context upto (YYYY-MM-DD.HH:MM:SS)";
         default "3000-01-01.00:00:00";
         type jt:time;
       }
       leaf save {
         description "Save ctxt-history to specified file (.gz is auto-added)";
         type jt:filename;
       }
     }
     output {
       choice output-tags {
         case actual-tag {
           container l2ald-ctxt-history {
             uses l2ald-ctxt-history-block;
           }
         }
         case multichassis-tag {
           container multi-routing-engine-results {
             list multi-routing-engine-item {
               leaf re-name {
                 type string;
               }
               choice output-tags {
                 case actual-tag {
                   container l2ald-ctxt-history {
                     uses l2ald-ctxt-history-block;
                   }
                 }
               }
             }
           }
         }
       }
     }
   }
   rpc get-l2-learning-context-history-inf {
     description "Context history info";
     output {
       choice output-tags {
         case actual-tag {
           container l2ald-ctxt-history-info {
             uses l2ald-ctxt-history-info-block;
           }
         }
         case multichassis-tag {
           container multi-routing-engine-results {
             list multi-routing-engine-item {
               leaf re-name {
                 type string;
               }
               choice output-tags {
                 case actual-tag {
                   container l2ald-ctxt-history-info {
                     uses l2ald-ctxt-history-info-block;
                   }
                 }
               }
             }
           }
         }
       }
     }
   }
   rpc get-l2-learning-mac-move-buffer-information {
     description "Display information on all MAC moves";
     input {
       leaf verbosity {
         default "brief";
         type enumeration {
           enum "detail" {
             description "Display detailed output";
           }
           enum "brief" {
             description "Display brief output";
           }
           enum "extensive" {
             description "Display extensive output";
           }
           enum "active" {
             description "Display only active entries";
           }
         }
       }
     }
     output {
       choice output-tags {
         case actual-tag {
           container l2ald-mac-move-buffer {
             uses l2ald-mac-move-buffer-block;
           }
         }
         case multichassis-tag {
           container multi-routing-engine-results {
             list multi-routing-engine-item {
               leaf re-name {
                 type string;
               }
               choice output-tags {
                 case actual-tag {
                   container l2ald-mac-move-buffer {
                     uses l2ald-mac-move-buffer-block;
                   }
                 }
               }
             }
           }
         }
       }
     }
   }
   rpc get-l2-learning-mgrp-policy {
     description "Display global mesh group policy";
     output {
       choice output-tags {
         case actual-tag {
           container l2ald-mgrp-policy {
             uses l2ald-mgrp-policy-block;
           }
         }
         case multichassis-tag {
           container multi-routing-engine-results {
             list multi-routing-engine-item {
               leaf re-name {
                 type string;
               }
               choice output-tags {
                 case actual-tag {
                   container l2ald-mgrp-policy {
                     uses l2ald-mgrp-policy-block;
                   }
                 }
               }
             }
           }
         }
       }
     }
   }
   rpc get-l2-learning-mgrp-policy-information {
     description "Display Mesh Group policy for routing instance";
     input {
       leaf instance-name {
         description "Display information for a specified instance";
         default "all";
         type string;
       }
       leaf mgrp-id {
         description "Mesh group id";
         type union {
           type uint32;
           type string {
             pattern "<.*>|$.*";
           }
         }
       }
     }
     output {
       choice output-tags {
         case actual-tag {
           container l2ald-mgrp-policy-ri {
             uses l2ald-mgrp-policy-ri-block;
           }
         }
         case multichassis-tag {
           container multi-routing-engine-results {
             list multi-routing-engine-item {
               leaf re-name {
                 type string;
               }
               choice output-tags {
                 case actual-tag {
                   container l2ald-mgrp-policy-ri {
                     uses l2ald-mgrp-policy-ri-block;
                   }
                 }
               }
             }
           }
         }
       }
     }
   }
   rpc get-l2-learning-flood-group {
     description "Display  Flood Group info";
     output {
       choice output-tags {
         case output-tag {
           leaf output {
             type string;
           }
         }
         case actual-tag {
           anyxml l2ald-flood-group;
         }
         case multichassis-tag {
           anyxml multi-routing-engine-results;
         }
       }
     }
   }
   rpc get-l2-learning-flood-group-information {
     description "Display Flood Group info for routing instance";
     input {
       leaf instance-name {
         description "Display information for a specified instance";
         default "all";
         type string;
       }
       leaf bd-index {
         description "Bd id";
         type union {
           type uint32;
           type string {
             pattern "<.*>|$.*";
           }
         }
       }
     }
     output {
       choice output-tags {
         case actual-tag {
           container l2ald-flood-group-ri {
             uses l2ald-flood-group-ri-block;
           }
         }
         case multichassis-tag {
           container multi-routing-engine-results {
             list multi-routing-engine-item {
               leaf re-name {
                 type string;
               }
               choice output-tags {
                 case actual-tag {
                   container l2ald-flood-group-ri {
                     uses l2ald-flood-group-ri-block;
                   }
                 }
               }
             }
           }
         }
       }
     }
   }
   rpc get-l2-learning-eamnh-information {
     description "Display EAMNH and member info";
     input {
       leaf logical-system {
         description "Name of logical system, or 'all'";
         default "all";
         type string {
         }
       }
       leaf instance {
         description "Display information for a specified instance";
         default "all";
         type string;
       }
       leaf bridge-domain {
         description "Name of bridging domain, or 'all'";
         default "all";
         type string;
       }
     }
     output {
       choice output-tags {
         case output-tag {
           leaf output {
             type string;
           }
         }
         case actual-tag {
           anyxml l2ald-enh-eamnh-info;
         }
         case multichassis-tag {
           anyxml multi-routing-engine-results;
         }
       }
     }
   }
   rpc get-l2-learning-nh-learn-entries {
     description "Display information on all RNH_LE entries";
     output {
       choice output-tags {
         case actual-tag {
           container l2ald-nh-learn-entity {
             uses l2ald-nh-learn-entity-block;
           }
         }
         case multichassis-tag {
           container multi-routing-engine-results {
             list multi-routing-engine-item {
               leaf re-name {
                 type string;
               }
               choice output-tags {
                 case actual-tag {
                   container l2ald-nh-learn-entity {
                     uses l2ald-nh-learn-entity-block;
                   }
                 }
               }
             }
           }
         }
       }
     }
   }
   rpc get-l2-learning-vxlan-svtep-info {
     description "Display source VXLAN tunnel endpoint configuration";
     input {
       leaf logical-system {
         description "Name of logical system, or 'all'";
         default "all";
         type string {
         }
       }
       leaf instance {
         description "Display information for a specified instance";
         default "all";
         type string;
       }
     }
     output {
       choice output-tags {
         case actual-tag {
           container vxlan-source-vtep-information {
             uses vxlan-source-vtep-information-block;
           }
         }
         case multichassis-tag {
           container multi-routing-engine-results {
             list multi-routing-engine-item {
               leaf re-name {
                 type string;
               }
               choice output-tags {
                 case actual-tag {
                   container vxlan-source-vtep-information {
                     uses vxlan-source-vtep-information-block;
                   }
                 }
               }
             }
           }
         }
       }
     }
   }
   rpc get-l2-learning-vxlan-svtep-ip-information {
     description "Display VXLAN configuration for source ip address";
     input {
       leaf virtual-tunnel-end-point-source-ip {
         description "Display information for a source ip";
         type jt:ipaddr;
         mandatory true;
       }
       leaf logical-system {
         description "Name of logical system, or 'all'";
         default "all";
         type string {
         }
       }
       leaf instance {
         description "Display information for a specified instance";
         default "all";
         type string;
       }
     }
     output {
       choice output-tags {
         case actual-tag {
           container vxlan-source-vtep-information {
             uses vxlan-source-vtep-information-block;
           }
         }
         case multichassis-tag {
           container multi-routing-engine-results {
             list multi-routing-engine-item {
               leaf re-name {
                 type string;
               }
               choice output-tags {
                 case actual-tag {
                   container vxlan-source-vtep-information {
                     uses vxlan-source-vtep-information-block;
                   }
                 }
               }
             }
           }
         }
       }
     }
   }
   rpc get-l2-learning-vxlan-rvtep-info {
     description "Display remote VXLAN tunnel endpoint information";
     input {
       leaf logical-system {
         description "Name of logical system, or 'all'";
         default "all";
         type string {
         }
       }
       leaf instance {
         description "Display information for a specified instance";
         default "all";
         type string;
       }
       leaf verbosity {
         default "detail";
         type enumeration {
           enum "detail" {
             description "Display detailed output";
           }
           enum "summary" {
             description "Display summary output";
           }
         }
       }
     }
     output {
       choice output-tags {
         case actual-tag {
           container vxlan-source-vtep-information {
             uses vxlan-source-vtep-information-block;
           }
         }
         case multichassis-tag {
           container multi-routing-engine-results {
             list multi-routing-engine-item {
               leaf re-name {
                 type string;
               }
               choice output-tags {
                 case actual-tag {
                   container vxlan-source-vtep-information {
                     uses vxlan-source-vtep-information-block;
                   }
                 }
               }
             }
           }
         }
       }
     }
   }
   rpc get-l2-learning-vxlan-rvtep-mactable-information {
     description "Display remote VTEP MAC table";
     input {
       leaf logical-system {
         description "Name of logical system, or 'all'";
         default "all";
         type string {
         }
       }
       leaf instance {
         description "Display information for a specified instance";
         default "all";
         type string;
       }
     }
     output {
       choice output-tags {
         case actual-tag {
           container vxlan-remote-vtep-mactable {
             uses vxlan-remote-vtep-mactable-block;
           }
         }
         case multichassis-tag {
           container multi-routing-engine-results {
             list multi-routing-engine-item {
               leaf re-name {
                 type string;
               }
               choice output-tags {
                 case actual-tag {
                   container vxlan-remote-vtep-mactable {
                     uses vxlan-remote-vtep-mactable-block;
                   }
                 }
               }
             }
           }
         }
       }
     }
   }
   rpc get-l2-learning-vxlan-remote-svtep-ip-information {
     description "Display remote VXLAN endpoints associated with source endpoint";
     input {
       leaf virtual-tunnel-end-point-source-ip {
         description "Display information for a source ip";
         type jt:ipaddr;
         mandatory true;
       }
     }
     output {
       choice output-tags {
         case actual-tag {
           container vxlan-source-vtep-information {
             uses vxlan-source-vtep-information-block;
           }
         }
         case multichassis-tag {
           container multi-routing-engine-results {
             list multi-routing-engine-item {
               leaf re-name {
                 type string;
               }
               choice output-tags {
                 case actual-tag {
                   container vxlan-source-vtep-information {
                     uses vxlan-source-vtep-information-block;
                   }
                 }
               }
             }
           }
         }
       }
     }
   }
   rpc get-l2-learning-vxlan-rvtep-ip-information {
     description "Display remote VTEP MAC table for ip address";
     input {
       leaf virtual-tunnel-end-point-remote-ip {
         description "Display information for a remote end point";
         type jt:ipaddr;
         mandatory true;
       }
       leaf logical-system {
         description "Name of logical system, or 'all'";
         default "all";
         type string {
         }
       }
       leaf instance {
         description "Display information for a specified instance";
         default "all";
         type string;
       }
     }
     output {
       choice output-tags {
         case actual-tag {
           container vxlan-remote-vtep-ip {
             uses vxlan-remote-vtep-ip-block;
           }
         }
         case multichassis-tag {
           container multi-routing-engine-results {
             list multi-routing-engine-item {
               leaf re-name {
                 type string;
               }
               choice output-tags {
                 case actual-tag {
                   container vxlan-remote-vtep-ip {
                     uses vxlan-remote-vtep-ip-block;
                   }
                 }
               }
             }
           }
         }
       }
     }
   }
   rpc get-l2-learning-vxlan-esi-info {
     description "Display VXLAN tunnel endpoint ESI information";
     input {
       leaf logical-system {
         description "Name of logical system, or 'all'";
         default "all";
         type string {
         }
       }
       leaf instance {
         description "Display information for a specified instance";
         default "all";
         type string;
       }
       leaf esi-identifier {
         description "Ethernet segment identifier";
         type string;
       }
     }
     output {
       choice output-tags {
         case actual-tag {
           container vxlan-esi-information {
             uses vxlan-esi-information-block;
           }
         }
         case multichassis-tag {
           container multi-routing-engine-results {
             list multi-routing-engine-item {
               leaf re-name {
                 type string;
               }
               choice output-tags {
                 case actual-tag {
                   container vxlan-esi-information {
                     uses vxlan-esi-information-block;
                   }
                 }
               }
             }
           }
         }
       }
     }
   }
   rpc get-l2-learning-vxlan-arvlbnh-info {
     description "Display VXLAN tunnel endpoint AR-VLBNH information";
     output {
       choice output-tags {
         case actual-tag {
           container vxlan-arvlbnh-information {
             uses vxlan-arvlbnh-information-block;
           }
         }
         case multichassis-tag {
           container multi-routing-engine-results {
             list multi-routing-engine-item {
               leaf re-name {
                 type string;
               }
               choice output-tags {
                 case actual-tag {
                   container vxlan-arvlbnh-information {
                     uses vxlan-arvlbnh-information-block;
                   }
                 }
               }
             }
           }
         }
       }
     }
   }
   rpc get-l2-learning-arvlbnh-info-index {
     description "Display VxLAN AR-VLBNH information for VLBNH index";
     input {
       leaf vxlan-ar-vlbnh-index {
         description "Display information for a specified index";
         type union {
           type uint32;
           type string {
             pattern "<.*>|$.*";
           }
         }
         mandatory true;
       }
     }
     output {
       choice output-tags {
         case actual-tag {
           container vxlan-arvlbnh-information {
             uses vxlan-arvlbnh-information-block;
           }
         }
         case multichassis-tag {
           container multi-routing-engine-results {
             list multi-routing-engine-item {
               leaf re-name {
                 type string;
               }
               choice output-tags {
                 case actual-tag {
                   container vxlan-arvlbnh-information {
                     uses vxlan-arvlbnh-information-block;
                   }
                 }
               }
             }
           }
         }
       }
     }
   }
   rpc get-l2-learning-vxlan-info-rtt-index {
     description "Display VxLAN AR-VLBNH information for RTT index";
     input {
       leaf vxlan-ar-vlbnh-rtt-index {
         description "Display information for a specified RTT index";
         type union {
           type uint32;
           type string {
             pattern "<.*>|$.*";
           }
         }
         mandatory true;
       }
     }
     output {
       choice output-tags {
         case actual-tag {
           container vxlan-arvlbnh-information {
             uses vxlan-arvlbnh-information-block;
           }
         }
         case multichassis-tag {
           container multi-routing-engine-results {
             list multi-routing-engine-item {
               leaf re-name {
                 type string;
               }
               choice output-tags {
                 case actual-tag {
                   container vxlan-arvlbnh-information {
                     uses vxlan-arvlbnh-information-block;
                   }
                 }
               }
             }
           }
         }
       }
     }
   }
   rpc get-l2-learning-vxlan-info-bd-index {
     description "Display VxLAN AR-VLBNH information for BD index";
     input {
       leaf vxlan-ar-vlbnh-bd-index {
         description "Display information for a specified BD index";
         type union {
           type uint32;
           type string {
             pattern "<.*>|$.*";
           }
         }
         mandatory true;
       }
     }
     output {
       choice output-tags {
         case actual-tag {
           container vxlan-arvlbnh-information {
             uses vxlan-arvlbnh-information-block;
           }
         }
         case multichassis-tag {
           container multi-routing-engine-results {
             list multi-routing-engine-item {
               leaf re-name {
                 type string;
               }
               choice output-tags {
                 case actual-tag {
                   container vxlan-arvlbnh-information {
                     uses vxlan-arvlbnh-information-block;
                   }
                 }
               }
             }
           }
         }
       }
     }
   }
   rpc get-l2-learning-vxlan-mh-vtep-info {
     description "Display Multi Homing Peer VTEP information";
     input {
       leaf logical-system {
         description "Name of logical system, or 'all'";
         default "all";
         type string {
         }
       }
     }
     output {
       choice output-tags {
         case actual-tag {
           container vxlan-ip-mh-vtep-information {
             uses vxlan-ip-mh-vtep-information-block;
           }
         }
         case multichassis-tag {
           container multi-routing-engine-results {
             list multi-routing-engine-item {
               leaf re-name {
                 type string;
               }
               choice output-tags {
                 case actual-tag {
                   container vxlan-ip-mh-vtep-information {
                     uses vxlan-ip-mh-vtep-information-block;
                   }
                 }
               }
             }
           }
         }
       }
     }
   }
   rpc get-l2-learning-vxlan-rtt-mh-vtep-information {
     description "Display MH Peer table for routing instance";
     input {
       leaf instance-name {
         description "Display information for a specified instance";
         default "all";
         type string;
       }
     }
     output {
       choice output-tags {
         case actual-tag {
           container vxlan-rtt-mh-vtep-information {
             uses vxlan-rtt-mh-vtep-information-block;
           }
         }
         case multichassis-tag {
           container multi-routing-engine-results {
             list multi-routing-engine-item {
               leaf re-name {
                 type string;
               }
               choice output-tags {
                 case actual-tag {
                   container vxlan-rtt-mh-vtep-information {
                     uses vxlan-rtt-mh-vtep-information-block;
                   }
                 }
               }
             }
           }
         }
       }
     }
   }
   rpc get-l2-learning-vxlan-ip-mh-vtep-information {
     description "Display MH Peer table for ip address";
     input {
       leaf virtual-tunnel-end-point-remote-ip {
         description "Display information for a remote end point";
         type jt:ipaddr;
         mandatory true;
       }
     }
     output {
       choice output-tags {
         case actual-tag {
           container vxlan-ip-mh-vtep-information {
             uses vxlan-ip-mh-vtep-information-block;
           }
         }
         case multichassis-tag {
           container multi-routing-engine-results {
             list multi-routing-engine-item {
               leaf re-name {
                 type string;
               }
               choice output-tags {
                 case actual-tag {
                   container vxlan-ip-mh-vtep-information {
                     uses vxlan-ip-mh-vtep-information-block;
                   }
                 }
               }
             }
           }
         }
       }
     }
   }
   rpc get-l2-learning-event-queue-stats {
     description "Show event queue stats";
     output {
       choice output-tags {
         case actual-tag {
           container l2ald-event-queue-stats {
             uses l2ald-event-queue-stats-block;
           }
         }
         case multichassis-tag {
           container multi-routing-engine-results {
             list multi-routing-engine-item {
               leaf re-name {
                 type string;
               }
               choice output-tags {
                 case actual-tag {
                   container l2ald-event-queue-stats {
                     uses l2ald-event-queue-stats-block;
                   }
                 }
               }
             }
           }
         }
       }
     }
   }
   rpc get-evpn-arp-statistics {
     description "EVPN arp statistics for irb interfaces";
     input {
       leaf instance {
         description "Display information for a specified instance";
         default "all";
         type string;
       }
       leaf bridge-domain {
         description "Name of bridging domain, or 'all'";
         default "all";
         type string;
       }
     }
     output {
       choice output-tags {
         case actual-tag {
           container l2rtb-evpn-arp-statistics {
             uses l2rtb-evpn-arp-statistics-block;
           }
         }
         case multichassis-tag {
           container multi-routing-engine-results {
             list multi-routing-engine-item {
               leaf re-name {
                 type string;
               }
               choice output-tags {
                 case actual-tag {
                   container l2rtb-evpn-arp-statistics {
                     uses l2rtb-evpn-arp-statistics-block;
                   }
                 }
               }
             }
           }
         }
       }
     }
   }
   rpc get-evpn-arp-statistics-interface {
     description "Display information for irb interfaces";
     input {
       choice interface-choice {
         case interface-name {
           leaf interface-name {
             description "Name of the irb interface";
             type string;
           }
         }
         case all {
           leaf all {
             description "All irb interfaces";
             type empty;
           }
         }
       }
     }
     output {
       choice output-tags {
         case output-tag {
           leaf output {
             type string;
           }
         }
         case actual-tag {
           anyxml l2rtb-evpn-arp-statistics-interface;
         }
         case multichassis-tag {
           anyxml multi-routing-engine-results;
         }
       }
     }
   }
   rpc get-evpn-nd-statistics {
     description "EVPN ND statistics for irb interfaces";
     input {
       leaf instance {
         description "Display information for a specified instance";
         default "all";
         type string;
       }
       leaf bridge-domain {
         description "Name of bridging domain, or 'all'";
         default "all";
         type string;
       }
     }
     output {
       choice output-tags {
         case actual-tag {
           container l2rtb-evpn-nd-statistics {
             uses l2rtb-evpn-nd-statistics-block;
           }
         }
         case multichassis-tag {
           container multi-routing-engine-results {
             list multi-routing-engine-item {
               leaf re-name {
                 type string;
               }
               choice output-tags {
                 case actual-tag {
                   container l2rtb-evpn-nd-statistics {
                     uses l2rtb-evpn-nd-statistics-block;
                   }
                 }
               }
             }
           }
         }
       }
     }
   }
   rpc get-evpn-nd-statistics-interface {
     description "Display information for irb interfaces";
     input {
       choice interface-choice {
         case interface-name {
           leaf interface-name {
             description "Name of the irb interface";
             type string;
           }
         }
         case all {
           leaf all {
             description "All irb interfaces";
             type empty;
           }
         }
       }
     }
     output {
       choice output-tags {
         case output-tag {
           leaf output {
             type string;
           }
         }
         case actual-tag {
           anyxml l2rtb-evpn-nd-statistics-interface;
         }
         case multichassis-tag {
           anyxml multi-routing-engine-results;
         }
       }
     }
   }
   rpc get-vlan-evpn-mcnh-information {
     description "EVPN MCNH Info";
     input {
       leaf instance {
         description "Display information for a specified instance";
         default "all";
         type string;
       }
       leaf bridge-domain {
         description "Name of bridging domain, or 'all'";
         default "all";
         type string;
       }
     }
     output {
       choice output-tags {
         case actual-tag {
           container l2ald-mcnh-info {
             uses l2ald-mcnh-info-block;
           }
         }
         case multichassis-tag {
           container multi-routing-engine-results {
             list multi-routing-engine-item {
               leaf re-name {
                 type string;
               }
               choice output-tags {
                 case actual-tag {
                   container l2ald-mcnh-info {
                     uses l2ald-mcnh-info-block;
                   }
                 }
               }
             }
           }
         }
       }
     }
   }
   rpc get-vlan-evpn-shnh-information {
     description "EVPN SHNH information";
     input {
       leaf instance {
         description "Display information for a specified instance";
         default "all";
         type string;
       }
       leaf bridge-domain {
         description "Name of bridging domain, or 'all'";
         default "all";
         type string;
       }
     }
     output {
       choice output-tags {
         case actual-tag {
           container l2ald-shnh-information {
             uses l2ald-shnh-information-block;
           }
         }
         case multichassis-tag {
           container multi-routing-engine-results {
             list multi-routing-engine-item {
               leaf re-name {
                 type string;
               }
               choice output-tags {
                 case actual-tag {
                   container l2ald-shnh-information {
                     uses l2ald-shnh-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping l2ald-telemetry-statistics-information-block {
     list l2ald-telemetry-notifications {
       key "notif-name";
       leaf notif-name {
         type string;
         description
           "Notification-name";
       }
       leaf total-notif-sent {
         type uint32;
         description
           "Total notifications-sent";
       }
       leaf total-notif-dropped-no-subscription {
         type uint32;
         description
           "Total notifications-dropped (no subscription)";
       }
       leaf total-notif-dropped-no-buffer {
         type uint32;
         description
           "Total notifications-dropped (no buffer)";
       }
     }
   }
   grouping l2ald-iff-information-block {
     list l2ald-iff-entry {
       leaf l2iff-lr-name {
         type string;
         description
           "Logical router name";
       }
       leaf l2iff-rtt-name {
         type string;
         description
           "Routing Instance name";
       }
       leaf l2iff-ifl-name {
         type string;
         description
           "Logical interface name";
       }
       leaf l2iff-ifbd-name {
         type string;
         description
           "BD name in compressed form";
       }
       leaf l2iff-mac-limit {
         type uint32;
         description
           "Maximum number of MAC addresses that can be learned on this 
           interface family";
       }
       leaf l2iff-mac-ip-limit {
         type uint32;
         description
           "Maximum number of MAC+IP bindings that can be learned on this 
           interface family";
       }
       leaf l2iff-ifbd-stp-state {
         type string;
         description
           "STP state for this IFBD";
       }
       leaf l2iff-flags {
         type string;
         description
           "Attributes associated with this interface family";
       }
       leaf l2iff-index {
         type uint32;
         description
           "Interface family index";
       }
       leaf l2iff-generation {
         type uint32;
         description
           "Layer 2 interface family creation time";
       }
       leaf l2iff-rt-index {
         type uint32;
         description
           "Routing instance to which the interface family belongs";
       }
       leaf l2iff-ifd-index {
         type uint32;
         description
           "Physical media to which the interface family belongs";
       }
       leaf l2iff-ifl-index {
         type uint32;
         description
           "Logical interface to which the interface family belongs";
       }
       leaf l2iff-af-value {
         type uint32;
         description
           "Address family to which the interface family belongs";
       }
       leaf l2iff-sequence-number {
         type uint32;
         description
           "Current interface family sequence number";
       }
       leaf l2iff-mac-sequence-number {
         type uint32;
         description
           "Current MAC address sequence number for this interface family";
       }
       leaf l2iff-macs-learned {
         type uint32;
         description
           "Number of configured static and dynamic MACs that are learned on
           this interface family";
       }
       leaf l2iff-config-smacs-learned {
         type uint32;
         description
           "Number of configured static MACs that are learned on this 
           interface family";
       }
       leaf l2iff-non-config-smacs-learned {
         type uint32;
         description
           "Number of non configured static MACs that are learned on this 
           interface family";
       }
       leaf l2iff-mac-ip-learned {
         type uint32;
         description
           "Number of configured static and dynamic MAC+IPs that are learned
           on this interface family";
       }
       leaf l2iff-handle {
         type uint32;
         description
           "Handle associated with this interface family";
       }
       leaf l2iff-config-mac-limit {
         type uint32;
         description
           "Maximum number of MAC addresses that is configured on this 
           interface family";
       }
       leaf l2iff-config-smac-count {
         type uint32;
         description
           "Number of static MAC addresses that is configured on this 
           interface family";
       }
       leaf l2iff-config-smac-applied {
         type uint32;
         description
           "Number of static MAC addresses that is successfully applied to 
           MAC DB on this interface family";
       }
       leaf l2iff-config-rtb-handle {
         type uint32;
         description
           "Handle for the routing instance for this IFL config";
       }
       leaf l2iff-config-state {
         type string;
         description
           "Configured state attributes associated with this interface 
           family";
       }
       leaf l2iff-config-flags {
         type string;
         description
           "Configured attributes associated with this interface family";
       }
       leaf l2iff-config-previous-flags {
         type string;
         description
           "Previous configured attributes associated with this interface 
           family";
       }
       leaf l2iff-config-smac-address {
         type jt:mac-addr;
         description
           "Configured static media access control address associated with 
           this interface family";
       }
       leaf l2iff-config-smac-vlan {
         type uint32;
         description
           "Configured VLAN ID for the static MAC associated with this 
           interface family";
       }
       leaf l2iff-config-smac-flags {
         type string;
         description
           "Configured static MAC attributes associated with this interface 
           family";
       }
       leaf l2iff-interface-type {
         type string;
         description
           "Type of interface (IFF/IFBD)";
       }
       leaf l2iff-rtsock-write-errors {
         type uint32;
         description
           "Number of times kernel write has failed.";
       }
       leaf l2iff-trunk-vlan {
         type uint32;
         description
           "Specify the incoming VLAN id which gets translated.";
       }
       leaf l2iff-rewrite-op {
         type string;
         description
           "Configured rewrite operation.";
       }
       leaf l2iff-vstp-index {
         type uint32;
         description
           "VSTP index";
       }
       leaf l2iff-ifbd-flags {
         type string;
         description
           "L2 learning level flags";
       }
       leaf l2iff-ifbd-mac-limit {
         type uint32;
         description
           "MAC limit for the IFBD";
       }
       leaf l2iff-ifbd-mac-ip-limit {
         type uint32;
         description
           "MAC+IP limit for the IFBD";
       }
       leaf l2iff-rbeb-mac-address {
         type jt:mac-addr;
         description
           "Media access control address of remote backbone edge bridge 
           (BEB)";
       }
       leaf l2iff-time-before-expiry {
         type uint32;
         description
           "Time before object is deleted in seconds";
       }
     }
   }
   grouping l2ald-global-macdb-count-block {
     leaf global-mac-count {
       type uint64;
       description
         "Number of global media access control addresses";
     }
   }
   grouping l2ald-global-mac-ip-count-block {
     leaf global-mac-ip-count {
       type uint64;
       description
         "Number of global MAC+IP bindings";
     }
   }
   grouping l2ald-global-configuration-block {
     leaf l2ald-mac-aging-time {
       type uint32;
       description
         "Configured aging interval for media access control entries";
     }
     leaf l2ald-config-flag {
       type uint32;
       description
         "Show the global configuration flag value";
     }
     leaf l2ald-mac-learning-status {
       type string;
       description
         "Status of media access control address learning (enabled or 
         disabled)";
     }
     leaf l2ald-hardware-mac-learning-status {
       type string;
       description
         "Status of media access control address learning in hardware 
         (enabled or disabled)";
     }
     leaf l2ald-software-mac-learning-status {
       type string;
       description
         "Status of media access control address learning in software 
         (enabled or disabled)";
     }
     leaf l2ald-statistics-status {
       type string;
       description
         "Status of statistics collection for media access control entries 
         (enabled or disabled)";
     }
     leaf l2ald-interface-mac-limit-wm {
       type uint32;
       description
         "Watermark of Inteface MAC limit in percentage";
     }
     leaf l2ald-rtb-mac-limit-wm {
       type uint32;
       description
         "Watermark of Routing MAC limit in percentage";
     }
     leaf l2ald-mac-limit-wm {
       type uint32;
       description
         "Watermark of Global MAC limit in percentage";
     }
     leaf l2ald-mac-limit-low-wm {
       type uint32;
       description
         "Low Watermark of Global MAC limit in percentage";
     }
     leaf l2ald-mac-limit-high-wm {
       type uint32;
       description
         "High Watermark of Global MAC limit in percentage";
     }
     leaf l2ald-interface-mac-limit-timeout {
       type uint32;
       description
         "Timeout value on Interface MAC limit in seconds";
     }
     leaf l2ald-rtb-mac-limit-timeout {
       type uint32;
       description
         "Timeout value on Routing instance MAC limit in seconds";
     }
     leaf l2ald-mac-limit-timeout {
       type uint32;
       description
         "Timeout value on Global MAC limit in seconds";
     }
     leaf l2ald-global-mac-limit {
       type string;
       description
         "Status of global mac limit (whether reached or not)";
     }
     leaf l2ald-sequence-number {
       type uint32;
       description
         "Count of global sequence number";
     }
     leaf l2ald-global-mbb-flag {
       type string;
       description
         "Status of make-before-break knob (enabled or disabled)";
     }
     leaf l2ald-global-packet-action-drop {
       type string;
       description
         "Status of packet action drop (enabled or disabled)";
     }
     leaf l2ald-global-mac-limit-count {
       type string;
       description
         "Count of number of MACs allowed globally in the system";
     }
     leaf l2ald-mac-ip-aging-time-ipv4 {
       type uint32;
       description
         "Configured aging interval for MAC+IPv4 bindings";
     }
     leaf l2ald-mac-ip-aging-time-ipv6 {
       type uint32;
       description
         "Configured aging interval for MAC+IPv6 bindings";
     }
     leaf l2ald-global-mac-ip-limit-reached {
       type string;
       description
         "Status of global mac+ip limit (whether reached or not)";
     }
     leaf l2ald-global-mac-ip-limit-count {
       type string;
       description
         "Count of number of MAC+IPs allowed globally in the system";
     }
     leaf l2ald-mac-ip-limit-wm {
       type uint32;
       description
         "Watermark of Global MAC+IP limit in percentage";
     }
     leaf l2ald-mac-learn-toggle-count {
       type uint32;
       description
         "Count of status changes for media access control address learning 
         (between enabled and disabled)";
     }
     leaf l2ald-hardware-mac-learn-toggle-count {
       type uint32;
       description
         "Count of status changes for media access control address learning 
         in hardware (between enabled and disabled)";
     }
     leaf l2ald-software-mac-learn-toggle-count {
       type uint32;
       description
         "Count of status changes for media access control address learning 
         in software (between enabled and disabled)";
     }
     leaf l2ald-statistics-toggle-count {
       type uint32;
       description
         "Count of status changes for statistics collection on media access 
         control entries (between enabled and disabled)";
     }
     leaf l2ald-config-smac-count {
       type uint32;
       description
         "Number of configured static MACs that are learned globally";
     }
     leaf l2ald-non-config-smac-count {
       type uint32;
       description
         "Number of non configured static MACs that are learned globally";
     }
     leaf l2ald-control-mac-aging-status {
       type string;
       description
         "Status of Control MAC aging (enabled or disabled)";
     }
     leaf l2ald-global-mp-discard-notification-interval {
       type uint32;
       description
         "Timer value for Mac Pinning discard notification interval";
     }
     leaf l2ald-global-evpn-bum-blocking-hold-timer {
       type string;
       description
         "Timer value for evpn bum blocking hold timer";
     }
     leaf l2ald-kernel-vtep-scaling-mode {
       type string;
       description
         "Kernel VTEP Scaling Mode";
     }
     leaf l2ald-vxlan-overlay-lb {
       type string;
       description
         "VXLAN Overlay Load Balance";
     }
     leaf l2ald-vxlan-ecmp {
       type string;
       description
         "VXLAN ECMP";
     }
     leaf l2ald-frr-support {
       type string;
       description
         "FRR Support";
     }
     leaf l2ald-evpn-vxlan-host-gbp-src-tag {
       type uint32;
       description
         "Configured GBP src tag value for host originated vxlan packets";
     }
     leaf l2ald-arp-nd-probe-disable {
       type string;
       description
         "Disable ARP or ND probing";
     }
     leaf l2ald-arp-nd-probe-failed-log {
       type string;
       description
         "Log failure of ARP or ND probe";
     }
     leaf l2ald-garp-na-enable {
       type string;
       description
         "Enable GARP or unsolicited NA";
     }
     leaf l2ald-anycast-multihoming {
       type string;
       description
         "Anycast Multihoming Mode";
     }
     leaf l2ald-anycast-vtep-address {
       type string;
       description
         "Anycast IP address";
     }
     leaf l2ald-l2alm-ctxt-hist-enable {
       type string;
       description
         "Enable L2alm send context history to L2ald";
     }
     leaf l2ald-decoupled-infra {
       type string;
       description
         "Enable a decoupled infrastructure to improve streaming performance";
     }
     leaf l2ald-gc-global-mode {
       type string;
       description
         "Global Mode";
     }
     leaf l2ald-re-state {
       type string;
       description
         "RE State";
     }
     leaf l2ald-crb-proxy-mac-inet4 {
       type string;
       description
         "CRB proxy MAC for IPv4";
     }
     leaf l2ald-crb-proxy-mac-inet6 {
       type string;
       description
         "CRB proxy MAC for IPv6";
     }
     leaf l2ald-event-retry-time {
       type string;
       description
         "Event retry time";
     }
     leaf l2ng-l2ald-fast-update-enable {
       type string;
       description
         "Fast update feature state";
     }
     container l2ald-process-information {
       description
         "Information about the Layer 2 address learning process";
       leaf l2ald-max-peers {
         type uint32;
         description
           "Maximum number of Layer 2 address learning service peers allowed";
       }
       leaf l2ald-rtm-retries {
         type uint32;
         description
           "Configured limit on retry attempts for asynchronous event 
           processing";
       }
       leaf l2ald-rtm-mac-process {
         type uint32;
         description
           "Number of media access control entries processed in each batch";
       }
       leaf l2ald-move-threshold-count {
         type uint32;
         description
           "Number of moves that will be treated as threshold for rapid MAC 
           address moves";
       }
       leaf l2ald-move-threshold-time {
         type uint32;
         description
           "Duration of time considered for monitoring the rapid MAC address
           move";
       }
       container l2ald-control-options {
         description
           "Control options configured for the media access control address 
           learning process";
         leaf l2ald-control-flag {
           type uint32;
           description
             "Currently configured value of control flags";
         }
         leaf l2ald-fnh-module-status {
           type string;
           description
             "Status of flood next-hop module (enabled or disabled)";
         }
         leaf l2ald-mlrn-module-status {
           type string;
           description
             "Status of media access control address learning module 
             (enabled or disabled)";
         }
         leaf l2ald-irb-module-status {
           type string;
           description
             "Status of integrated routing and bridging module (enabled or 
             disabled)";
         }
         leaf l2ald-enhanced-fnh-module-status {
           type string;
           description
             "Status of enhanced flood module (enabled or disabled)";
         }
         leaf l2ald-routing-table-owner-status {
           type string;
           description
             "Status of routing table manipulation by process (enabled or 
             disabled)";
         }
         leaf l2ald-hardware-split-horizon-status {
           type string;
           description
             "Status of split-horizon in hardware (enabled or disabled)";
         }
         leaf l2ald-hardware-learning-status {
           type string;
           description
             "Status of hardware learning (enabled or disabled)";
         }
         leaf l2ald-fork-ui-status {
           type string;
           description
             "Status of forking for 'show' commands (enabled or disabled)";
         }
         leaf l2ald-lc-status {
           type string;
           description
             "Status of lc interfaces (enabled or disabled)";
         }
         leaf l2ald-stp-status {
           type string;
           description
             "Status of Spanning Tree Protocol (enabled or disabled)";
         }
         leaf l2ald-sync-read-status {
           type string;
           description
             "Status of synchronous kernel read (enabled or disabled)";
         }
       }
     }
   }
   grouping l2ald-routing-table-information-block {
     list l2ald-rtb-entry {
       key "l2rtb-name";
       leaf l2rtb-instance-type {
         type string;
         description
           "Type of instance (routing instance/bridge domain)";
       }
       leaf l2rtb-logical-system {
         type string;
         description
           "Logical system name";
       }
       leaf l2rtb-name {
         type string;
         description
           "Name of the routing instance";
       }
       leaf l2rtb-bridging-domain {
         type string;
         description
           "Name of the bridging domain";
       }
       leaf l2rtb-id {
         type uint32;
         description
           "Routing instance identifier";
       }
       leaf l2rtb-l2irb-ifl-index {
         type uint32;
       }
       leaf l2rtb-flags {
         type string;
         description
           "Attributes associated with this routing instance";
       }
       leaf l2bd-vlan-id {
         type string;
       }
       leaf l2ng-l2rtb-instance-type {
         type string;
         description
           "Type of instance (routing instance/bridge domain)";
       }
       leaf l2bd-id {
         type uint32;
         description
           "Bridge domain identifier";
       }
       leaf l2bd-generation {
         type uint32;
         description
           "Bridge domain generation identifier";
       }
       leaf l2rtb-mac-limit {
         type uint32;
         description
           "Maximum number of MAC addresses that can be learned on this 
           routing instance";
       }
       leaf l2rtb-macs-learned {
         type uint32;
         description
           "Number of configured static and dynamic MACs that are learned on
           this routing instance";
       }
       leaf l2rtb-local-macs-learned {
         type uint32;
         description
           "Number of configured static and dynamic MACs that are learned on
           this routing instance";
       }
       leaf l2rtb-config-smacs-learned {
         type uint32;
         description
           "Number of configured static MACs that are learned on this 
           routing instance";
       }
       leaf l2rtb-non-config-smacs-learned {
         type uint32;
         description
           "Number of non configured static MACs that are learned on this 
           routing instance";
       }
       leaf l2rtb-mac-ip-limit {
         type uint32;
         description
           "Maximum number of MAC+IP bindings that can be learned on this 
           routing instance";
       }
       leaf l2rtb-mac-ip-learned {
         type uint32;
         description
           "Number of MAC+IP bindings that are learned on this routing 
           instance";
       }
       leaf l2rtb-local-mac-ip-learned {
         type uint32;
         description
           "Number of local MAC+IP bindings that are learned on this routing
           instance";
       }
       leaf l2rtb-irb-interface {
         type string;
         description
           "Name of the IRB interface associated with this routing instance";
       }
       leaf l2rtb-irb-interface-index {
         type uint32;
         description
           "IRB interface index associated with this routing instance";
       }
       leaf l2rtb-sequence-number {
         type uint32;
         description
           "Current routing instance sequence number";
       }
       leaf l2rtb-handle {
         type uint32;
         description
           "Handle associated with this routing instance";
       }
       leaf l2rtb-peer-pbbn-rtb-id {
         type uint32;
         description
           "Peer PBBN RTB index";
       }
       leaf l2rtb-configured-service-id {
         type uint32;
         description
           "Configured Service-id attributes associated with this routing 
           instance";
       }
       leaf l2rtb-active-service-id {
         type uint32;
         description
           "Service-id attributes associated with this routing 
           instance/bridge domain";
       }
       leaf l2rtb-iesi-value {
         type string;
         description
           "Interconnect ESI Value";
       }
       leaf l2rtb-esi-mode {
         type uint32;
         description
           "Interconnect Esi Mode";
       }
       leaf l2rtb-esi-df-role {
         type uint32;
         description
           "Interconnect Esi DF Role";
       }
       leaf l2rtb-indr-sess-id {
         type uint32;
         description
           "Indirect Session ID for IESI";
       }
       leaf l2rtb-dc-pref {
         type uint32;
         description
           "Interconnect VTEP preference mode";
       }
       leaf l2rtb-vxlan-mpls-aa-src-ip {
         type string;
         description
           "Source IP in outer header of vxlan packet";
       }
       leaf l2rtb-config-bd-vlan {
         type string;
         description
           "Vlan configured for the givn bridge domain on routing instance";
       }
       leaf l2rtb-config-operation {
         type string;
         description
           "Configuration notify operation on bridge domain/routing instance";
       }
       leaf l2rtb-config-smac-count {
         type uint32;
         description
           "Configured Static MAC on the BD";
       }
       leaf l2rtb-config-params {
         type string;
         description
           "Configured attributes associated with this routing 
           instance/bridge domain";
       }
       leaf l2rtb-config-mac-ip-params {
         type string;
         description
           "Configured MAC+IP attributes associated with this routing 
           instance/bridge domain";
       }
       leaf l2rtb-config-flags {
         type string;
         description
           "Configured flags associated with this routing instance/bridge 
           domain";
       }
       leaf l2rtb-service-type {
         type string;
         description
           "Configured service type for this routing instance";
       }
       leaf l2rtb-configured-rg-id {
         type uint32;
         description
           "Config Redundancy Group ID";
       }
       leaf l2rtb-active-rg-id {
         type uint32;
         description
           "Active Redundancy Group ID";
       }
       leaf l2rtb-configured-bd-service-id {
         type uint32;
         description
           "Configured Service-id attributes associated with this bridge 
           domain";
       }
       leaf l2rtb-active-bd-service-id {
         type uint32;
         description
           "Service-id attributes associated with this bridge domain";
       }
       leaf l2rtb-configured-bd-vnid {
         type uint32;
         description
           "Configured VXLAN identifier";
       }
       leaf l2rtb-active-bd-vnid {
         type uint32;
         description
           "Active VXLAN identifier";
       }
       leaf l2rtb-configured-bd-trans-vnid {
         type uint32;
         description
           "Configured translation VXLAN identifier";
       }
       leaf l2rtb-active-bd-trans-vnid {
         type uint32;
         description
           "Active translation VXLAN identifier";
       }
       leaf l2rtb-configured-bd-vxgrp {
         type string;
         description
           "Configured VXLAN multicast group IP address";
       }
       leaf l2rtb-active-bd-vxgrp {
         type string;
         description
           "Active VXLAN multicast group IP address";
       }
       leaf l2rtb-configured-decap-accept-inner-vlan {
         type uint32;
         description
           "Configured VXLAN Decap accept inner vlan";
       }
       leaf l2rtb-configured-encap-inner-vlan {
         type uint32;
         description
           "Configured VXLAN Encap inner vlan";
       }
       leaf l2rtb-configured-unreachable-rvtep-timer {
         type uint32;
         description
           "Configured VXLAN Unreachable rvtep timer";
       }
       leaf l2rtb-configured-ovsdb-enabled {
         type string;
         description
           "Configured VXLAN OVSDB Enabled";
       }
       leaf l2rtb-active-bd-l3rtt {
         type uint32;
         description
           "Active VXLAN Layer-3 routing instance index";
       }
       leaf l2rtb-active-bd-svtep-ip {
         type string;
         description
           "Active VXLAN source tunnel endpoint IP address";
       }
       leaf l2rtb-active-vxlan-token {
         type uint32;
         description
           "VXLAN Token";
       }
       leaf l2rtb-active-vxlan-bcport-token {
         type uint32;
         description
           "VXLAN bcport Token";
       }
       leaf l2rtb-active-vxlan-flood-token {
         type uint32;
         description
           "VXLAN flood Token";
       }
       leaf l2rtb-active-vxlan-wan-token {
         type uint32;
         description
           "VXLAN Wan Token";
       }
       leaf l2rtb-config-ownership-flags {
         type string;
         description
           "Configured ownership flags on attributes associated with this 
           routing instance/bridge domain";
       }
       leaf l2rtb-ownership-flags {
         type string;
         description
           "Kernel ownership flags on attributes associated with this 
           routing instance";
       }
       leaf l2rtb-active-re-flood-token {
         type uint32;
         description
           "RE flood token";
       }
       leaf l2rtb-active-mlp-flood-token {
         type uint32;
         description
           "MLP flood token";
       }
       leaf l2rtb-config-mvrp-ref-count {
         type uint32;
         description
           " Number of join count on the bridge domain";
       }
       leaf l2rtb-rtsock-write-errors {
         type uint32;
         description
           "Number of times kernel write has failed.";
       }
     }
   }
   grouping l2ald-irb-interface-state-info-block {
     list l2ald-irb-state-entry {
       key "interface-name irb-state";
       leaf interface-name {
         type string;
         description
           "Bridging media access control address interface";
       }
       leaf l2rtb-bridging-domain {
         type string;
         description
           "Name of the bridging domain";
       }
       leaf irb-state-network-isolation {
         type string;
         description
           "Network isolation group associated with this IRB";
       }
       leaf irb-state-flags {
         type string;
         description
           "Flags to display knobs configured at CLI";
       }
       leaf irb-state-hold-time-up {
         type uint32;
         description
           "Timeout to wait before declaring IRB is UP";
       }
       leaf irb-state-hold-time-down {
         type uint32;
         description
           "Timeout to wait before declaring IRB is DOWN";
       }
       leaf irb-state-loopback-interface {
         type string;
         description
           "Loopback AE port";
       }
       leaf irb-state {
         type string;
         description
           "IRB interface state flags";
       }
       leaf irb-state-irb-down-reason {
         type string;
         description
           "Reason for IRB interface down";
       }
       leaf l2rtb-name {
         type string;
         description
           "Name of the routing instance";
       }
       leaf irb-state-niso-state {
         type string;
         description
           "Network isolation state";
       }
       leaf irb-state-num-local-intf-up {
         type uint32;
         description
           "Number of local interface in up state under IRB";
       }
       leaf irb-state-num-local-intf-down {
         type uint32;
         description
           "Number of local interface in down state under IRB";
       }
       leaf irb-state-num-remote-intf-up {
         type uint32;
         description
           "Number of rvtep interface in up state under IRB";
       }
       leaf irb-state-num-remote-intf-down {
         type uint32;
         description
           "Number of rvtep interface in down state under IRB";
       }
     }
   }
   grouping l2ald-network-isolation-information-block {
     container niso-group-information {
       list niso-group {
         key "niso-group-name";
         leaf niso-group-name {
           type string;
           description
             "Network isolation group";
         }
         leaf niso-failure-action {
           type string;
           description
             "Detection action status";
         }
         leaf niso-hold-timer {
           type string;
           description
             "Configured hold interval for the group";
         }
         list niso-link-to-monitor-list {
           key "niso-uplink-interface";
           leaf niso-uplink-interface {
             type string;
             description
               "Uplink interface";
           }
         }
         list niso-link-to-disable-list {
           key "niso-downlink-interface";
           leaf niso-downlink-interface {
             type string;
             description
               "Layer 2 interface to disable";
           }
         }
       }
     }
   }
   grouping l2ald-pbn-block {
     list l2ald-pbn-entry-common {
       key "l2pbn-logical-system l2pbn-rtb";
       leaf l2pbn-logical-system {
         type string;
         description
           "Logical system name";
       }
       leaf l2pbn-rtb {
         type string;
         description
           "Name of the routing instance(I-Component)";
       }
     }
     list l2ald-pbn-entry {
       key "l2pbn-pbn-bd l2pbn-isid";
       leaf l2pbn-pbn-bd {
         type string;
         description
           "I-Component bridging domain";
       }
       leaf l2pbn-svlan {
         type string;
         description
           "Service Provider bridge vlan(S-VLAN)";
       }
       leaf l2pbn-isid {
         type uint32;
         description
           "Service Provider I-tag(ISID)";
       }
       leaf l2pbn-sbmac {
         type string;
         description
           "Source B-MAC address";
       }
       leaf l2pbn-pbbn-bd {
         type string;
         description
           "B-Component bridging domain";
       }
       leaf l2pbn-bvlan {
         type string;
         description
           "Backbone bridge vlan(B-VLAN)";
       }
       leaf l2pbn-flags {
         type string;
         description
           "Attributes of this Service Instance I-tag";
       }
       leaf l2pbn-logical-system {
         type string;
         description
           "Logical system name";
       }
       leaf l2pbn-rtb {
         type string;
         description
           "Name of the routing instance(I-Component)";
       }
       leaf l2pbn-rtb-bb {
         type string;
         description
           "Name of the routing instance(B-Component)";
       }
       leaf l2pbn-pbn-bd-index {
         type uint32;
         description
           "BD Index of I-Component bridging domain";
       }
       leaf l2pbn-pbbn-bd-index {
         type uint32;
         description
           "BD Index of B-Component bridging domain";
       }
       leaf l2pbn-generation {
         type uint32;
         description
           "Backbone connectivity establishment time";
       }
       leaf l2pbn-sequence-number {
         type uint32;
         description
           "Backbone connectivity establishment sequence number";
       }
       leaf l2pbn-handle {
         type uint32;
         description
           "Handle associated with this PBN's connectivity to PBBN";
       }
       leaf l2pbn-mac-address {
         type string;
         description
           "Remote BEB Mac address";
       }
     }
   }
   grouping l2ald-pbbn-block {
     list l2ald-pbbn-entry {
       leaf l2pbbn-logical-system {
         type string;
         description
           "Logical system name";
       }
       leaf l2pbbn-rtb-bb {
         type string;
         description
           "Name of the routing instance(B-Component)";
       }
       leaf l2pbbn-rtb-pbbn-id {
         type string;
         description
           "Internal PBBN ID allocated for this B-Component Routing instance";
       }
       leaf l2pbbn-pbbn-bd {
         type string;
         description
           "BD Index of B-Component bridging domain";
       }
       leaf l2pbbn-bvlan {
         type string;
         description
           "Backbone bridge vlan(B-VLAN)";
       }
       leaf l2pbbn-isid {
         type uint32;
         description
           "Service Provider I-tag(ISID)";
       }
       leaf l2pbbn-rtb {
         type string;
         description
           "Name of the routing instance(I-Component)";
       }
       leaf l2pbbn-pbn-bd {
         type string;
         description
           "I-Component bridging domain";
       }
       leaf l2pbbn-svlan {
         type string;
         description
           "Service Provider bridge vlan(S-VLAN)";
       }
       leaf l2pbbn-flags {
         type string;
         description
           "Attributes of this Service Instance I-tag";
       }
       leaf l2pbbn-mac-address {
         type string;
         description
           "Remote BEB MAC address";
       }
       leaf l2pbbn-pbbn-bd-index {
         type uint32;
         description
           "BD Index of B-Component bridging domain";
       }
       leaf l2pbbn-pbn-bd-index {
         type uint32;
         description
           "BD Index of I-Component bridging domain";
       }
       leaf l2pbbn-generation {
         type uint32;
         description
           "Backbone connectivity establishment time";
       }
       leaf l2pbbn-sequence-number {
         type uint32;
         description
           "Backbone connectivity establishment sequence number";
       }
       leaf l2pbbn-handle {
         type uint32;
         description
           "Handle associated with this PBN's connectivity to PBBN";
       }
     }
   }
   grouping l2ald-rbeb-information-block {
     list l2ald-rbeb-entry {
       leaf l2-rbeb-logical-system {
         type string;
         description
           "PBBN Logical system name where remote backbone edge bridges were
           identified";
       }
       leaf l2-rbeb-routing-instance {
         type string;
         description
           "PBBN Routing instance where remote backbone edge bridges were 
           identified";
       }
       leaf l2-rbeb-mac-address {
         type jt:mac-addr;
         description
           "Remote backbone edge bridge's media access control address";
       }
       leaf l2-rbeb-time-left-sec {
         type uint32;
         description
           "Time in seconds left before backbone edge bridge next-hop is 
           deleted";
       }
       leaf l2-rbeb-time-left-msec {
         type uint32;
         description
           "Time in milli-seconds left before backbone edge bridge next-hop 
           is deleted";
       }
       leaf l2-rbeb-flags {
         type string;
         description
           "Remote backbone edge bridge flags";
       }
       leaf l2-rbeb-reference-count {
         type uint32;
         description
           "Remote backbone edge bridge reference count";
       }
       leaf l2-rbeb-le-index {
         type uint32;
         description
           "Remote backbone edge bridge's system index";
       }
       leaf l2-rbeb-state-flags {
         type string;
         description
           "Remote backbone edge bridge state flags";
       }
     }
   }
   grouping l2ald-rg-information-block {
     container l2ald-mc-ae-rg-entry {
       leaf logical-system-name {
         type string;
         description
           "Logical System";
       }
       leaf l2ald-mc-ae-rg-id {
         type uint32;
         description
           "Redundancy Group ID";
       }
       leaf l2ald-mc-ae-rg-flags {
         type string;
         description
           "Redundancy Group Flags";
       }
       leaf l2ald-mc-ae-rg-ref-count {
         type uint32;
         description
           "Redundancy reference count";
       }
       leaf l2ald-mc-ae-rg-disconnect-count {
         type uint32;
         description
           "Redundancy group disconnect count";
       }
       leaf l2ald-mc-ae-rg-tx-count {
         type uint32;
         description
           "Redundancy MAC tx count";
       }
       leaf l2ald-mc-ae-rg-rx-count {
         type uint32;
         description
           "Redundancy MAC rx count";
       }
     }
     container l2ald-mc-ae-sh-remote-macs {
       list l2ald-mc-ae-sh-remote-mac-entry {
         leaf l2ald-mc-ae-sh-service-id {
           type uint32;
           description
             "Service ID";
         }
         leaf l2ald-mc-ae-sh-peer-address {
           type jt:ipaddr;
           description
             "Peer address";
         }
         leaf l2ald-mc-ae-sh-vlan-id {
           type uint32;
           description
             "VLAN ID";
         }
         leaf l2ald-mc-ae-sh-mac-address {
           type jt:mac-addr;
           description
             "MAC address";
         }
         leaf l2ald-mc-ae-sh-rtm-op {
           type uint32;
           description
             "RTM operation";
         }
         leaf l2ald-mc-ae-sh-flags {
           type uint32;
           description
             "Single home entry flags";
         }
         leaf l2ald-mc-ae-sh-status {
           type string;
           description
             "Status";
         }
       }
     }
     container l2ald-mc-ae-mh-remote-macs {
       list l2ald-mc-ae-mh-remote-mac-entry {
         key "l2ald-mc-ae-mh-service-id";
         leaf l2ald-mc-ae-mh-service-id {
           type uint32;
           description
             "Service ID";
         }
         leaf l2ald-mc-ae-mh-peer-address {
           type jt:ipaddr;
           description
             "Peer address";
         }
         leaf l2ald-mc-ae-mh-vlan-id {
           type uint32;
           description
             "VLAN ID";
         }
         leaf l2ald-mc-ae-mh-mac-address {
           type jt:mac-addr;
           description
             "MAC address";
         }
         leaf l2ald-mc-ae-mh-mcae-id {
           type uint32;
           description
             "Multi-chassis AE ID";
         }
         leaf l2ald-mc-ae-mh-unit-num {
           type uint32;
           description
             "Unit number";
         }
         leaf l2ald-mc-ae-mh-rtm-op {
           type uint32;
           description
             "RTM operation";
         }
         leaf l2ald-mc-ae-mh-flags {
           type uint32;
           description
             "Multi-home entry flags";
         }
         leaf l2ald-mc-ae-mh-status {
           type string;
           description
             "Status";
         }
       }
     }
     list l2ald-mc-ae-arp-entry {
       key "l2ald-mc-ae-rg-id";
       leaf l2ald-mc-ae-rg-id {
         type uint32;
         description
           "Redundancy Group ID";
       }
       leaf l2ald-mc-ae-arp-rx-count-from-line {
         type uint32;
         description
           "Number of arps received from local interfaces for replication";
       }
       leaf l2ald-mc-ae-arp-tx-count-to-peer {
         type uint32;
         description
           "Number of arps sent to mclag peer device";
       }
       leaf l2ald-mc-ae-arp-rx-count-from-peer {
         type uint32;
         description
           "Number of arps received from mclag peer device";
       }
       leaf l2ald-mc-ae-arp-install-count {
         type uint32;
         description
           "Number of arps installed locally which are received from mclag 
           peer device";
       }
       leaf l2ald-mc-ae-arp-local-drop-count {
         type uint32;
         description
           "Number of arps dropped locally which are received from line";
       }
       leaf l2ald-mc-ae-arp-remote-drop-count {
         type uint32;
         description
           "Number of arps dropped locally which are received from mclag 
           peer device";
       }
     }
     list l2ald-mc-ae-nd-entry {
       key "l2ald-mc-ae-rg-id";
       leaf l2ald-mc-ae-rg-id {
         type uint32;
         description
           "Redundancy Group ID";
       }
       leaf l2ald-mc-ae-nd-rx-count-from-line {
         type uint32;
         description
           "Number of nds received from local interfaces for replication";
       }
       leaf l2ald-mc-ae-nd-tx-count-to-peer {
         type uint32;
         description
           "Number of nd sent to mclag peer device";
       }
       leaf l2ald-mc-ae-nd-rx-count-from-peer {
         type uint32;
         description
           "Number of nds received from mclag peer device";
       }
       leaf l2ald-mc-ae-nd-install-count {
         type uint32;
         description
           "Number of nds installed locally which are received from mclag 
           peer device";
       }
       leaf l2ald-mc-ae-nd-local-drop-count {
         type uint32;
         description
           "Number of nds dropped locally which are received from line";
       }
       leaf l2ald-mc-ae-nd-remote-drop-count {
         type uint32;
         description
           "Number of nds dropped locally which are received from mclag peer
           device";
       }
     }
     container local-irb-ifa-entry {
       list irb-ifa-entry-format {
         key "ifa-ip-address";
         leaf ifa-ip-address {
           type jt:ipaddr;
           description
             "Ip address";
         }
         leaf ifa-mac-address {
           type jt:mac-addr;
           description
             "MAC address";
         }
         leaf ifa-svc-id {
           type uint32;
           description
             "Service ID";
         }
         leaf ifa-vlan-id {
           type uint32;
           description
             "VLAN ID";
         }
         leaf ifa-status {
           type string;
           description
             "Status";
         }
       }
     }
     container remote-irb-ifa-entry {
       list irb-ifa-entry-format {
         key "ifa-ip-address";
         leaf ifa-ip-address {
           type jt:ipaddr;
           description
             "Ip address";
         }
         leaf ifa-mac-address {
           type jt:mac-addr;
           description
             "MAC address";
         }
         leaf ifa-svc-id {
           type uint32;
           description
             "Service ID";
         }
         leaf ifa-vlan-id {
           type uint32;
           description
             "VLAN ID";
         }
         leaf ifa-status {
           type string;
           description
             "Status";
         }
       }
     }
   }
   grouping l2ald-ctxt-history-block {
     list l2ald-ctxt-history-entry {
       leaf ctxt-current {
         type uint32;
         description
           "Current count";
       }
       leaf ctxt-total {
         type uint32;
         description
           "Total todate";
       }
       leaf ctxt-current-mem {
         type uint32;
         description
           "Current memory used";
       }
       leaf ctxt-max {
         type uint32;
         description
           "Max allowed";
       }
       leaf kern-irb-overflow-cntr {
         type uint32;
         description
           "Kernel IRB overflow counter";
       }
       leaf ctxt-entry {
         type string;
         description
           "Ctxt entry as string";
       }
       leaf ctxt-summary {
         type string;
         description
           "Summary";
       }
       leaf ctxt-free {
         type uint32;
         description
           "Free count";
       }
     }
   }
   grouping l2ald-ctxt-history-info-block {
     leaf ctxt-hist-max-mem-size {
       type uint32;
       description
         "Context history maximum memory size";
     }
     leaf ctxt-hist-cur-mem-size {
       type uint32;
       description
         "Context history current memory size";
     }
     leaf ctxt-hist-cur-ctx-cnt {
       type uint32;
       description
         "Context history current context count";
     }
     leaf ctxt-hist-tot-ctx-cnt {
       type uint32;
       description
         "Context history total context count";
     }
     leaf ctxt-hist-kern-irb-overflow-cnt {
       type uint32;
       description
         "Context history kernel irb overflow count";
     }
     leaf ctxt-hist-in-mem-max-mem-size {
       type uint32;
       description
         "In-memory debug context history maximum memory size";
     }
     leaf ctxt-hist-in-mem-cur-mem-size {
       type uint32;
       description
         "In-memory debug context history current memory size";
     }
     leaf ctxt-hist-in-mem-cur-ctx-cnt {
       type uint32;
       description
         "In-memory debug context history current context count";
     }
     leaf ctxt-hist-in-mem-tot-ctx-cnt {
       type uint32;
       description
         "In-memory debug context history total context count";
     }
     leaf ctxt-hist-rts-max-mem-size {
       type uint32;
       description
         "Rtsock context history maximum memory size";
     }
     leaf ctxt-hist-rts-cur-mem-size {
       type uint32;
       description
         "Rtsock context history current memory size";
     }
     leaf ctxt-hist-rts-cur-ctx-cnt {
       type uint32;
       description
         "Rtsock context history current context count";
     }
     leaf ctxt-hist-rts-tot-ctx-cnt {
       type uint32;
       description
         "Rtsock context history total context count";
     }
     leaf ctxt-hist-mem-max-mem-size {
       type uint32;
       description
         "Memory context history maximum memory size";
     }
     leaf ctxt-hist-mem-cur-mem-size {
       type uint32;
       description
         "Memory context history current memory size";
     }
     leaf ctxt-hist-mem-cur-ctx-cnt {
       type uint32;
       description
         "Memory context history current context count";
     }
     leaf ctxt-hist-mem-tot-ctx-cnt {
       type uint32;
       description
         "Memory context history total context count";
     }
     leaf ctxt-hist-l2alm-max-mem-size {
       type uint32;
       description
         "L2alm context history maximum memory size";
     }
     leaf ctxt-hist-l2alm-cur-mem-size {
       type uint32;
       description
         "L2alm context history current memory size";
     }
     leaf ctxt-hist-l2alm-cur-ctx-cnt {
       type uint32;
       description
         "L2alm context history current context count";
     }
     leaf ctxt-hist-l2alm-tot-ctx-cnt {
       type uint32;
       description
         "L2alm context history total context count";
     }
     leaf ctxt-hist-bgrnd-save-status {
       type string;
       description
         "Context history background save status";
     }
     leaf ctxt-hist-tot-ctx-saved-cnt {
       type uint32;
       description
         "Context history total context saved count";
     }
     leaf ctxt-hist-tot-ctx-saved-mem-size {
       type uint32;
       description
         "Context history total memory size of context saved";
     }
     leaf ctxt-hist-mem-bgrnd-save-file-size {
       type uint32;
       description
         "Context history file size";
     }
     leaf ctxt-hist-mem-bgrnd-save-file-cnt {
       type uint32;
       description
         "Memory context history file count";
     }
     leaf ctxt-hist-max-cfg-size {
       type uint32;
       description
         "Context history maximum configuration size allowed";
     }
     leaf ctxt-hist-min-cfg-size {
       type uint32;
       description
         "Context history minimum configuration size allowed";
     }
   }
   grouping l2ald-mac-move-buffer-block {
     list l2ald-mac-move-entry {
       key "l2ald-mac-address l2ald-learn-vlan-id";
       leaf l2ald-mac-address {
         type string;
         description
           "MAC move of the address";
       }
       leaf l2ald-mac-move-time-rec {
         type string;
         description
           "Time of the MAC move";
       }
       leaf l2ald-mac-move-bridge-domain {
         type string;
         description
           "Bridge domain of the moved MAC";
       }
       leaf l2ald-learn-vlan-id {
         type uint32;
         description
           "Vlan-id of the MAC move";
       }
       leaf l2ald-mac-move-from-ifl {
         type string;
         description
           "MAC moved from this ifl";
       }
       leaf l2ald-mac-move-to-ifl {
         type string;
         description
           "MAC moved to this ifl";
       }
       leaf l2ald-mac-move-ifbd {
         type string;
         description
           "MAC moved to this IFBD";
       }
       leaf l2ald-mac-move-is-blocked {
         type string;
         description
           "Is this IFBD blocked by mac move feature";
       }
     }
   }
   grouping l2ald-mgrp-policy-block {
     leaf l2-mgrp-role {
       type string;
       description
         "Meshgroup Role";
     }
     leaf l2-mgrp-name {
       type string;
       description
         "Meshgroup Name";
     }
     leaf l2-mgrp-name-to {
       type string;
       description
         "Meshgroup Name";
     }
   }
   grouping l2ald-mgrp-policy-ri-block {
     leaf l2-mgrp-role-ri {
       type string;
       description
         "Meshgroup Role";
     }
     leaf l2-mgrp-name-ri {
       type string;
       description
         "Meshgroup Name";
     }
     leaf l2-mgrp-flags-ri {
       type uint32;
       description
         "Meshgroup Flag";
     }
     leaf l2-mgrp-flags-str-ri {
       type string;
       description
         "Meshgroup Name";
     }
     leaf l2-mgrp-name-to-ri {
       type string;
       description
         "Meshgroup Name";
     }
   }
   grouping l2ald-flood-group-ri-block {
     list l2ald-flood-group-ri-entry {
       leaf l2-flood-group-fgname {
         type string;
         description
           "Flood group Name";
       }
       leaf l2-flood-group-mgname {
         type string;
         description
           "Mesh group Name";
       }
       leaf l2-flood-group-bdname {
         type string;
         description
           "Bridge Name";
       }
       leaf l2-flood-group-fgflag {
         type uint32;
         description
           "Flood group Flag";
       }
       leaf l2-flood-group-eamnh {
         type uint32;
         description
           "Eamnh pointer";
       }
       leaf l2-flood-group-eamnhid {
         type uint32;
         description
           "Eamnh Id";
       }
       leaf l2-flood-group-eamnhflag {
         type uint32;
         description
           "Eamnh Flag";
       }
       leaf l2-flood-group-token-flag {
         type uint32;
         description
           "Token Flag";
       }
       leaf l2-flood-group-fld-route {
         type uint32;
         description
           "Route pointer";
       }
       leaf l2-flood-group-token {
         type string;
         description
           "Token prefix";
       }
       leaf l2-flood-group-fnhid {
         type uint32;
         description
           "Flood group Id";
       }
     }
   }
   grouping l2ald-nh-learn-entity-block {
     container evpn-format {
       leaf l2rtt-name {
         type string;
         description
           "Routing instance";
       }
       leaf l2-nh-learn-router-id {
         type uint32;
         description
           "Router ID (Indirect NH ID)";
       }
       leaf l2-nh-learn-index {
         type uint32;
         description
           "RNH LE nexthop index";
       }
       leaf l2-mh-ifl-name {
         type string;
         description
           "Multi-homed IFL name";
       }
       leaf interface-esi {
         type string;
         description
           "ESI";
       }
     }
   }
   grouping vxlan-source-vtep-information-block {
     list svtep-format {
       key "vtep-logical-system-name source-vtep-address source-vtep-interface";
       leaf vtep-logical-system-name {
         type string;
         description
           "Name of the logical system";
       }
       leaf vtep-logical-system-id {
         type uint32;
         description
           "Logical system index";
       }
       leaf source-vtep-address {
         type string;
         description
           "Source VXLAN tunnel endpoint IP address";
       }
       leaf source-vtep-interface {
         type string;
         description
           "Source VXLAN tunnel endpoint IFL name";
       }
       leaf l3-id {
         type uint32;
         description
           "Layer-3 routing instance index";
       }
       leaf source-vtep-mode {
         type string;
         description
           "Source VXLAN tunnel endpoint mode";
       }
       leaf elp-source-vtep-address {
         type string;
         description
           "ELP Source VXLAN tunnel endpoint IP address";
       }
       leaf source-vtep-interface-id {
         type uint32;
         description
           "Source VXLAN tunnel endpoint IFL index";
       }
       container vxlan-routing-instance-information {
         list vxlan-format {
           key "source-vtep-address routing-instance-name bridge-domain-vni-name vn-id source-vtep-name";
           leaf source-vtep-address {
             type string;
             description
               "Source VXLAN tunnel endpoint IP address";
           }
           leaf routing-instance-name {
             type string;
             description
               "Name of the layer-2 routing instance";
           }
           leaf bridge-domain-vni-name {
             type string;
             description
               "Name of the layer-2 bridge domain for VNID";
           }
           leaf vn-id {
             type uint32;
           }
           leaf translation-vn-id {
             type uint32;
             description
               "Tanslation VXLAN identifier";
           }
           leaf multicast-address {
             type string;
             description
               "Multicast IP address";
           }
           leaf snode-tag {
             type string;
             description
               "Designated service npde";
           }
           leaf source-vtep-name {
             type string;
             description
               "Source VTEP name";
           }
           leaf source-vtep-interface-id {
             type uint32;
             description
               "Source VXLAN tunnel endpoint IFL index";
           }
         }
       }
       list vxlan-real-rvtep-information {
         key "remote-vtep-address vtep-routing-instance-name";
         leaf remote-vtep-address {
           type string;
           description
             "Remote VXLAN tunnel endpoint IP address";
         }
         leaf remote-vtep-interface-index {
           type uint32;
           description
             "Remote VXLAN tunnel endpoint IFL index";
         }
         leaf remote-vtep-interface-name {
           type string;
           description
             "Remote VXLAN tunnel endpoint IFL name";
         }
         leaf remote-vtep-nh-id {
           type uint32;
           description
             "Remote VXLAN tunnel endpoint nexthop index";
         }
         leaf remote-vtep-mode {
           type string;
           description
             "Remote VXLAN tunnel endpoint mode";
         }
         leaf elp-remote-vtep-address {
           type string;
           description
             "ELP Remote VXLAN tunnel endpoint IP address";
         }
         leaf extended-mh {
           type string;
           description
             "Extended Multihome Replicator";
         }
         leaf vtep-routing-instance-name {
           type string;
           description
             "Name of the layer-2 routing instance";
         }
         container vxlan-dynamic-information {
           list vxlan-format {
             key "vn-id";
             leaf vn-id {
               type uint32;
             }
             leaf multicast-address {
               type string;
               description
                 "Multicast IP address";
             }
             leaf snode-tag {
               type string;
               description
                 "Designated service npde";
             }
             leaf mc-nh-id {
               type uint32;
               description
                 "Multicast nexthop index";
             }
           }
           list l2ald-mclag-mlsync-status {
             leaf mlsync-local-ip-address {
               type string;
               description
                 "Mclag mac sync local ip address";
             }
             leaf mlsync-peer-ip-address {
               type string;
               description
                 "Mcalg mac sync peer ip address";
             }
             leaf mlsync_status {
               type string;
               description
                 "Mclag mac sync stauts";
             }
           }
           list l2ald-mclag-mlsync-nack-entry {
             leaf l2ald-mclag-mlsync-nack-service-id {
               type uint32;
               description
                 "Service ID";
             }
             leaf l2ald-mclag-mlsync-nack-vlan-id {
               type uint32;
               description
                 "VLAN ID";
             }
             leaf l2ald-mclag-mlsync-nack-mcae-id {
               type uint32;
               description
                 "MCAE id";
             }
             leaf l2ald-mclag-mlsync-nack-unit-num {
               type uint32;
               description
                 "Unit number";
             }
           }
         }
       }
       list vxlan-remote-vtep-information {
         key "remote-vtep-address vtep-routing-instance-name";
         leaf remote-vtep-address {
           type string;
           description
             "Remote VXLAN tunnel endpoint IP address";
         }
         leaf vtep-routing-instance-name {
           type string;
           description
             "Name of the layer-2 routing instance";
         }
         leaf remote-vtep-interface-index {
           type uint32;
           description
             "Remote VXLAN tunnel endpoint IFL index";
         }
         leaf remote-vtep-interface-name {
           type string;
           description
             "Remote VXLAN tunnel endpoint IFL name";
         }
         leaf remote-vtep-nh-id {
           type uint32;
           description
             "Remote VXLAN tunnel endpoint nexthop index";
         }
         leaf remote-vtep-mode {
           type string;
           description
             "Remote VXLAN tunnel endpoint mode";
         }
         leaf elp-remote-vtep-address {
           type string;
           description
             "ELP Remote VXLAN tunnel endpoint IP address";
         }
         leaf extended-mh {
           type string;
           description
             "Extended Multihome Replicator";
         }
         container vxlan-dynamic-information {
           list vxlan-format {
             key "vn-id";
             leaf vn-id {
               type uint32;
             }
             leaf multicast-address {
               type string;
               description
                 "Multicast IP address";
             }
             leaf snode-tag {
               type string;
               description
                 "Designated service npde";
             }
             leaf mc-nh-id {
               type uint32;
               description
                 "Multicast nexthop index";
             }
           }
           list l2ald-mclag-mlsync-status {
             leaf mlsync-local-ip-address {
               type string;
               description
                 "Mclag mac sync local ip address";
             }
             leaf mlsync-peer-ip-address {
               type string;
               description
                 "Mcalg mac sync peer ip address";
             }
             leaf mlsync_status {
               type string;
               description
                 "Mclag mac sync stauts";
             }
           }
           list l2ald-mclag-mlsync-nack-entry {
             leaf l2ald-mclag-mlsync-nack-service-id {
               type uint32;
               description
                 "Service ID";
             }
             leaf l2ald-mclag-mlsync-nack-vlan-id {
               type uint32;
               description
                 "VLAN ID";
             }
             leaf l2ald-mclag-mlsync-nack-mcae-id {
               type uint32;
               description
                 "MCAE id";
             }
             leaf l2ald-mclag-mlsync-nack-unit-num {
               type uint32;
               description
                 "Unit number";
             }
           }
         }
       }
     }
   }
   grouping vxlan-remote-vtep-mactable-block {
     leaf l2-mac-logical-system {
       type string;
       description
         "Name of logical system in which this MAC address was learned";
     }
     leaf l2-mac-routing-instance {
       type string;
       description
         "Routing instance in which the MAC address was learned";
     }
     leaf l2-mac-bridging-domain {
       type string;
       description
         "Bridging domain in which the MAC address was learned";
     }
     leaf l2-bridge-vlan {
       type string;
       description
         "Vlan for the bridging domain";
     }
     leaf l2rtb-active-bd-vnid {
       type uint32;
       description
         "Active VXLAN identifier";
     }
     leaf l2-mac-address {
       type jt:mac-addr;
       description
         "Media access control address learned from another source";
     }
     leaf l2-mac-flags {
       type string;
       description
         "Forwarding entry flags associated with MACs displayed in short 
         form";
     }
     leaf l2-mac-logical-interface {
       type string;
       description
         "Name of logical interface on which MAC address was learned";
     }
     leaf l2-remote-vtep-address {
       type string;
       description
         "Remote VXLAN tunnel endpoint ip address";
     }
   }
   grouping vxlan-remote-vtep-ip-block {
     leaf l2-mac-logical-system {
       type string;
       description
         "Name of logical system in which this MAC address was learned";
     }
     leaf l2-mac-routing-instance {
       type string;
       description
         "Routing instance in which the MAC address was learned";
     }
     leaf l2-mac-bridging-domain {
       type string;
       description
         "Bridging domain in which the MAC address was learned";
     }
     leaf l2-bridge-vlan {
       type string;
       description
         "Vlan for the bridging domain";
     }
     leaf l2rtb-active-bd-vnid {
       type uint32;
       description
         "Active VXLAN identifier";
     }
     leaf l2rtb-configured-bd-vxgrp {
       type string;
       description
         "Configured VXLAN multicast group IP address";
     }
     leaf l2-remote-vtep-address-global {
       type string;
       description
         "Remote VXLAN tunnel endpoint IP address";
     }
     leaf l2-rvtep-nh-id {
       type uint32;
       description
         "Remote VXLAN tunnel endpoint nexthop index";
     }
     leaf l2-mac-address {
       type jt:mac-addr;
       description
         "Media access control address learned from another source";
     }
     leaf l2-mac-flags {
       type string;
       description
         "Forwarding entry flags associated with MACs displayed in short 
         form";
     }
     leaf l2-mac-logical-interface {
       type string;
       description
         "Name of logical interface on which MAC address was learned";
     }
     leaf l2-remote-vtep-address {
       type string;
       description
         "Remote VXLAN tunnel endpoint ip address";
     }
   }
   grouping vxlan-esi-information-block {
     list esi-format {
       key "esi-value";
       leaf esi-value {
         type string;
         description
           "Interface ESI Value";
       }
       leaf routing-instance-name {
         type string;
         description
           "Name of the layer-2 routing instance";
       }
       leaf vxlan-load-balancing-next-hop {
         type uint32;
         description
           "VXLAN Load Balancing Next Hop";
       }
       leaf indirect-next-hop {
         type uint32;
         description
           "VXLAN Indirect Next Hop";
       }
       leaf shared-vlbnh {
         type uint32;
         description
           "Shared VXLAN Load Balancing Next Hop";
       }
       leaf esi-interface {
         type string;
         description
           "Ethernet Segment Id IFL name";
       }
       leaf local-interface {
         type string;
         description
           "Local Ethernet Segment Id IFL name";
       }
       leaf num-remote-vteps {
         type uint32;
         description
           "Number of RVTEPs in this ESI";
       }
       leaf num-unique-remote-vteps {
         type uint32;
         description
           "Number of unique RVTEPs in this anycast ESI";
       }
       leaf esi-aliasing-enabled {
         type string;
         description
           "ESI Aliasing Enabled";
       }
       leaf esi-interconn-esi {
         type string;
         description
           "Interconnect ESI";
       }
       container esi-remote-vtep-information {
         list esi-remote-vtep-entry {
           key "remote-vtep-address remote-vtep-interface";
           leaf remote-vtep-address {
             type string;
             description
               "Remote VXLAN tunnel endpoint IP address";
           }
           leaf remote-vtep-interface {
             type string;
             description
               "Remote VXLAN tunnel end point IP interface name";
           }
           leaf vxlan-encapsulation-next-hop {
             type uint32;
             description
               "VXLAN encapsulation next hop identifier";
           }
           leaf mask-id {
             type uint32;
             description
               "RVTEP learn mask position";
           }
           leaf flags {
             type string;
             description
               "RVTEP learn mask flags";
           }
           leaf remote-vtep-mac-count {
             type uint32;
             description
               "RVTEP mac count";
           }
           leaf remote-vtep-type {
             type string;
             description
               "Type of RVTEP IFL";
           }
         }
       }
     }
   }
   grouping vxlan-arvlbnh-information-block {
     list arvlbnh-format {
       key "routing-instance-name ar-bridge-domain-name";
       leaf routing-instance-name {
         type string;
         description
           "Name of the layer-2 routing instance";
       }
       leaf ar-bridge-domain-name {
         type string;
         description
           "Name of bridge domain";
       }
       leaf ar-vxlan-load-balancing-next-hop {
         type uint32;
         description
           "VXLAN AR Load Balancing Next Hop";
       }
       leaf ar-num-remote-replicator-vteps {
         type uint32;
         description
           "Number of replicator RVTEPs in this AR VLBNH";
       }
       container ar-remote-vtep-information {
         list ar-remote-vtep-entry {
           key "remote-vtep-address ar-remote-vtep-interface";
           leaf remote-vtep-address {
             type string;
             description
               "Remote VXLAN tunnel endpoint IP address";
           }
           leaf ar-remote-vtep-interface {
             type string;
             description
               "Remote VXLAN tunnel end point IP interface name";
           }
           leaf ar-vxlan-encapsulation-next-hop {
             type uint32;
             description
               "VXLAN encapsulation next hop identifier";
           }
           leaf ar-remote-designated {
             type string;
             description
               "Remote VTEP designated node if load balance not supported";
           }
         }
       }
     }
   }
   grouping vxlan-ip-mh-vtep-information-block {
     list mh-vtep-format {
       key "routing-instance-name";
       leaf routing-instance-name {
         type string;
         description
           "Name of the layer-2 routing instance";
       }
       leaf source-vtep-address {
         type string;
         description
           "Source VXLAN tunnel endpoint IP address";
       }
       leaf source-vtep-interface {
         type string;
         description
           "Source VXLAN tunnel endpoint IFL name";
       }
       leaf source-vtep-interface-id {
         type uint32;
         description
           "Source VXLAN tunnel endpoint IFL index";
       }
       container vxlan-mh-vtep-ifl-information {
         container mh-vtep-ifl-format {
           leaf mh-vtep-address {
             type string;
             description
               "MH VXLAN tunnel endpoint IP address";
           }
           leaf mh-vtep-interface {
             type string;
             description
               "MH VXLAN tunnel endpoint IFL name";
           }
           leaf mh-vtep-interface-id {
             type uint32;
             description
               "MH VXLAN tunnel endpoint IFL index";
           }
           container vxlan-mh-vtep-esi-information {
             container mh-esi-format {
               leaf mh-esi-value {
                 type string;
                 description
                   "Interface ESI Value";
               }
             }
           }
         }
       }
     }
   }
   grouping vxlan-rtt-mh-vtep-information-block {
     list mh-vtep-format {
       key "routing-instance-name";
       leaf routing-instance-name {
         type string;
         description
           "Name of the layer-2 routing instance";
       }
       leaf source-vtep-address {
         type string;
         description
           "Source VXLAN tunnel endpoint IP address";
       }
       leaf source-vtep-interface {
         type string;
         description
           "Source VXLAN tunnel endpoint IFL name";
       }
       leaf source-vtep-interface-id {
         type uint32;
         description
           "Source VXLAN tunnel endpoint IFL index";
       }
       container vxlan-mh-vtep-ifl-information {
         container mh-vtep-ifl-format {
           leaf mh-vtep-address {
             type string;
             description
               "MH VXLAN tunnel endpoint IP address";
           }
           leaf mh-vtep-interface {
             type string;
             description
               "MH VXLAN tunnel endpoint IFL name";
           }
           leaf mh-vtep-interface-id {
             type uint32;
             description
               "MH VXLAN tunnel endpoint IFL index";
           }
           container vxlan-mh-vtep-esi-information {
             container mh-esi-format {
               leaf mh-esi-value {
                 type string;
                 description
                   "Interface ESI Value";
               }
             }
           }
         }
       }
     }
   }
   grouping l2ald-event-queue-stats-block {
     list l2ald-event-queue-cntr-list {
       leaf l2ald-event-queue-cntr-list-id {
         type int32;
         description
           "Event list id";
       }
       list l2ald-event-queue-cntr-list-q-entry {
         leaf l2ald-event-queue-cntr-type {
           type string;
           description
             "Event queue counter type";
         }
         leaf l2ald-event-queue-cntr-pq-0 {
           type int32;
           description
             "Number of event of pq-0";
         }
         leaf l2ald-event-queue-cntr-pq-1 {
           type int32;
           description
             "Number of event of pq-1";
         }
         leaf l2ald-event-queue-cntr-pq-2 {
           type int32;
           description
             "Number of event of pq-2";
         }
         leaf l2ald-event-queue-cntr-pq-3 {
           type int32;
           description
             "Number of event of pq-3";
         }
         leaf l2ald-event-queue-cntr-pq-4 {
           type int32;
           description
             "Number of event of pq-4";
         }
       }
       list l2ald-event-queue-cntr-list-info {
         leaf l2ald-event-queue-cntr-event-name {
           type string;
           description
             "Event name";
         }
         leaf l2ald-event-queue-cntr-rstrt {
           type uint64;
           description
             "Number of restart event";
         }
         leaf l2ald-event-queue-cntr-cntr {
           type uint64;
           description
             "Number of event";
         }
       }
     }
   }
   grouping l2rtb-evpn-arp-statistics-block {
     list l2rtb-evpn-arp-statistics-entry {
       leaf interface-name {
         type string;
         description
           "Bridging media access control address interface";
       }
       leaf l2rtb-name {
         type string;
         description
           "Name of the routing instance";
       }
       leaf bd-name {
         type string;
         description
           "Bridging media access control address count for bridge-domain";
       }
       leaf arp-add-count {
         type uint32;
         description
           "Number of arp route adds received from local interfaces";
       }
       leaf arp-delete-count {
         type uint32;
         description
           "Number of arp route deletes received from local interfaces";
       }
       leaf arp-drop-count {
         type uint32;
         description
           "Number of arps dropped";
       }
       leaf arp-sent-count {
         type uint32;
         description
           "Number of arps sent to EVPN peer device";
       }
     }
   }
   grouping l2rtb-evpn-nd-statistics-block {
     list l2rtb-evpn-nd-statistics-entry {
       leaf interface-name {
         type string;
         description
           "Bridging media access control address interface";
       }
       leaf l2rtb-name {
         type string;
         description
           "Name of the routing instance";
       }
       leaf bd-name {
         type string;
         description
           "Bridging media access control address count for bridge-domain";
       }
       leaf nd-add-count {
         type uint32;
         description
           "Number of nd route adds received from local interfaces";
       }
       leaf nd-delete-count {
         type uint32;
         description
           "Number of nd route deletes received from local interfaces";
       }
       leaf nd-drop-count {
         type uint32;
         description
           "Number of nds dropped";
       }
       leaf nd-sent-count {
         type uint32;
         description
           "Number of nds sent to EVPN peer device";
       }
     }
   }
   grouping l2ald-mcnh-info-block {
     container l2ald-mcnh-entry {
       leaf l2-mcnh-rttname {
         type string;
         description
           "RTT Name";
       }
       leaf l2-mcnh-bridge-domain-name {
         type string;
         description
           "Bridge Domain Name";
       }
       leaf l2-mcnh-vlan {
         type string;
         description
           "VLAN";
       }
       list l2ald-mcnh-entry-list {
         key "mcnh-comp-nh";
         leaf mcnh-comp-nh {
           type uint32;
           description
             "Computed Nexthop index";
         }
         leaf mcnh-im-nh {
           type uint32;
           description
             "IM Nexthop index";
         }
         leaf mcnh-peer-id {
           type string;
           description
             "Peer ID";
         }
       }
     }
   }
   grouping l2ald-shnh-information-block {
     list l2ald-shnh-entry-list {
       leaf l2-shnh-rttname {
         type string;
         description
           "RTT name";
       }
       leaf l2-shnh-bridge-domain-name {
         type string;
         description
           "Bridge domain name";
       }
       list l2ald-shnh-entry {
         leaf shnh-esi {
           type string;
           description
             "ESI";
         }
         leaf shnh-peer-id {
           type string;
           description
             "Peer ID";
         }
         leaf shnh-sh-nh-index {
           type uint32;
           description
             "SH NH index";
         }
       }
     }
   }
 }
