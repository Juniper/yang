/*
 * Copyright (c) 2026 Juniper Networks, Inc.
 * All rights reserved.
 */
 module junos-rpc-snmp {
   namespace "http://yang.juniper.net/junos/rpc/snmp";

   prefix snmp;

   import junos-common-types {
     prefix jt;
     revision-date 2026-01-01;
   }

   organization "Juniper Networks, Inc.";

   contact "yang-support@juniper.net";

   description "Junos RPC YANG module for snmp command(s)";

   revision 2026-01-01 {
     description "Junos: 26.2R1.7";
   }

   rpc get-snmp-object {
     description "Get SNMP object value";
     input {
       leaf format {
         default "decimal";
         type enumeration {
           enum "decimal" {
             description "Decimal format (default)";
           }
           enum "ascii" {
             description "Convert string indices to 'ascii-keys' representation";
           }
           enum "hex" {
             description "Shows value part in hexadecimal format";
           }
         }
       }
       leaf snmp-object-name {
         type string {
         }
         mandatory true;
       }
     }
     output {
       choice output-tags {
         case actual-tag {
           container snmp-object-information {
             uses snmp-object-information-block;
           }
         }
         case multichassis-tag {
           container multi-routing-engine-results {
             list multi-routing-engine-item {
               leaf re-name {
                 type string;
               }
               choice output-tags {
                 case actual-tag {
                   container snmp-object-information {
                     uses snmp-object-information-block;
                   }
                 }
               }
             }
           }
         }
       }
     }
   }
   rpc next-snmp-object {
     description "Get next SNMP object value";
     input {
       leaf format {
         default "decimal";
         type enumeration {
           enum "decimal" {
             description "Decimal format (default)";
           }
           enum "ascii" {
             description "Convert string indices to 'ascii-keys' representation";
           }
           enum "hex" {
             description "Shows value part in hexadecimal format";
           }
         }
       }
       leaf snmp-object-name {
         type string {
         }
         mandatory true;
       }
     }
     output {
       choice output-tags {
         case actual-tag {
           container snmp-object-information {
             uses snmp-object-information-block;
           }
         }
         case multichassis-tag {
           container multi-routing-engine-results {
             list multi-routing-engine-item {
               leaf re-name {
                 type string;
               }
               choice output-tags {
                 case actual-tag {
                   container snmp-object-information {
                     uses snmp-object-information-block;
                   }
                 }
               }
             }
           }
         }
       }
     }
   }
   rpc walk-snmp-object {
     description "Walk SNMP object values";
     input {
       leaf format {
         default "decimal";
         type enumeration {
           enum "decimal" {
             description "Decimal format (default)";
           }
           enum "ascii" {
             description "Convert string indices to 'ascii-keys' representation";
           }
           enum "hex" {
             description "Shows value part in hexadecimal format";
           }
         }
       }
       leaf snmp-object-name {
         description "Requested SNMP object names";
         type string {
         }
         mandatory true;
       }
     }
     output {
       choice output-tags {
         case actual-tag {
           container snmp-object-information {
             uses snmp-object-information-block;
           }
         }
         case multichassis-tag {
           container multi-routing-engine-results {
             list multi-routing-engine-item {
               leaf re-name {
                 type string;
               }
               choice output-tags {
                 case actual-tag {
                   container snmp-object-information {
                     uses snmp-object-information-block;
                   }
                 }
               }
             }
           }
         }
       }
     }
   }
   rpc get-snmp-information {
     description "Show SNMP statistics";
     input {
       leaf subsystem {
         description "Name of the subsystem";
         type string;
         mandatory true;
       }
     }
     output {
       choice output-tags {
         case actual-tag {
           container snmp-statistics {
             uses snmp-statistics-block;
           }
         }
         case multichassis-tag {
           container multi-routing-engine-results {
             list multi-routing-engine-item {
               leaf re-name {
                 type string;
               }
               choice output-tags {
                 case actual-tag {
                   container snmp-statistics {
                     uses snmp-statistics-block;
                   }
                 }
               }
             }
           }
         }
       }
     }
   }
   rpc get-snmp-subagent-statistics {
     description "Show statistics for all SNMP subagents";
     input {
       leaf subsystem {
         description "Name of the subsystem";
         type string;
         mandatory true;
       }
     }
     output {
       choice output-tags {
         case actual-tag {
           container snmp-subagent-statistics {
             uses snmp-subagent-statistics-block;
           }
         }
         case multichassis-tag {
           container multi-routing-engine-results {
             list multi-routing-engine-item {
               leaf re-name {
                 type string;
               }
               choice output-tags {
                 case actual-tag {
                   container snmp-subagent-statistics {
                     uses snmp-subagent-statistics-block;
                   }
                 }
               }
             }
           }
         }
       }
     }
   }
   rpc get-snmp-stats-response-statistics-information {
     description "Show mib2d's statistics for the stats responses from kernel/PFE";
     output {
       choice output-tags {
         case actual-tag {
           container snmp-stats-response-statistics {
             uses snmp-stats-response-statistics-block;
           }
         }
         case multichassis-tag {
           container multi-routing-engine-results {
             list multi-routing-engine-item {
               leaf re-name {
                 type string;
               }
               choice output-tags {
                 case actual-tag {
                   container snmp-stats-response-statistics {
                     uses snmp-stats-response-statistics-block;
                   }
                 }
               }
             }
           }
         }
       }
     }
   }
   rpc get-rmon-information {
     description "Show remote monitoring information";
     output {
       choice output-tags {
         case actual-tag {
           container rmon-information {
             uses rmon-information-block;
           }
         }
         case multichassis-tag {
           container multi-routing-engine-results {
             list multi-routing-engine-item {
               leaf re-name {
                 type string;
               }
               choice output-tags {
                 case actual-tag {
                   container rmon-information {
                     uses rmon-information-block;
                   }
                 }
               }
             }
           }
         }
       }
     }
   }
   rpc get-rmon-history-information {
     description "Show RMON history";
     input {
       leaf index {
         type union {
           type int32;
           type string {
             pattern "<.*>|$.*";
           }
         }
       }
       leaf sample-index {
         type union {
           type int32;
           type string {
             pattern "<.*>|$.*";
           }
         }
       }
     }
     output {
       choice output-tags {
         case actual-tag {
           container rmon-history-information {
             uses rmon-history-information-block;
           }
         }
         case multichassis-tag {
           container multi-routing-engine-results {
             list multi-routing-engine-item {
               leaf re-name {
                 type string;
               }
               choice output-tags {
                 case actual-tag {
                   container rmon-history-information {
                     uses rmon-history-information-block;
                   }
                 }
               }
             }
           }
         }
       }
     }
   }
   rpc get-rmon-alarm-information {
     description "Show RMON alarms";
     input {
       leaf level {
         default "brief";
         type enumeration {
           enum "brief" {
             description "Display brief output (default)";
           }
           enum "detail" {
             description "Display detailed output";
           }
         }
       }
     }
     output {
       choice output-tags {
         case actual-tag {
           container rmon-alarm-information {
             uses rmon-alarm-information-block;
           }
         }
         case multichassis-tag {
           container multi-routing-engine-results {
             list multi-routing-engine-item {
               leaf re-name {
                 type string;
               }
               choice output-tags {
                 case actual-tag {
                   container rmon-alarm-information {
                     uses rmon-alarm-information-block;
                   }
                 }
               }
             }
           }
         }
       }
     }
   }
   rpc get-rmon-event-information {
     description "Show RMON events";
     input {
       leaf level {
         default "brief";
         type enumeration {
           enum "brief" {
             description "Display brief output (default)";
           }
           enum "detail" {
             description "Display detailed output";
           }
         }
       }
     }
     output {
       choice output-tags {
         case actual-tag {
           container rmon-event-information {
             uses rmon-event-information-block;
           }
         }
         case multichassis-tag {
           container multi-routing-engine-results {
             list multi-routing-engine-item {
               leaf re-name {
                 type string;
               }
               choice output-tags {
                 case actual-tag {
                   container rmon-event-information {
                     uses rmon-event-information-block;
                   }
                 }
               }
             }
           }
         }
       }
     }
   }
   rpc get-rmon-log-information {
     description "Show rmon monitoring logs";
     output {
       choice output-tags {
         case actual-tag {
           container rmon-log-information {
             uses rmon-log-information-block;
           }
         }
         case multichassis-tag {
           container multi-routing-engine-results {
             list multi-routing-engine-item {
               leaf re-name {
                 type string;
               }
               choice output-tags {
                 case actual-tag {
                   container rmon-log-information {
                     uses rmon-log-information-block;
                   }
                 }
               }
             }
           }
         }
       }
     }
   }
   rpc get-health-monitor-information {
     description "Show health-monitoring information";
     output {
       choice output-tags {
         case output-tag {
           leaf output {
             type string;
           }
         }
         case actual-tag {
           anyxml health-monitor-information;
         }
         case multichassis-tag {
           anyxml multi-routing-engine-results;
         }
       }
     }
   }
   rpc get-health-monitor-alarm-information {
     description "Show health-monitor alarms";
     input {
       leaf level {
         default "brief";
         type enumeration {
           enum "brief" {
             description "Display brief output (default)";
           }
           enum "detail" {
             description "Display detailed output";
           }
         }
       }
     }
     output {
       choice output-tags {
         case actual-tag {
           container rmon-alarm-information {
             uses rmon-alarm-information-block;
           }
         }
         case multichassis-tag {
           container multi-routing-engine-results {
             list multi-routing-engine-item {
               leaf re-name {
                 type string;
               }
               choice output-tags {
                 case actual-tag {
                   container rmon-alarm-information {
                     uses rmon-alarm-information-block;
                   }
                 }
               }
             }
           }
         }
       }
     }
   }
   rpc get-health-monitor-log-information {
     description "Show health-monitoring logs";
     output {
       choice output-tags {
         case actual-tag {
           container rmon-log-information {
             uses rmon-log-information-block;
           }
         }
         case multichassis-tag {
           container multi-routing-engine-results {
             list multi-routing-engine-item {
               leaf re-name {
                 type string;
               }
               choice output-tags {
                 case actual-tag {
                   container rmon-log-information {
                     uses rmon-log-information-block;
                   }
                 }
               }
             }
           }
         }
       }
     }
   }
   rpc get-snmp-v3-information {
     description "Show SNMP version 3 information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-general-information {
     description "Show general SNMPv3 information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-group-information {
     description "Show SNMPv3 security-to-group information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-usm-user-information {
     description "Show SNMPv3 user information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-access-information {
     description "Show SNMPv3 access information";
     input {
       leaf subsystem {
         description "Name of the subsystem";
         type string;
         mandatory true;
       }
       leaf level {
         default "brief";
         type enumeration {
           enum "brief" {
             description "Display brief output (default)";
           }
           enum "detail" {
             description "Display detailed output";
           }
         }
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-community-information {
     description "Show SNMPv3 community information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-target-information {
     description "Show SNMPv3 target information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-target-address-information {
     description "Show SNMPv3 target address information";
     input {
       leaf subsystem {
         description "Name of the subsystem";
         type string;
         mandatory true;
       }
     }
     output {
       choice output-tags {
         case actual-tag {
           container snmp-v3-target-information {
             uses snmp-v3-target-information-block;
           }
         }
         case multichassis-tag {
           container multi-routing-engine-results {
             list multi-routing-engine-item {
               leaf re-name {
                 type string;
               }
               choice output-tags {
                 case actual-tag {
                   container snmp-v3-target-information {
                     uses snmp-v3-target-information-block;
                   }
                 }
               }
             }
           }
         }
       }
     }
   }
   rpc get-snmp-v3-target-parameters-information {
     description "Show SNMPv3 target parameters information";
     input {
       leaf subsystem {
         description "Name of the subsystem";
         type string;
         mandatory true;
       }
     }
     output {
       choice output-tags {
         case actual-tag {
           container snmp-v3-target-information {
             uses snmp-v3-target-information-block;
           }
         }
         case multichassis-tag {
           container multi-routing-engine-results {
             list multi-routing-engine-item {
               leaf re-name {
                 type string;
               }
               choice output-tags {
                 case actual-tag {
                   container snmp-v3-target-information {
                     uses snmp-v3-target-information-block;
                   }
                 }
               }
             }
           }
         }
       }
     }
   }
   rpc get-snmp-v3-notify-information {
     description "Show SNMPv3 notify information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-v3-notify-filter-information {
     description "Show SNMPv3 notify filter information";
     input {
       leaf subsystem {
         description "Name of the subsystem";
         type string;
         mandatory true;
       }
     }
     output {
       choice output-tags {
         case actual-tag {
           container snmp-v3-information {
             uses snmp-v3-information-block;
           }
         }
         case multichassis-tag {
           container multi-routing-engine-results {
             list multi-routing-engine-item {
               leaf re-name {
                 type string;
               }
               choice output-tags {
                 case actual-tag {
                   container snmp-v3-information {
                     uses snmp-v3-information-block;
                   }
                 }
               }
             }
           }
         }
       }
     }
   }
   rpc get-snmp-inform-statistics {
     description "Show SNMP Inform request statistics";
     input {
       leaf subsystem {
         description "Name of the subsystem";
         type string;
         mandatory true;
       }
     }
     output {
       choice output-tags {
         case actual-tag {
           container snmp-inform-statistics {
             uses snmp-inform-statistics-block;
           }
         }
         case multichassis-tag {
           container multi-routing-engine-results {
             list multi-routing-engine-item {
               leaf re-name {
                 type string;
               }
               choice output-tags {
                 case actual-tag {
                   container snmp-inform-statistics {
                     uses snmp-inform-statistics-block;
                   }
                 }
               }
             }
           }
         }
       }
     }
   }
   rpc get-snmp-proxy-information {
     description "Show SNMP Proxy information";
     input {
       leaf subsystem {
         description "Name of the subsystem";
         type string;
         mandatory true;
       }
     }
     output {
       choice output-tags {
         case actual-tag {
           container snmp-proxy-information {
             uses snmp-proxy-information-block;
           }
         }
         case multichassis-tag {
           container multi-routing-engine-results {
             list multi-routing-engine-item {
               leaf re-name {
                 type string;
               }
               choice output-tags {
                 case actual-tag {
                   container snmp-proxy-information {
                     uses snmp-proxy-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping snmp-object-information-block {
     list snmp-object {
       key "name";
       leaf name {
         type string;
         description
           "SNMP object name";
       }
       leaf object-value {
         type string;
         description
           "SNMP object value";
       }
       leaf error {
         type string;
         description
           "SNMP object error";
       }
       leaf oid {
         type string;
         description
           "SNMP object identifier";
       }
       leaf object-value-type {
         type string;
       }
       list index {
         leaf index-name {
           type string;
           description
             "SNMP index name";
         }
         leaf index-value {
           type string;
           description
             "SNMP index value";
         }
       }
     }
     container snmp-request-error {
       leaf snmp-req-error-value {
         type string;
         description
           "SNMP request error";
       }
     }
   }
   grouping snmp-statistics-block {
     container snmp-input-statistics {
       leaf packets {
         type int32;
       }
       leaf bad-versions {
         type int32;
       }
       leaf bad-community-names {
         type int32;
       }
       leaf bad-community-uses {
         type int32;
       }
       leaf asn-parse-errors {
         type int32;
       }
       leaf too-bigs {
         type int32;
       }
       leaf no-such-names {
         type int32;
       }
       leaf bad-values {
         type int32;
       }
       leaf read-onlys {
         type int32;
       }
       leaf general-errors {
         type int32;
       }
       leaf total-request-varbinds {
         type int32;
       }
       leaf total-set-varbinds {
         type int32;
       }
       leaf get-requests {
         type int32;
       }
       leaf get-nexts {
         type int32;
       }
       leaf set-requests {
         type int32;
       }
       leaf get-responses {
         type int32;
       }
       leaf traps {
         type int32;
       }
       leaf silent-drops {
         type int32;
       }
       leaf proxy-drops {
         type int32;
       }
       leaf commit-pending-drops {
         type int32;
       }
       leaf throttle-drops {
         type int32;
       }
       leaf duplicate-request-drops {
         type int32;
         description
           "Number of duplicate requests that were dropped";
       }
     }
     container snmp-v3-input-statistics {
       leaf unknown-secmodels {
         type int32;
       }
       leaf invalid-msgs {
         type int32;
       }
       leaf unknown-pduhandlers {
         type int32;
       }
       leaf unavail-contexts {
         type int32;
       }
       leaf unknown-contexts {
         type int32;
       }
       leaf unsupported-seclevels {
         type int32;
       }
       leaf not-in-timewindows {
         type int32;
       }
       leaf unknown-usernames {
         type int32;
       }
       leaf unknown-eids {
         type int32;
       }
       leaf wrong-digests {
         type int32;
       }
       leaf decrypt-errors {
         type int32;
       }
     }
     container snmp-output-statistics {
       leaf packets {
         type int32;
       }
       leaf too-bigs {
         type int32;
       }
       leaf no-such-names {
         type int32;
       }
       leaf bad-values {
         type int32;
       }
       leaf general-errors {
         type int32;
       }
       leaf get-requests {
         type int32;
       }
       leaf get-nexts {
         type int32;
       }
       leaf set-requests {
         type int32;
       }
       leaf get-responses {
         type int32;
       }
       leaf traps {
         type int32;
       }
     }
     container snmp-performance-statistics {
       leaf average-response-time {
         type string;
         description
           "Average response time in ms for processing SNMP PDU";
       }
       leaf one-minute-request-throughput {
         type int32;
         description
           "Throughput of request diaptaching in last minute";
       }
       leaf five-minute-request-throughput {
         type int32;
         description
           "Throughput of request dispatching in last five minutes";
       }
       leaf fifteen-minute-request-throughput {
         type int32;
         description
           "Throughput of request dispatching in last fifteen minutes";
       }
       leaf one-minute-response-throughput {
         type int32;
         description
           "Throughput of response dispatching in last minute";
       }
       leaf five-minute-response-throughput {
         type int32;
         description
           "Throughput of response dispatching in last five minutes";
       }
       leaf fifteen-minute-response-throughput {
         type int32;
         description
           "Throughput of response dispatching in last fifteen minutes";
       }
     }
     container sub-agent-control-blocks {
       leaf total {
         type int32;
       }
       leaf currently-active {
         type int32;
       }
       leaf max-active {
         type int32;
       }
       leaf not-found {
         type int32;
       }
       leaf timed-out {
         type int32;
       }
       leaf max-latency {
         type int32;
       }
     }
     container sub-agent-registration {
       leaf group-registers {
         type int32;
       }
       leaf group-deregisters {
         type int32;
       }
       leaf group-removes {
         type int32;
       }
     }
     container sec-sub-agent-control-blocks {
       leaf sec-total {
         type int32;
       }
       leaf sec-currently-active {
         type int32;
       }
       leaf sec-max-active {
         type int32;
       }
       leaf sec-sa-max-latency {
         type int32;
       }
       leaf sec-max-latency {
         type int32;
       }
     }
     container trap-queue-stats {
       leaf current-queued {
         type int32;
       }
       leaf total-queued {
         type int32;
       }
       leaf total-discards {
         type int32;
       }
       leaf total-overflows {
         type int32;
       }
     }
     container trap-throttle-stats {
       leaf current-throttled {
         type int32;
       }
       leaf total-throttles {
         type int32;
       }
     }
     container snmp-set-stats {
       leaf nvs-commit-pending {
         type int32;
         description
           "Set requests failed because of a pending commit";
       }
       leaf nvs-conflock-failures {
         type int32;
         description
           "Set requests failed because of configuration lock conflict";
       }
       leaf nvs-rpc-mgd-failures {
         type int32;
         description
           "Set requests failed because of a management daemon rpc error";
       }
       leaf nvs-journal-write-failures {
         type int32;
         description
           "Set requests failed because of journal write error";
       }
       leaf nvs-mgd-connect-failures {
         type int32;
         description
           "Set requests failed because snmpd could not connect to mgd";
       }
       leaf nvs-commit-failures {
         type int32;
         description
           "Set requests failed because of a general commit error";
       }
     }
   }
   grouping snmp-subagent-statistics-block {
     list subagent-statistics {
       leaf subagent {
         type string;
         description
           "Subagent identifier";
       }
       leaf subagent-request-pdus {
         type uint32;
         description
           "Number of request PDUs handled by subagent";
       }
       leaf subagent-response-pdus {
         type uint32;
         description
           "Number of response PDUs handled by subagent";
       }
       leaf subagent-request-variables {
         type uint32;
         description
           "Number of request variables handled by subagent";
       }
       leaf subagent-response-variables {
         type uint32;
         description
           "Number of request variables handled by subagent";
       }
       leaf subagent-average-response-time {
         type string;
         description
           "Average response time of subagent";
       }
       leaf subagent-maximum-response-time {
         type string;
         description
           "Maximum response time of subagent";
       }
     }
   }
   grouping snmp-stats-response-statistics-block {
     list stats-average-response-time-statistics {
       leaf stats-type {
         type string;
         description
           "Stats type";
       }
       leaf stats-type-count {
         type uint64;
         description
           "Stats count for a stats type";
       }
       leaf stats-average-response-time {
         type string;
         description
           "Average response time for a stats type";
       }
     }
     list bucket-statistics {
       leaf bucket-type {
         type string;
         description
           "Bucket type";
       }
       leaf bucket-stats-response-count {
         type uint64;
         description
           "Stats count for a bucket";
       }
     }
     list bad-responses {
       leaf bad-responses-response-time {
         type string;
         description
           "Response time of a stats request";
       }
       leaf bad-responses-request-timestamp {
         type int32;
         description
           "Timestamp of stats request";
       }
       leaf bad-responses-stats-type {
         type string;
         description
           "Stats type";
       }
       leaf bad-responses-key {
         type string;
         description
           "Key for a stats request";
       }
     }
   }
   grouping rmon-information-block {
     container rmon-log-information {
       list rmon-log {
         leaf rmon-log-event-index {
           type int32;
           description
             "Event instance identifier";
         }
         leaf rmon-log-descr {
           type string;
           description
             "Log description";
         }
         leaf rmon-log-time {
           type string;
           description
             "Time this event was last generated";
         }
         leaf rmon-log-index {
           type int32;
           description
             "Log instance identifier";
         }
       }
     }
     container rmon-alarm-information {
       list rmon-alarm {
         key "alarm-index";
         leaf alarm-index {
           type int32;
           description
             "Alarm instance identifier";
         }
         leaf var-name {
           type string;
           description
             "Monitored variable name";
         }
         leaf var-oid {
           type string;
           description
             "Monitored variable OID";
         }
         leaf sample-type {
           type string;
           description
             "Method of sampling the monitored variable";
         }
         leaf startup {
           type string;
           description
             "Alarm that might be sent when entry is activated";
         }
         leaf alarm-owner {
           type string;
           description
             "Name of owner of this entry";
         }
         leaf alarm-creator {
           type string;
           description
             "Method by which entry was created";
         }
         leaf alarm-subtag {
           type string;
           description
             "Additional tag added to system logs for this entry";
         }
         leaf alarm-state {
           type string;
           description
             "Current state of the entry";
         }
         leaf alarm-interval {
           type int32;
           description
             "Interval between samples, in seconds";
         }
         leaf rising-threshold {
           type int32;
           description
             "Rising alarm threshold";
         }
         leaf falling-threshold {
           type int32;
           description
             "Falling alarm threshold";
         }
         leaf rising-event-index {
           type int32;
           description
             "Event generated when a rising alarm is sent";
         }
         leaf falling-event-index {
           type int32;
           description
             "Event generated when a falling alarm is sent";
         }
         leaf alarm-value {
           type int32;
           description
             "Most recently monitored value";
         }
         list rmon-alarm-instance {
           description
             "Information about an alarm instance";
           leaf inst-var-name {
             type string;
             description
               "Monitored variable name";
           }
           leaf inst-description {
             type string;
             description
               "Monitored variable description";
           }
           leaf inst-value {
             type int32;
             description
               "Most recently monitored value";
           }
           leaf inst-state {
             type string;
             description
               "Current state of the alarm instance";
           }
         }
         leaf moderate-threshold {
           type int32;
           description
             "Moderate alarm threshold";
         }
         leaf high-threshold {
           type int32;
           description
             "High alarm threshold";
         }
         leaf critical-threshold {
           type int32;
           description
             "Critical alarm threshold";
         }
       }
     }
     container rmon-event-information {
       list rmon-event {
         key "event-index";
         leaf event-index {
           type int32;
           description
             "Event instance identifier";
         }
         leaf event-descr {
           type string;
           description
             "Comment describing the event entry";
         }
         leaf event-type {
           type string;
           description
             "Type of notification made about this event";
         }
         leaf community {
           type string;
           description
             "Trap group to which trap is sent";
         }
         leaf last-time-sent {
           type string;
           description
             "Time this event was last generated";
         }
         leaf event-owner {
           type string;
           description
             "Name of owner of the event";
         }
         leaf event-creator {
           type string;
           description
             "Method by which the entry was created";
         }
         leaf event-state {
           type string;
           description
             "Current state of the entry";
         }
       }
     }
     container rmon-history-information {
       list rmon-history {
         leaf history-index {
           type int32;
           description
             "History instance identifier";
         }
         leaf history-interface {
           type string;
           description
             "Comment describing the RMON interface";
         }
         leaf history-requested-buckets {
           type int32;
           description
             "Requested buckets for the RMON interface";
         }
         leaf history-interval {
           type int32;
           description
             "Interval for statistics collection on the RMON interface";
         }
         leaf history-owner {
           type string;
           description
             "Owner for RMON history";
         }
         leaf history-status {
           type string;
           description
             "Status of RMON history";
         }
       }
       list history-sample {
         leaf history-sample-index {
           type int32;
           description
             "History sample instance identifier";
         }
         leaf history-sample-start-time {
           type string;
           description
             "History sample collection start time ";
         }
         leaf history-sample-drop-events {
           type uint64;
           description
             "Sample drop events";
         }
         leaf history-sample-octect {
           type uint64;
           description
             "Octets";
         }
         leaf history-sample-packets {
           type uint64;
           description
             "Packets";
         }
         leaf history-sample-broadcast-packets {
           type uint64;
           description
             "Number of broadcast packets";
         }
         leaf history-sample-multicast-packets {
           type uint64;
           description
             "Number of multicast packets";
         }
         leaf history-sample-crc-errors {
           type uint64;
           description
             "Crc errors";
         }
         leaf history-sample-undersize-packets {
           type uint64;
           description
             "Number of undersize packets";
         }
         leaf history-sample-oversize-packets {
           type uint64;
           description
             "Number of oversize packets";
         }
         leaf history-sample-fragments {
           type uint64;
           description
             "Number of fragment";
         }
         leaf history-sample-jabbers {
           type uint64;
           description
             "Number of jabbers";
         }
         leaf history-sample-collisions {
           type uint64;
           description
             "Number of collisions";
         }
         leaf history-sample-utilization {
           type uint64;
           description
             "Utilization ";
         }
       }
     }
   }
   grouping rmon-history-information-block {
     list rmon-history {
       leaf history-index {
         type int32;
         description
           "History instance identifier";
       }
       leaf history-interface {
         type string;
         description
           "Comment describing the RMON interface";
       }
       leaf history-requested-buckets {
         type int32;
         description
           "Requested buckets for the RMON interface";
       }
       leaf history-interval {
         type int32;
         description
           "Interval for statistics collection on the RMON interface";
       }
       leaf history-owner {
         type string;
         description
           "Owner for RMON history";
       }
       leaf history-status {
         type string;
         description
           "Status of RMON history";
       }
     }
     list history-sample {
       leaf history-sample-index {
         type int32;
         description
           "History sample instance identifier";
       }
       leaf history-sample-start-time {
         type string;
         description
           "History sample collection start time ";
       }
       leaf history-sample-drop-events {
         type uint64;
         description
           "Sample drop events";
       }
       leaf history-sample-octect {
         type uint64;
         description
           "Octets";
       }
       leaf history-sample-packets {
         type uint64;
         description
           "Packets";
       }
       leaf history-sample-broadcast-packets {
         type uint64;
         description
           "Number of broadcast packets";
       }
       leaf history-sample-multicast-packets {
         type uint64;
         description
           "Number of multicast packets";
       }
       leaf history-sample-crc-errors {
         type uint64;
         description
           "Crc errors";
       }
       leaf history-sample-undersize-packets {
         type uint64;
         description
           "Number of undersize packets";
       }
       leaf history-sample-oversize-packets {
         type uint64;
         description
           "Number of oversize packets";
       }
       leaf history-sample-fragments {
         type uint64;
         description
           "Number of fragment";
       }
       leaf history-sample-jabbers {
         type uint64;
         description
           "Number of jabbers";
       }
       leaf history-sample-collisions {
         type uint64;
         description
           "Number of collisions";
       }
       leaf history-sample-utilization {
         type uint64;
         description
           "Utilization ";
       }
     }
   }
   grouping rmon-alarm-information-block {
     list rmon-alarm {
       key "alarm-index";
       leaf alarm-index {
         type int32;
         description
           "Alarm instance identifier";
       }
       leaf var-name {
         type string;
         description
           "Monitored variable name";
       }
       leaf var-oid {
         type string;
         description
           "Monitored variable OID";
       }
       leaf sample-type {
         type string;
         description
           "Method of sampling the monitored variable";
       }
       leaf startup {
         type string;
         description
           "Alarm that might be sent when entry is activated";
       }
       leaf alarm-owner {
         type string;
         description
           "Name of owner of this entry";
       }
       leaf alarm-creator {
         type string;
         description
           "Method by which entry was created";
       }
       leaf alarm-subtag {
         type string;
         description
           "Additional tag added to system logs for this entry";
       }
       leaf alarm-state {
         type string;
         description
           "Current state of the entry";
       }
       leaf alarm-interval {
         type int32;
         description
           "Interval between samples, in seconds";
       }
       leaf rising-threshold {
         type int32;
         description
           "Rising alarm threshold";
       }
       leaf falling-threshold {
         type int32;
         description
           "Falling alarm threshold";
       }
       leaf rising-event-index {
         type int32;
         description
           "Event generated when a rising alarm is sent";
       }
       leaf falling-event-index {
         type int32;
         description
           "Event generated when a falling alarm is sent";
       }
       leaf alarm-value {
         type int32;
         description
           "Most recently monitored value";
       }
       list rmon-alarm-instance {
         description
           "Information about an alarm instance";
         leaf inst-var-name {
           type string;
           description
             "Monitored variable name";
         }
         leaf inst-description {
           type string;
           description
             "Monitored variable description";
         }
         leaf inst-value {
           type int32;
           description
             "Most recently monitored value";
         }
         leaf inst-state {
           type string;
           description
             "Current state of the alarm instance";
         }
       }
       leaf moderate-threshold {
         type int32;
         description
           "Moderate alarm threshold";
       }
       leaf high-threshold {
         type int32;
         description
           "High alarm threshold";
       }
       leaf critical-threshold {
         type int32;
         description
           "Critical alarm threshold";
       }
     }
   }
   grouping rmon-event-information-block {
     list rmon-event {
       key "event-index";
       leaf event-index {
         type int32;
         description
           "Event instance identifier";
       }
       leaf event-descr {
         type string;
         description
           "Comment describing the event entry";
       }
       leaf event-type {
         type string;
         description
           "Type of notification made about this event";
       }
       leaf community {
         type string;
         description
           "Trap group to which trap is sent";
       }
       leaf last-time-sent {
         type string;
         description
           "Time this event was last generated";
       }
       leaf event-owner {
         type string;
         description
           "Name of owner of the event";
       }
       leaf event-creator {
         type string;
         description
           "Method by which the entry was created";
       }
       leaf event-state {
         type string;
         description
           "Current state of the entry";
       }
     }
   }
   grouping rmon-log-information-block {
     list rmon-log {
       leaf rmon-log-event-index {
         type int32;
         description
           "Event instance identifier";
       }
       leaf rmon-log-descr {
         type string;
         description
           "Log description";
       }
       leaf rmon-log-time {
         type string;
         description
           "Time this event was last generated";
       }
       leaf rmon-log-index {
         type int32;
         description
           "Log instance identifier";
       }
     }
   }
   grouping snmp-v3-information-block {
     container snmp-v3-general-information {
       list snmp-v3-engine-information {
         key "engine-id";
         leaf engine-id {
           type string;
           description
             "Engine ID";
         }
         leaf engine-boots {
           type int32;
           description
             "Number of times this engine has booted";
         }
         leaf engine-time {
           type int32;
           description
             "Number of seconds since this engine has booted";
         }
         leaf max-msg-size {
           type int32;
           description
             "Maximum message size allowed by this engine";
         }
       }
     }
     container snmp-v3-usm-user-information {
       container snmp-v3-usm-user-engine-id {
         leaf user-engine-id {
           type string;
           description
             "Engine ID";
         }
       }
       list snmp-v3-usm-user {
         key "user-name";
         leaf user-name {
           type string;
           description
             "User name";
         }
         leaf auth-type {
           type string;
           description
             "Type of authentication required by this user";
         }
         leaf priv-type {
           type string;
           description
             "Type of encryption required by this user";
         }
         leaf storage-type {
           type string;
           description
             "Type of storage for this entry";
         }
         leaf row-status {
           type string;
           description
             "Status for this entry";
         }
       }
     }
     container snmp-v3-group-information {
       list snmp-v3-group {
         key "group-name";
         leaf group-name {
           type string;
           description
             "Group name";
         }
         leaf security-model {
           type string;
           description
             "Security model";
         }
         leaf security-name {
           type string;
           description
             "Security name";
         }
         leaf storage-type {
           type string;
           description
             "Type of storage for this entry";
         }
         leaf row-status {
           type string;
           description
             "Status for this entry";
         }
       }
     }
     container snmp-v3-access-information {
       list snmp-v3-access {
         key "group-name";
         leaf group-name {
           type string;
           description
             "Group name";
         }
         leaf context-prefix {
           type string;
           description
             "Context prefix";
         }
         leaf security-model {
           type string;
           description
             "Security model";
         }
         leaf security-level {
           type string;
           description
             "Security level";
         }
         leaf read-view {
           type string;
           description
             "MIB view allowed for read access";
         }
         leaf write-view {
           type string;
           description
             "MIB view allowed for write access";
         }
         leaf notify-view {
           type string;
           description
             "MIB view allowed for notifications";
         }
         leaf row-status {
           type string;
           description
             "Status for this entry";
         }
         leaf context-match {
           type string;
         }
         leaf storage-type {
           type string;
           description
             "Type of storage for this entry";
         }
       }
     }
     container snmp-v3-target-information {
       container snmp-v3-target-address-information {
         description
           "SNMPv3 target address information";
         list snmp-v3-target_address {
           key "target-address-name address port target-parameters-name";
           description
             "SNMPv3 target address";
           leaf target-address-name {
             type string;
             description
               "Target address name in target address table";
           }
           leaf address {
             type string;
             description
               "Target address";
           }
           leaf port {
             type string;
             description
               "Target port number";
           }
           leaf target-parameters-name {
             type string;
             description
               "Target parameters name";
           }
           leaf storage-type {
             type string;
             description
               "Type of storage for this entry";
           }
           leaf row-status {
             type string;
             description
               "Status for this entry";
           }
         }
       }
       container snmp-v3-target-parameters-information {
         description
           "SNMPv3 target parameters information";
         list snmp-v3-target_parameters {
           key "target-parameters-name";
           description
             "SNMPv3 target parameters";
           leaf target-parameters-name {
             type string;
             description
               "Target parameters name";
           }
           leaf security-name {
             type string;
             description
               "Security name";
           }
           leaf security-model {
             type string;
             description
               "Security model";
           }
           leaf security-level {
             type string;
             description
               "Security level";
           }
           leaf notify-filter-name {
             type string;
             description
               "Notify filter name in the notify filter table";
           }
           leaf storage-type {
             type string;
             description
               "Type of storage for this entry";
           }
           leaf row-status {
             type string;
             description
               "Status for this entry";
           }
         }
       }
     }
     container snmp-v3-notify-information {
       description
         "SNMPv3 notify information";
       list snmp-v3-notify {
         key "notify-name";
         description
           "SNMPv3 notify";
         leaf notify-name {
           type string;
           description
             "Notify name";
         }
         leaf notify-tag {
           type string;
           description
             "Notify tag used to identify all acceptable targets";
         }
         leaf notify-type {
           type string;
         }
         leaf storage-type {
           type string;
           description
             "Type of storage for this entry";
         }
         leaf row-status {
           type string;
           description
             "Status for this entry";
         }
       }
     }
     container snmp-v3-notify-filter-information {
       description
         "SNMPv3 notify filter information";
       list snmp-v3-notify-filter {
         key "filter-name";
         description
           "SNMPv3 notify filter";
         leaf filter-name {
           type string;
           description
             "Notify filter name";
         }
         leaf subtree {
           type string;
           description
             "MIB subtree for this filter";
         }
         leaf filter-type {
           type string;
         }
         leaf storage-type {
           type string;
           description
             "Type of storage for this entry";
         }
         leaf row-status {
           type string;
           description
             "Status for this entry";
         }
       }
     }
     container snmp-v3-community-information {
       description
         "SNMPv3 community information";
       list snmp-v3-community {
         key "community-index";
         description
           "SNMPv3 community";
         leaf community-index {
           type string;
           description
             "Community index in this community table entry";
         }
         leaf security-name {
           type string;
           description
             "Security name";
         }
         leaf context-name {
           type string;
           description
             "Context name used when performing access control";
         }
         leaf transport-tag {
           type string;
           description
             "Transport tag used to identify a set of targets";
         }
         leaf storage-type {
           type string;
           description
             "Type of storage for this entry";
         }
         leaf row-status {
           type string;
           description
             "Status for this entry";
         }
       }
     }
   }
   grouping snmp-v3-target-information-block {
     container snmp-v3-target-address-information {
       description
         "SNMPv3 target address information";
       list snmp-v3-target_address {
         key "target-address-name address port target-parameters-name";
         description
           "SNMPv3 target address";
         leaf target-address-name {
           type string;
           description
             "Target address name in target address table";
         }
         leaf address {
           type string;
           description
             "Target address";
         }
         leaf port {
           type string;
           description
             "Target port number";
         }
         leaf target-parameters-name {
           type string;
           description
             "Target parameters name";
         }
         leaf storage-type {
           type string;
           description
             "Type of storage for this entry";
         }
         leaf row-status {
           type string;
           description
             "Status for this entry";
         }
       }
     }
     container snmp-v3-target-parameters-information {
       description
         "SNMPv3 target parameters information";
       list snmp-v3-target_parameters {
         key "target-parameters-name";
         description
           "SNMPv3 target parameters";
         leaf target-parameters-name {
           type string;
           description
             "Target parameters name";
         }
         leaf security-name {
           type string;
           description
             "Security name";
         }
         leaf security-model {
           type string;
           description
             "Security model";
         }
         leaf security-level {
           type string;
           description
             "Security level";
         }
         leaf notify-filter-name {
           type string;
           description
             "Notify filter name in the notify filter table";
         }
         leaf storage-type {
           type string;
           description
             "Type of storage for this entry";
         }
         leaf row-status {
           type string;
           description
             "Status for this entry";
         }
       }
     }
   }
   grouping snmp-inform-statistics-block {
     list inform-stats-entry {
       leaf target-name {
         type string;
         description
           "Name of the target (receiver of Inform requests)";
       }
       leaf target-address {
         type jt:ipaddr;
         description
           "Target address";
       }
       leaf informs-sent {
         type int32;
         description
           "Total number of Inform requests sent successfully";
       }
       leaf informs-pending {
         type int32;
         description
           "Number of Inform requests sent but not yet acknowledged";
       }
       leaf informs-discarded {
         type int32;
         description
           "Number of Inform requests discarded because no acknowledgment 
           was received";
       }
       leaf inform-timeouts {
         type int32;
         description
           "Number of Inform requests that timed out";
       }
       leaf inform-probe-failures {
         type int32;
         description
           "Number of remote engine ID discovery probes that failed";
       }
     }
   }
   grouping snmp-proxy-information-block {
     list snmp-proxy {
       description
         "SNMP proxy";
       leaf proxy-name {
         type string;
         description
           "Proxy name in this proxy table entry";
       }
       leaf device-name {
         type string;
         description
           "Satellite Device name associated to this Proxy";
       }
       leaf version {
         type string;
         description
           "Version";
       }
       leaf community-or-security-name {
         type string;
         description
           "Community Or Security Name associated to this Proxy";
       }
       leaf context {
         type string;
         description
           "Context associated to this Proxy";
       }
       leaf routing-instance {
         type string;
         description
           "Routing Instance associated to this Proxy";
       }
     }
   }
 }
