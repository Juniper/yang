/*
 * Copyright (c) 2026 Juniper Networks, Inc.
 * All rights reserved.
 */
 module junos-rpc-isis {
   namespace "http://yang.juniper.net/junos/rpc/isis";

   prefix isis;

   import junos-common-types {
     prefix jt;
     revision-date 2026-01-01;
   }

   organization "Juniper Networks, Inc.";

   contact "yang-support@juniper.net";

   description "Junos RPC YANG module for isis command(s)";

   revision 2026-01-01 {
     description "Junos: 26.2R1.7";
   }

   rpc get-isis-adjacency-information {
     description "Show IS-IS adjacency database";
     input {
       choice daemon-select {
         case logical-system {
           leaf logical-system {
             description "Name of logical system, or 'all'";
             type string {
             }
           }
         }
       }
       leaf igp-instance {
         description "Regular expression for igp-instance names to match";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf system-id {
         description "System ID of intermediate system";
         type string;
       }
     }
     output {
       choice output-tags {
         case actual-tag {
           container isis-adjacency-information {
             uses isis-adjacency-information-block;
           }
         }
         case multichassis-tag {
           container multi-routing-engine-results {
             list multi-routing-engine-item {
               leaf re-name {
                 type string;
               }
               choice output-tags {
                 case actual-tag {
                   container isis-adjacency-information {
                     uses isis-adjacency-information-block;
                   }
                 }
               }
             }
           }
         }
       }
     }
   }
   rpc get-isis-adjacency-holddown-information {
     description "Show IS-IS adjacency-holddown status";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
     }
     output {
       choice output-tags {
         case actual-tag {
           container isis-adjacency-holddown-information {
             uses isis-adjacency-holddown-information-block;
           }
         }
         case multichassis-tag {
           container multi-routing-engine-results {
             list multi-routing-engine-item {
               leaf re-name {
                 type string;
               }
               choice output-tags {
                 case actual-tag {
                   container isis-adjacency-holddown-information {
                     uses isis-adjacency-holddown-information-block;
                   }
                 }
               }
             }
           }
         }
       }
     }
   }
   rpc get-isis-authentication-information {
     description "Show IS-IS authentication information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output-tags {
         case actual-tag {
           container isis-authentication-information {
             uses isis-authentication-information-block;
           }
         }
         case multichassis-tag {
           container multi-routing-engine-results {
             list multi-routing-engine-item {
               leaf re-name {
                 type string;
               }
               choice output-tags {
                 case actual-tag {
                   container isis-authentication-information {
                     uses isis-authentication-information-block;
                   }
                 }
               }
             }
           }
         }
       }
     }
   }
   rpc get-isis-bgporr-information {
     description "Show BGP optimal route reflection groups";
     input {
       choice daemon-select {
         case logical-system {
           leaf logical-system {
             description "Name of logical system, or 'all'";
             type string {
             }
           }
         }
       }
       leaf igp-instance {
         description "Name of igp-instance";
         type string;
       }
       leaf destination {
         description "IP address and optional prefix length of destination";
         type jt:ipprefix;
       }
       leaf instance {
         description "Name of IS-IS instance";
         type string;
       }
       leaf group {
         description "BGP optimal route-reflection peer group name";
         type string;
       }
     }
     output {
       choice output-tags {
         case actual-tag {
           container isis-bgporr-information {
             uses isis-bgporr-information-block;
           }
         }
         case multichassis-tag {
           container multi-routing-engine-results {
             list multi-routing-engine-item {
               leaf re-name {
                 type string;
               }
               choice output-tags {
                 case actual-tag {
                   container isis-bgporr-information {
                     uses isis-bgporr-information-block;
                   }
                 }
               }
             }
           }
         }
       }
     }
   }
   rpc get-isis-database-information {
     description "Show IS-IS link-state database";
     input {
       choice daemon-select {
         case logical-system {
           leaf logical-system {
             description "Name of logical system, or 'all'";
             type string {
             }
           }
         }
       }
       leaf igp-instance {
         description "Regular expression for igp-instance names to match";
         type string;
       }
       leaf flex-algorithm-id {
         description "Flex Algorithm id";
         type union {
           type string {
             pattern "<.*>|$.*";
           }
           type uint32 {
             range "128 .. 255";
           }
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
       leaf system-id {
         description "System ID of IS";
         type string;
       }
     }
     output {
       choice output-tags {
         case actual-tag {
           container isis-database-information {
             uses isis-database-information-block;
           }
         }
         case multichassis-tag {
           container multi-routing-engine-results {
             list multi-routing-engine-item {
               leaf re-name {
                 type string;
               }
               choice output-tags {
                 case actual-tag {
                   container isis-database-information {
                     uses isis-database-information-block;
                   }
                 }
               }
             }
           }
         }
       }
     }
   }
   rpc get-isis-hostname-information {
     description "Show IS-IS hostname database";
     input {
       choice daemon-select {
         case logical-system {
           leaf logical-system {
             description "Name of logical system, or 'all'";
             type string {
             }
           }
         }
       }
     }
     output {
       choice output-tags {
         case actual-tag {
           container isis-hostname-information {
             uses isis-hostname-information-block;
           }
         }
         case multichassis-tag {
           container multi-routing-engine-results {
             list multi-routing-engine-item {
               leaf re-name {
                 type string;
               }
               choice output-tags {
                 case actual-tag {
                   container isis-hostname-information {
                     uses isis-hostname-information-block;
                   }
                 }
               }
             }
           }
         }
       }
     }
   }
   rpc get-isis-interface-information {
     description "Show IS-IS interface information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf interface-name {
         description "Name of interface";
         type string;
       }
     }
     output {
       choice output-tags {
         case actual-tag {
           container isis-interface-information {
             uses isis-interface-information-block;
           }
         }
         case multichassis-tag {
           container multi-routing-engine-results {
             list multi-routing-engine-item {
               leaf re-name {
                 type string;
               }
               choice output-tags {
                 case actual-tag {
                   container isis-interface-information {
                     uses isis-interface-information-block;
                   }
                 }
               }
             }
           }
         }
       }
     }
   }
   rpc get-isis-interface-group-information {
     description "Show IS-IS interface-group information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output-tags {
         case actual-tag {
           container isis-interface-group-information {
             uses isis-interface-group-information-block;
           }
         }
         case multichassis-tag {
           container multi-routing-engine-results {
             list multi-routing-engine-item {
               leaf re-name {
                 type string;
               }
               choice output-tags {
                 case actual-tag {
                   container isis-interface-group-information {
                     uses isis-interface-group-information-block;
                   }
                 }
               }
             }
           }
         }
       }
     }
   }
   rpc get-isis-layer2-map-information {
     description "Show IS-IS ARP/ND mapping information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf destination {
         description "IP address of mapping entry";
         type jt:ipaddr;
       }
     }
     output {
       choice output-tags {
         case actual-tag {
           container isis-layer2-map-information {
             uses isis-layer2-map-information-block;
           }
         }
         case multichassis-tag {
           container multi-routing-engine-results {
             list multi-routing-engine-item {
               leaf re-name {
                 type string;
               }
               choice output-tags {
                 case actual-tag {
                   container isis-layer2-map-information {
                     uses isis-layer2-map-information-block;
                   }
                 }
               }
             }
           }
         }
       }
     }
   }
   rpc get-isis-overview-information {
     description "Show overview of IS-IS information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output-tags {
         case actual-tag-1 {
           container isis-overview-information-logical-system-all {
             uses isis-overview-information-logical-system-all-block;
           }
         }
         case actual-tag-2 {
           container isis-overview-information {
             uses isis-overview-information-block;
           }
         }
         case multichassis-tag {
           container multi-routing-engine-results {
             list multi-routing-engine-item {
               leaf re-name {
                 type string;
               }
               choice output-tags {
                 case actual-tag-1 {
                   container isis-overview-information-logical-system-all {
                     uses isis-overview-information-logical-system-all-block;
                   }
                 }
                 case actual-tag-2 {
                   container isis-overview-information {
                     uses isis-overview-information-block;
                   }
                 }
               }
             }
           }
         }
       }
     }
   }
   rpc get-isis-route-information {
     description "Show IS-IS routing table";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf verbosity_level {
         default "brief";
         type enumeration {
           enum "brief" {
             description "Display brief output (default)";
           }
           enum "detail" {
             description "Display detailed output";
           }
         }
       }
       leaf instance {
         description "Name of IS-IS instance";
         type string;
       }
       leaf destination {
         description "IP address and optional prefix length of destination";
         type jt:ipprefix;
       }
       leaf floodgroup {
         description "Routes belonging to a specific floodgroup";
         type string {
         }
       }
       leaf nexthop {
         description "Routes reachable through specific nexthop";
         type string;
       }
       leaf download-priority {
         description "Sorted by download priority";
         type empty;
       }
       leaf family {
         type enumeration {
           enum "inet" {
             description "Display IPv4 routes";
           }
           enum "inet6" {
             description "Display IPv6 routes";
           }
           enum "iso" {
             description "Display CLNS routes";
           }
           enum "bier" {
             description "Display bier routes";
           }
         }
       }
       leaf topology {
         description "Name of topology from which routes were learned";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output-tags {
         case actual-tag {
           container isis-route-information {
             uses isis-route-information-block;
           }
         }
         case multichassis-tag {
           container multi-routing-engine-results {
             list multi-routing-engine-item {
               leaf re-name {
                 type string;
               }
               choice output-tags {
                 case actual-tag {
                   container isis-route-information {
                     uses isis-route-information-block;
                   }
                 }
               }
             }
           }
         }
       }
     }
   }
   rpc get-isis-upa-log-information {
     description "Show log of UPA handling";
     input {
       choice daemon-select {
         case logical-system {
           leaf logical-system {
             description "Name of logical system, or 'all'";
             type string {
             }
           }
         }
       }
       leaf igp-instance {
         description "Regular expression for igp-instance names to match";
         type string;
       }
       leaf instance {
         description "Name of IS-IS instance";
         type string;
       }
       leaf level {
         description "Number of IS-IS level";
         type union {
           type string {
             pattern "<.*>|$.*";
           }
           type uint32 {
             range "1 .. 2";
           }
         }
       }
       leaf destination {
         description "IP address and optional prefix length of UPA";
         type jt:ipprefix;
       }
     }
     output {
       choice output-tags {
         case actual-tag {
           container isis-upa-information {
             uses isis-upa-information-block;
           }
         }
         case multichassis-tag {
           container multi-routing-engine-results {
             list multi-routing-engine-item {
               leaf re-name {
                 type string;
               }
               choice output-tags {
                 case actual-tag {
                   container isis-upa-information {
                     uses isis-upa-information-block;
                   }
                 }
               }
             }
           }
         }
       }
     }
   }
   rpc get-isis-purge-log-information {
     description "Show log of PURGE runs";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of IS-IS level";
         type union {
           type string {
             pattern "<.*>|$.*";
           }
           type uint32 {
             range "1 .. 2";
           }
         }
       }
     }
     output {
       choice output-tags {
         case actual-tag {
           container isis-purge-information {
             uses isis-purge-information-block;
           }
         }
         case multichassis-tag {
           container multi-routing-engine-results {
             list multi-routing-engine-item {
               leaf re-name {
                 type string;
               }
               choice output-tags {
                 case actual-tag {
                   container isis-purge-information {
                     uses isis-purge-information-block;
                   }
                 }
               }
             }
           }
         }
       }
     }
   }
   rpc get-isis-spf-log-information {
     description "Show log of SPF runs";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf instance {
         description "Name of IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output-tags {
         case actual-tag {
           container isis-spf-information {
             uses isis-spf-information-block;
           }
         }
         case multichassis-tag {
           container multi-routing-engine-results {
             list multi-routing-engine-item {
               leaf re-name {
                 type string;
               }
               choice output-tags {
                 case actual-tag {
                   container isis-spf-information {
                     uses isis-spf-information-block;
                   }
                 }
               }
             }
           }
         }
       }
     }
   }
   rpc get-isis-spf-results-information {
     description "Show results from SPF runs";
     input {
       choice daemon-select {
         case logical-system {
           leaf logical-system {
             description "Name of logical system, or 'all'";
             type string {
             }
           }
         }
       }
       leaf igp-instance {
         description "Name of igp-instance";
         type string;
       }
       leaf instance {
         description "IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output-tags {
         case actual-tag {
           container isis-spf-information {
             uses isis-spf-information-block;
           }
         }
         case multichassis-tag {
           container multi-routing-engine-results {
             list multi-routing-engine-item {
               leaf re-name {
                 type string;
               }
               choice output-tags {
                 case actual-tag {
                   container isis-spf-information {
                     uses isis-spf-information-block;
                   }
                 }
               }
             }
           }
         }
       }
     }
   }
   rpc get-isis-spf-results-brief-information {
     description "Show brief summary of SPF results";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output-tags {
         case actual-tag {
           container isis-spf-information {
             uses isis-spf-information-block;
           }
         }
         case multichassis-tag {
           container multi-routing-engine-results {
             list multi-routing-engine-item {
               leaf re-name {
                 type string;
               }
               choice output-tags {
                 case actual-tag {
                   container isis-spf-information {
                     uses isis-spf-information-block;
                   }
                 }
               }
             }
           }
         }
       }
     }
   }
   rpc get-isis-statistics-information {
     description "Show IS-IS performance statistics";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output-tags {
         case actual-tag {
           container isis-statistics-information {
             uses isis-statistics-information-block;
           }
         }
         case multichassis-tag {
           container multi-routing-engine-results {
             list multi-routing-engine-item {
               leaf re-name {
                 type string;
               }
               choice output-tags {
                 case actual-tag {
                   container isis-statistics-information {
                     uses isis-statistics-information-block;
                   }
                 }
               }
             }
           }
         }
       }
     }
   }
   rpc get-isis-interface-statistics-information {
     description "ISIS interface statistics information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf interface-name {
         description "Name of interface";
         type string;
       }
     }
     output {
       choice output-tags {
         case actual-tag {
           container isis-interface-statistics-information {
             uses isis-interface-statistics-information-block;
           }
         }
         case multichassis-tag {
           container multi-routing-engine-results {
             list multi-routing-engine-item {
               leaf re-name {
                 type string;
               }
               choice output-tags {
                 case actual-tag {
                   container isis-interface-statistics-information {
                     uses isis-interface-statistics-information-block;
                   }
                 }
               }
             }
           }
         }
       }
     }
   }
   rpc get-isis-interface-traffic-stats-information {
     description "Show aggregate SPRING traffic";
     input {
       choice daemon-select {
         case logical-system {
           leaf logical-system {
             description "Name of logical system, or 'all'";
             type string {
             }
           }
         }
       }
       leaf igp-instance {
         description "Name of igp-instance";
         type string;
       }
     }
     output {
       choice output-tags {
         case actual-tag {
           container isis-interface-traffic-statistics-information {
             uses isis-interface-traffic-statistics-information-block;
           }
         }
         case multichassis-tag {
           container multi-routing-engine-results {
             list multi-routing-engine-item {
               leaf re-name {
                 type string;
               }
               choice output-tags {
                 case actual-tag {
                   container isis-interface-traffic-statistics-information {
                     uses isis-interface-traffic-statistics-information-block;
                   }
                 }
               }
             }
           }
         }
       }
     }
   }
   rpc get-isis-spring-flex-algorithm-information {
     description "Show SPRING flex-algorithm information";
     input {
       choice daemon-select {
         case logical-system {
           leaf logical-system {
             description "Name of logical system, or 'all'";
             type string {
             }
           }
         }
       }
       leaf flex-algorithm-id {
         description "Flex Algorithm id";
         type union {
           type string {
             pattern "<.*>|$.*";
           }
           type uint32 {
             range "128 .. 255";
           }
         }
       }
       leaf igp-instance {
         description "Name of igp-instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv6-unicast" {
             description "IPv6 unicast topology";
           }
         }
       }
     }
     output {
       choice output-tags {
         case actual-tag {
           container isis-spring-flex-algorithm-information {
             uses isis-spring-flex-algorithm-information-block;
           }
         }
         case multichassis-tag {
           container multi-routing-engine-results {
             list multi-routing-engine-item {
               leaf re-name {
                 type string;
               }
               choice output-tags {
                 case actual-tag {
                   container isis-spring-flex-algorithm-information {
                     uses isis-spring-flex-algorithm-information-block;
                   }
                 }
               }
             }
           }
         }
       }
     }
   }
   rpc get-isis-spring-sensor-information {
     description "Show SPRING sensor info";
     input {
       choice daemon-select {
         case logical-system {
           leaf logical-system {
             description "Name of logical system, or 'all'";
             type string {
             }
           }
         }
       }
       leaf igp-instance {
         description "Name of igp-instance";
         type string;
       }
     }
     output {
       choice output-tags {
         case actual-tag {
           container isis-spring-sensor-information {
             uses isis-spring-sensor-information-block;
           }
         }
         case multichassis-tag {
           container multi-routing-engine-results {
             list multi-routing-engine-item {
               leaf re-name {
                 type string;
               }
               choice output-tags {
                 case actual-tag {
                   container isis-spring-sensor-information {
                     uses isis-spring-sensor-information-block;
                   }
                 }
               }
             }
           }
         }
       }
     }
   }
   rpc get-isis-srv6-sensor-information {
     description "Show SRv6 sensor info";
     input {
       choice daemon-select {
         case logical-system {
           leaf logical-system {
             description "Name of logical system, or 'all'";
             type string {
             }
           }
         }
       }
       leaf igp-instance {
         description "Name of igp-instance";
         type string;
       }
     }
     output {
       choice output-tags {
         case actual-tag {
           container isis-srv6-sensor-information {
             uses isis-srv6-sensor-information-block;
           }
         }
         case multichassis-tag {
           container multi-routing-engine-results {
             list multi-routing-engine-item {
               leaf re-name {
                 type string;
               }
               choice output-tags {
                 case actual-tag {
                   container isis-srv6-sensor-information {
                     uses isis-srv6-sensor-information-block;
                   }
                 }
               }
             }
           }
         }
       }
     }
   }
   rpc get-isis-backup-spf-results-information {
     description "Show results from backup SPF runs";
     input {
       choice daemon-select {
         case logical-system {
           leaf logical-system {
             description "Name of logical system, or 'all'";
             type string {
             }
           }
         }
       }
       leaf igp-instance {
         description "Name of igp-instance";
         type string;
       }
       leaf destination {
         description "Hostname or System-ID of remote destination";
         type string;
       }
       leaf instance {
         description "IS-IS instance";
         type string;
       }
       leaf level {
         description "Number of IS-IS level";
         type union {
           type string {
             pattern "<.*>|$.*";
           }
           type uint32 {
             range "1 .. 2";
           }
         }
       }
       leaf no-coverage {
         description "Destinations with no backup coverage";
         type empty;
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output-tags {
         case actual-tag {
           container isis-spf-information {
             uses isis-spf-information-block;
           }
         }
         case multichassis-tag {
           container multi-routing-engine-results {
             list multi-routing-engine-item {
               leaf re-name {
                 type string;
               }
               choice output-tags {
                 case actual-tag {
                   container isis-spf-information {
                     uses isis-spf-information-block;
                   }
                 }
               }
             }
           }
         }
       }
     }
   }
   rpc get-isis-backup-coverage-information {
     description "Show IS-IS backup coverage";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output-tags {
         case actual-tag {
           container isis-backup-coverage-information {
             uses isis-backup-coverage-information-block;
           }
         }
         case multichassis-tag {
           container multi-routing-engine-results {
             list multi-routing-engine-item {
               leaf re-name {
                 type string;
               }
               choice output-tags {
                 case actual-tag {
                   container isis-backup-coverage-information {
                     uses isis-backup-coverage-information-block;
                   }
                 }
               }
             }
           }
         }
       }
     }
   }
   rpc get-isis-backup-lsp-information {
     description "Show IS-IS MPLS backup LSP information";
     input {
       choice daemon-select {
         case logical-system {
           leaf logical-system {
             description "Name of logical system, or 'all'";
             type string {
             }
           }
         }
       }
       leaf igp-instance {
         description "Name of igp-instance";
         type string;
       }
     }
     output {
       choice output-tags {
         case actual-tag {
           container isis-backup-mplsp-information {
             uses isis-backup-mplsp-information-block;
           }
         }
         case multichassis-tag {
           container multi-routing-engine-results {
             list multi-routing-engine-item {
               leaf re-name {
                 type string;
               }
               choice output-tags {
                 case actual-tag {
                   container isis-backup-mplsp-information {
                     uses isis-backup-mplsp-information-block;
                   }
                 }
               }
             }
           }
         }
       }
     }
   }
   rpc get-isis-context-identifier-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf instance {
         description "Name of IS-IS instance";
         type string;
       }
     }
     output {
       choice output-tags {
         case actual-tag {
           container isis-context-information {
             uses isis-context-information-block;
           }
         }
         case multichassis-tag {
           container multi-routing-engine-results {
             list multi-routing-engine-item {
               leaf re-name {
                 type string;
               }
               choice output-tags {
                 case actual-tag {
                   container isis-context-information {
                     uses isis-context-information-block;
                   }
                 }
               }
             }
           }
         }
       }
     }
   }
   rpc get-isis-context-identifier-origin-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf id_addr {
         description "Context identifier address of session";
         type jt:ipprefix;
         mandatory true;
       }
       leaf instance {
         description "Name of IS-IS instance";
         type string;
       }
     }
     output {
       choice output-tags {
         case actual-tag {
           container isis-context-information {
             uses isis-context-information-block;
           }
         }
         case multichassis-tag {
           container multi-routing-engine-results {
             list multi-routing-engine-item {
               leaf re-name {
                 type string;
               }
               choice output-tags {
                 case actual-tag {
                   container isis-context-information {
                     uses isis-context-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping isis-adjacency-information-block {
     list isis-adjacency-instance-information {
       list isis-adjacency {
         key "interface-name system-name";
         list srv6-micro-adjacency-segment-information {
           key "srv6-micro-adjacency-segment-level";
           leaf srv6-micro-adjacency-segment-level {
             type int32;
             description
               "Micro adjacency Level";
           }
           leaf srv6-protected-micro-adjacency-segment {
             type jt:ipv6addr;
             description
               "SRv6 protected micro-adjacency-SID";
           }
           leaf srv6-unprotected-micro-adjacency-segment {
             type jt:ipv6addr;
             description
               "SRv6 unprotected micro-adjacency-SID";
           }
           leaf srv6-micro-adjacency-segment-end-point-func {
             type string;
             description
               "SRv6 micro-adjacency-SID Function";
           }
           leaf srv6-micro-adjacency-segment-flags {
             type string;
             description
               "SRv6 micro adjacency flags";
           }
           leaf srv6-micro-adjacency-segment-algorithm {
             type uint32;
             description
               "SRv6 micro adjacency algorithm";
           }
         }
         container isis-bfd-nlpid-stats {
           description
             "Nlpid state of bfd tlvs";
           leaf isis-bfd-nlpid-stats-header {
             type string;
           }
           container isis-bfd-tlv-mtids {
             description
               "Received bfd tlv mtids";
             leaf isis-bfd-tlv-mtid {
               type int32;
             }
             leaf isis-bfd-mtid-v4nlpid-state {
               type string;
             }
             leaf isis-bfd-mtid-v6nlpid-state {
               type string;
             }
           }
         }
         list snpa {
           key "snpa-type";
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
         }
         leaf interface-name {
           type string;
           description
             "Name of interface";
         }
         leaf system-name {
           type string;
           description
             "Hostname for a system";
         }
         leaf not-remote-address {
           type empty;
         }
         leaf level {
           type int32;
           description
             "IS-IS Level";
         }
         leaf adjacency-state {
           type string;
           description
             "State of the adjacency";
         }
         leaf holdtime {
           type int32;
           description
             "Delay before timing out the adjacency (default is 180 seconds)";
         }
         leaf interface-priority {
           type int32;
         }
         leaf transition-count {
           type int32;
         }
         leaf last-transition-time {
           type string;
         }
         leaf circuit-type {
           type int32;
         }
         leaf adjacency-flag {
           type string;
         }
         leaf mac-address {
           type jt:mac-addr;
         }
         leaf adjacency-topologies {
           type string;
         }
         leaf adjacency-restart-capable {
           type string;
           description
             "Restart capability of the adjacency";
         }
         leaf adjacency-advertisement {
           type string;
           description
             "State of the adjacency advertisment";
         }
         leaf lan-id {
           type string;
         }
         leaf ip-address {
           type jt:ipaddr;
         }
         leaf ipv6-address {
           type jt:ipv6addr;
         }
         leaf global-ipv6-address {
           type jt:ipv6addr;
         }
         leaf flood-ref-level {
           type int32;
         }
         leaf flood-ref-node {
           type string;
           description
             "Flood reflector";
         }
         leaf flood-ref-cluster-id {
           type uint32;
           description
             "Flood reflector cluster id";
         }
         leaf-list adjacency-segment-level {
           type int32;
         }
         leaf ipv4-adjacency-segment-id {
           type int32;
         }
         leaf ipv6-adjacency-segment-id {
           type int32;
         }
         list adjacency-segment-information {
           key "adjacency-segment-level";
           leaf adjacency-segment-level {
             type int32;
           }
           leaf ipv4-protected-adjacency-segment-id {
             type int32;
           }
           leaf ipv4-unprotected-adjacency-segment-id {
             type int32;
           }
           leaf ipv6-protected-adjacency-segment-id {
             type int32;
           }
           leaf ipv6-unprotected-adjacency-segment-id {
             type int32;
           }
           leaf adjacency-segment-flags {
             type string;
           }
         }
         list srv6-adjacency-segment-information {
           key "srv6-adjacency-segment-level";
           leaf srv6-adjacency-segment-level {
             type int32;
             description
               "Adjacency Level";
           }
           leaf srv6-protected-adjacency-segment {
             type jt:ipv6addr;
             description
               "SRv6 Protected END-X-SID";
           }
           leaf srv6-unprotected-adjacency-segment {
             type jt:ipv6addr;
             description
               "SRv6 UnProtected END-X-SID";
           }
           leaf srv6-adjacency-segment-end-point-func {
             type string;
             description
               "SRv6 END-X-SID Function";
           }
           leaf srv6-adjacency-segment-flags {
             type string;
             description
               "SRv6 Adjacency Flags";
           }
           leaf srv6-adjacency-segment-algorithm {
             type uint32;
             description
               "SRv6 Adjacency Algorithm";
           }
         }
         container bfd-tlv-information {
           description
             "Received bfd tlv in hello";
           leaf bfd-tlv-info-level {
             type string;
           }
         }
         container isis-adj-bfd-state-info {
           description
             "Adjacency bfd state information";
           leaf isis-bfd-v4-sess-state {
             type string;
           }
           leaf isis-bfd-v6-sess-state {
             type string;
           }
           leaf isis-bfd-req-state {
             type string;
           }
           leaf isis-bfd-adj-usable {
             type string;
           }
         }
         list isis-adjacency-log {
           key "adjacency-when";
           description
             "Entry describing adjacency transition";
           leaf adjacency-when {
             type string;
             description
               "Time at which the transition occurred";
           }
           leaf adjacency-state {
             type string;
             description
               "State of the adjacency";
           }
           leaf adjacency-event {
             type string;
             description
               "Event which triggered the transition";
           }
           leaf adjacency-down-reason {
             type string;
             description
               "Reason for the down transition event";
           }
         }
       }
       leaf isis-instance-name {
         type string;
         description
           "Name of ISIS instance";
       }
       leaf isis-routing-instance-name {
         type string;
         description
           "Name of Routing instance";
       }
     }
     list isis-adjacency {
       key "interface-name system-name";
       leaf interface-name {
         type string;
         description
           "Name of interface";
       }
       leaf system-name {
         type string;
         description
           "Hostname for a system";
       }
       leaf not-remote-address {
         type empty;
       }
       leaf level {
         type int32;
         description
           "IS-IS Level";
       }
       leaf adjacency-state {
         type string;
         description
           "State of the adjacency";
       }
       leaf holdtime {
         type int32;
         description
           "Delay before timing out the adjacency (default is 180 seconds)";
       }
       leaf-list snpa {
         type string;
       }
       leaf snpa-type {
         type string;
         description
           "Type of SNPA";
       }
       list pfe-port-snpa {
         key "pfe-id";
         description
           "PFE Port SNPA";
         leaf pfe-id {
           type int32;
         }
         leaf port-id {
           type int32;
         }
       }
       container network-element-port-snpa {
         description
           "Network Element Port SNPA";
         leaf port-id {
           type int32;
         }
       }
       container mstp-root-snpa {
         description
           "Multiple Spanning Tree Protocol Root SNPA";
         leaf mstp-root-id {
           type int32;
         }
       }
       list gateway-snpa {
         key "gateway-addr";
         description
           "Gateway SNPA";
         leaf gateway-addr {
           type jt:ipaddr;
         }
       }
       container layer2-domain-port-snpa {
         description
           "Layer-2 Domain Port SNPA";
         leaf port-id {
           type int32;
         }
       }
       container replication-block-snpa {
         description
           "Replication Block SNPA";
         leaf replication-block-id {
           type int32;
         }
       }
       container replication-route-snpa {
         description
           "Replication Route SNPA";
         leaf network-element-id {
           type jt:ipaddr;
         }
       }
       container layer2-multicast-port-snpa {
         description
           "Layer-2 Multicast Port SNPA";
         leaf layer2-multicast-port-id {
           type int32;
         }
       }
       container inh-snpa {
         description
           "Indirection SNPA";
         leaf inh-id {
           type int32;
         }
       }
       list srv6-micro-adjacency-segment-information {
         key "srv6-micro-adjacency-segment-level";
         leaf srv6-micro-adjacency-segment-level {
           type int32;
           description
             "Micro adjacency Level";
         }
         leaf srv6-protected-micro-adjacency-segment {
           type jt:ipv6addr;
           description
             "SRv6 protected micro-adjacency-SID";
         }
         leaf srv6-unprotected-micro-adjacency-segment {
           type jt:ipv6addr;
           description
             "SRv6 unprotected micro-adjacency-SID";
         }
         leaf srv6-micro-adjacency-segment-end-point-func {
           type string;
           description
             "SRv6 micro-adjacency-SID Function";
         }
         leaf srv6-micro-adjacency-segment-flags {
           type string;
           description
             "SRv6 micro adjacency flags";
         }
         leaf srv6-micro-adjacency-segment-algorithm {
           type uint32;
           description
             "SRv6 micro adjacency algorithm";
         }
       }
       container isis-bfd-nlpid-stats {
         description
           "Nlpid state of bfd tlvs";
         leaf isis-bfd-nlpid-stats-header {
           type string;
         }
         container isis-bfd-tlv-mtids {
           description
             "Received bfd tlv mtids";
           leaf isis-bfd-tlv-mtid {
             type int32;
           }
           leaf isis-bfd-mtid-v4nlpid-state {
             type string;
           }
           leaf isis-bfd-mtid-v6nlpid-state {
             type string;
           }
         }
       }
       leaf interface-priority {
         type int32;
       }
       leaf transition-count {
         type int32;
       }
       leaf last-transition-time {
         type string;
       }
       leaf circuit-type {
         type int32;
       }
       leaf adjacency-flag {
         type string;
       }
       leaf mac-address {
         type jt:mac-addr;
       }
       leaf adjacency-topologies {
         type string;
       }
       leaf adjacency-restart-capable {
         type string;
         description
           "Restart capability of the adjacency";
       }
       leaf adjacency-advertisement {
         type string;
         description
           "State of the adjacency advertisment";
       }
       leaf lan-id {
         type string;
       }
       leaf ip-address {
         type jt:ipaddr;
       }
       leaf ipv6-address {
         type jt:ipv6addr;
       }
       leaf global-ipv6-address {
         type jt:ipv6addr;
       }
       leaf flood-ref-level {
         type int32;
       }
       leaf flood-ref-node {
         type string;
         description
           "Flood reflector";
       }
       leaf flood-ref-cluster-id {
         type uint32;
         description
           "Flood reflector cluster id";
       }
       leaf-list adjacency-segment-level {
         type int32;
       }
       leaf ipv4-adjacency-segment-id {
         type int32;
       }
       leaf ipv6-adjacency-segment-id {
         type int32;
       }
       list adjacency-segment-information {
         key "adjacency-segment-level";
         leaf adjacency-segment-level {
           type int32;
         }
         leaf ipv4-protected-adjacency-segment-id {
           type int32;
         }
         leaf ipv4-unprotected-adjacency-segment-id {
           type int32;
         }
         leaf ipv6-protected-adjacency-segment-id {
           type int32;
         }
         leaf ipv6-unprotected-adjacency-segment-id {
           type int32;
         }
         leaf adjacency-segment-flags {
           type string;
         }
       }
       list srv6-adjacency-segment-information {
         key "srv6-adjacency-segment-level";
         leaf srv6-adjacency-segment-level {
           type int32;
           description
             "Adjacency Level";
         }
         leaf srv6-protected-adjacency-segment {
           type jt:ipv6addr;
           description
             "SRv6 Protected END-X-SID";
         }
         leaf srv6-unprotected-adjacency-segment {
           type jt:ipv6addr;
           description
             "SRv6 UnProtected END-X-SID";
         }
         leaf srv6-adjacency-segment-end-point-func {
           type string;
           description
             "SRv6 END-X-SID Function";
         }
         leaf srv6-adjacency-segment-flags {
           type string;
           description
             "SRv6 Adjacency Flags";
         }
         leaf srv6-adjacency-segment-algorithm {
           type uint32;
           description
             "SRv6 Adjacency Algorithm";
         }
       }
       container bfd-tlv-information {
         description
           "Received bfd tlv in hello";
         leaf bfd-tlv-info-level {
           type string;
         }
       }
       container isis-adj-bfd-state-info {
         description
           "Adjacency bfd state information";
         leaf isis-bfd-v4-sess-state {
           type string;
         }
         leaf isis-bfd-v6-sess-state {
           type string;
         }
         leaf isis-bfd-req-state {
           type string;
         }
         leaf isis-bfd-adj-usable {
           type string;
         }
       }
       list isis-adjacency-log {
         key "adjacency-when";
         description
           "Entry describing adjacency transition";
         leaf adjacency-when {
           type string;
           description
             "Time at which the transition occurred";
         }
         leaf adjacency-state {
           type string;
           description
             "State of the adjacency";
         }
         leaf adjacency-event {
           type string;
           description
             "Event which triggered the transition";
         }
         leaf adjacency-down-reason {
           type string;
           description
             "Reason for the down transition event";
         }
       }
     }
   }
   grouping isis-adjacency-holddown-information-block {
     list isis-adjacencyholddown {
       leaf level {
         type int32;
         description
           "IS-IS Level";
       }
       leaf active {
         type string;
       }
       leaf first-adj-up {
         type string;
       }
       leaf first-adj-down {
         type string;
       }
       leaf reset-complete {
         type string;
       }
       leaf last-holddown {
         type string;
       }
       leaf started {
         type string;
       }
       leaf network-stable {
         type string;
       }
       leaf time {
         type string;
         description
           "Time of the event";
       }
       leaf first-adj-up-time {
         type string;
       }
       leaf adj-up-count {
         type string;
       }
       leaf adjacency-holddown-when {
         type string;
       }
       leaf adjacency-holddown-state {
         type string;
       }
       leaf adjacency-holddown-event {
         type string;
       }
       leaf adjacency-holddown-reason {
         type string;
       }
     }
   }
   grouping isis-authentication-information-block {
     list isis-interface-authentication {
       key "interface-name";
       leaf interface-name {
         type string;
         description
           "Name of interface";
       }
       list isis-interface-level-authentication {
         key "level";
         leaf level {
           type int32;
           description
             "IS-IS Level";
         }
         leaf isis-interface-level-iih-authentication {
           type string;
           description
             "Authentication type for IIH packets";
         }
         leaf isis-interface-level-csn-authentication {
           type string;
           description
             "Authentication type for CSN packets";
         }
         leaf isis-interface-level-psn-authentication {
           type string;
           description
             "Authentication type for PSN packets";
         }
       }
     }
     list isis-lsp-authentication {
       key "level";
       description
         "Authentication type for LSP packets";
       leaf level {
         type int32;
         description
           "IS-IS Level";
       }
       leaf isis-level-lsp-authentication {
         type string;
         description
           "Authentication type for LSP packets";
       }
     }
   }
   grouping isis-bgporr-information-block {
     container isis-bgporr {
       leaf isis-bgporr-name {
         type string;
       }
       leaf isis-bgporr-primary {
         type jt:ipaddr;
       }
       leaf isis-bgporr-primary-active-tag {
         type string;
       }
       leaf isis-bgporr-backup {
         type jt:ipaddr;
       }
       leaf isis-bgporr-backup-active-tag {
         type string;
       }
       container isis-route {
         leaf address-prefix {
           type jt:ipaddr;
         }
         leaf level {
           type int32;
           description
             "IS-IS Level";
         }
         leaf route-version {
           type int32;
         }
         leaf metric {
           type int32;
         }
         leaf metric-type {
           type string;
         }
         leaf interface-name {
           type string;
           description
             "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf prefix-downbit {
           type int32;
         }
         leaf isis-route-priority {
           type string;
         }
         leaf isis-rt-congestion-protection-activate {
           type string;
         }
         leaf isis-rt-congestion-protection-activate-count {
           type uint32;
         }
         list isis-backup-next-hop-sid-info {
           leaf isis-backup-next-hop-label {
             type uint32;
           }
           leaf isis-backup-next-hop-label-type {
             type string;
           }
           leaf isis-backup-next-hop-srv6-sid {
             type jt:ipaddr;
           }
           leaf isis-backup-next-hop-srv6-sid-type {
             type string;
           }
           leaf isis-backup-next-hop-sid-info-node-id {
             type string;
           }
           leaf isis-backup-next-hop-sid-info-adj-local-node-id {
             type string;
           }
           leaf isis-backup-next-hop-sid-info-adj-remote-node-id {
             type string;
           }
           leaf isis-backup-next-hop-sid-info-adj-local-v4-addr {
             type jt:ipaddr;
           }
           leaf isis-backup-next-hop-sid-info-adj-remote-v4-addr {
             type jt:ipaddr;
           }
           leaf isis-backup-next-hop-sid-info-adj-local-v6-addr {
             type jt:ipaddr;
           }
           leaf isis-backup-next-hop-sid-info-adj-remote-v6-addr {
             type jt:ipaddr;
           }
           leaf isis-backup-next-hop-sid-info-adj-local-unnumbered-id {
             type uint32;
           }
           leaf isis-backup-next-hop-sid-info-adj-remote-unnumbered-id {
             type uint32;
           }
         }
         list snpa {
           key "snpa-type";
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
         }
         list isis-rt-sessid {
           description
             "Session ID associated with the route";
           leaf-list isis-rt-sessid-val {
             type uint32;
           }
           leaf-list isis-rt-sessid-ver {
             type uint32;
           }
         }
         container isis-computed-backup-paths {
           leaf isis-computed-backup-paths-type {
             type string;
           }
           leaf isis-computed-backup-paths-count {
             type uint32;
           }
           leaf isis-computed-backup-paths-valid-count {
             type uint32;
           }
           leaf isis-computed-backup-paths-rttype {
             type string;
           }
           list isis-computed-backup-path {
             leaf isis-computed-backup-path-id {
               type uint32;
             }
             leaf isis-computed-backup-path-sid-count {
               type uint32;
             }
             leaf isis-computed-backup-path-error {
               type string;
             }
           }
         }
         leaf igp-metric {
           type uint32;
         }
       }
     }
   }
   grouping isis-database-information-block {
     list isis-database {
       key "level";
       leaf level {
         type int32;
         description
           "IS-IS Level";
       }
       leaf isis-instance-name {
         type string;
         description
           "Name of ISIS instance";
       }
       leaf isis-routing-instance-name {
         type string;
         description
           "Name of Routing instance";
       }
       leaf lsp-count {
         type int32;
       }
       list isis-database-entry {
         key "lsp-id";
         leaf lsp-id {
           type string;
         }
         leaf sequence-number {
           type int64;
           description
             "History event number";
         }
         leaf checksum {
           type int32;
         }
         leaf remaining-lifetime {
           type int32;
         }
         leaf lsp-attributes {
           type string;
         }
         container isis-node-segment {
           leaf isis-node-segment-ipv4-index {
             type int32;
             description
               "IPv4 Node Segment index for this device";
           }
           leaf isis-node-segment-ipv6-index {
             type int32;
             description
               "IPv6 Node Segment index for this device";
           }
           leaf isis-node-segment-block-header {
             type empty;
             description
               "Node Segment Blocks";
           }
           list isis-node-segment-block {
             key "isis-node-segment-block-start-index";
             description
               "Node Segment Blocks related information";
             leaf isis-node-segment-block-start-index {
               type int32;
               description
                 "Starting Index for the specific Node Segment Block";
             }
             leaf isis-node-segment-block-size {
               type int32;
               description
                 "Size of the specific Node Segment Block";
             }
             leaf isis-node-segment-block-first-label {
               type int32;
               description
                 "First label allocated for the specific Node Segment Block";
             }
             leaf isis-node-segment-block-last-label {
               type int32;
               description
                 "Last label allocated for the specific Node Segment Block";
             }
           }
         }
         list isis-neighbor {
           leaf reachability-delay {
             type empty;
           }
           leaf reachability-expense {
             type empty;
           }
           leaf reachability-error {
             type empty;
           }
           leaf isis-topology-id {
             type string;
           }
           leaf is-neighbor-id {
             type string;
           }
           leaf metric {
             type int32;
           }
           leaf two-way-lsp-id {
             type string;
           }
           leaf firstfrag-lsp-id {
             type string;
           }
           list adjacency-segment-information {
             leaf adjacency-segment-type {
               type string;
             }
             leaf ipv4-adjacency-segment-id {
               type int32;
             }
             leaf ipv6-adjacency-segment-id {
               type int32;
             }
             leaf adjacency-segment-weight {
               type int32;
             }
             leaf adjacency-segment-neighbor {
               type string;
             }
             leaf adjacency-segment-flags {
               type string;
             }
           }
         }
         list isis-prefix {
           leaf protocol-name {
             type string;
           }
           leaf isis-topology-id {
             type string;
           }
           leaf address-prefix {
             type jt:ipaddr;
           }
           leaf metric {
             type int32;
           }
           leaf prefix-flag {
             type string;
           }
           leaf prefix-status {
             type string;
           }
           leaf reachability-delay {
             type empty;
           }
           leaf reachability-expense {
             type empty;
           }
           leaf reachability-error {
             type empty;
           }
         }
         container isis-header {
           leaf lsp-buffer-size {
             type int32;
           }
           leaf iid-tlv-len {
             type int32;
           }
           leaf iid {
             type int32;
           }
           leaf itids {
             type string;
           }
           leaf lsp-id {
             type string;
           }
           leaf pdu-length {
             type int32;
           }
           leaf allocated-length {
             type int32;
           }
           leaf router-id {
             type jt:ipaddr;
           }
           leaf remaining-lifetime {
             type int32;
           }
           leaf level {
             type int32;
             description
               "IS-IS Level";
           }
           leaf interface-index {
             type int32;
           }
           leaf estimated-free-bytes {
             type int32;
           }
           leaf actual-free-bytes {
             type int32;
           }
           leaf lsdb-timer-type {
             type string;
           }
           leaf lsdb-expiration-time {
             type int32;
           }
           leaf needs-rebuild {
             type empty;
           }
           leaf protocol {
             type string;
             description
               "Protocol from which route was learned";
           }
         }
         container isis-packet {
           leaf mtid {
             type string;
           }
           leaf lsp-id {
             type string;
           }
           leaf pdu-length {
             type int32;
           }
           leaf pdu-lifetime {
             type int32;
           }
           leaf checksum {
             type int32;
           }
           leaf sequence-number {
             type int64;
             description
               "History event number";
           }
           leaf lsp-attributes {
             type string;
           }
           leaf nlp-id {
             type int32;
           }
           leaf lsp-length {
             type int32;
           }
           leaf pdu-version {
             type int32;
           }
           leaf system-id-length {
             type int32;
           }
           leaf isis-packet-type {
             type int32;
           }
           leaf packet-version {
             type int32;
           }
           leaf maximum-area {
             type int32;
           }
         }
         container isis-tlv {
           leaf srv6-flags {
             type uint32;
           }
           container isis-tlv-overhead {
             leaf isis-tlv-type {
               type int32;
             }
             leaf tlv-length {
               type int32;
             }
             leaf bytes-left {
               type int32;
             }
           }
           container area-address-tlv {
             leaf address {
               type jt:ipaddr;
             }
             leaf tlv-length {
               type int32;
             }
           }
           container iid-tlv {
             leaf iid-tlv-len {
               type int32;
             }
             leaf iid {
               type int32;
             }
             leaf itids {
               type string;
             }
           }
           container lsp-buffer-size-tlv {
             leaf lsp-buffer-size {
               type int32;
             }
           }
           container protocols-tlv {
             leaf protocol {
               type string;
               description
                 "Protocol from which route was learned";
             }
           }
           container mt-tlv {
             leaf mtid {
               type string;
             }
           }
           container hostname-tlv {
             leaf hostname {
               type string;
             }
           }
           container purge-originator-tlv {
             leaf purge-originator {
               type string;
             }
             leaf purge-originator-from {
               type string;
             }
           }
           container ipaddress-tlv {
             leaf address {
               type jt:ipaddr;
             }
           }
           container ipv6address-tlv {
             leaf address {
               type jt:ipaddr;
             }
           }
           container ipv6-te-router-id-tlv {
             leaf address {
               type jt:ipaddr;
             }
           }
           container router-id-tlv {
             leaf router-id {
               type jt:ipaddr;
             }
           }
           container ext-reachability-tlv {
             leaf isis-tlv-type {
               type int32;
             }
             leaf tlv-length {
               type int32;
             }
           }
           list reachability-tlv {
             leaf isis-topology-id {
               type string;
             }
             leaf-list reachability-tlv.heading {
               type string;
             }
             leaf address-prefix {
               type jt:ipaddr;
             }
             leaf metric-flag {
               type string;
             }
             leaf metric {
               type int32;
             }
             leaf subtlv-length {
               type int32;
             }
             leaf reachability-delay {
               type empty;
             }
             leaf reachability-expense {
               type empty;
             }
             leaf reachability-error {
               type empty;
             }
             leaf prefix-status {
               type string;
             }
             leaf address {
               type jt:ipaddr;
             }
             leaf neighbor-prefix {
               type jt:ipaddr;
             }
             leaf tlv-length {
               type int32;
             }
             list isis-reachability-subtlv {
               leaf address-prefix {
                 type jt:ipaddr;
               }
               leaf prefix-err-message {
                 type empty;
               }
               container admin-groups {
                 leaf color {
                   type int32;
                 }
                 leaf no-group-flag {
                   type empty;
                 }
                 leaf-list admin-group-name {
                   type string;
                   description
                     "Name of the admin group";
                 }
                 leaf admin-group-number {
                   type int32;
                   description
                     "Number of the admin group";
                 }
               }
               container link-msd-adv-sub-tlv {
                 description
                   "Link Maximum SID Depth TLV";
                 leaf link-msd-adv-sub-tlv.heading {
                   type string;
                   description
                     "Link Maximum SID Depth TLV";
                 }
                 leaf link-msd-adv-sub-tlv-type {
                   type uint32;
                 }
                 leaf link-msd-adv-sub-tlv-length {
                   type uint32;
                 }
                 list mpls-link-msd {
                   leaf-list mpls-link-msd.heading {
                     type string;
                   }
                   leaf mpls-link-msd-type {
                     type uint32;
                   }
                   leaf mpls-link-msd-value {
                     type uint32;
                   }
                 }
               }
               list srv6-micro-adjacency-segment-information {
                 leaf srv6-micro-adjacency-seg-type {
                   type string;
                   description
                     "P2P or LAN micro-adjacency segment type";
                 }
                 leaf srv6-micro-adjacency-sid {
                   type jt:ipv6addr;
                   description
                     "Micro-adjacency-SID address";
                 }
                 leaf srv6-micro-adjacency-sid-flags {
                   type string;
                   description
                     "SRv6 micro-adjacency-SID flags";
                 }
                 leaf srv6-micro-adjacency-sid-weight {
                   type int32;
                   description
                     "SRv6 micro-adjacency-SID weight";
                 }
                 leaf srv6-micro-adjacency-sid-algorithm {
                   type int32;
                   description
                     "SRv6 micro-adjacency-SID algorithm";
                 }
                 leaf srv6-micro-adjacency-sid-flags-detail {
                   type string;
                   description
                     "SRv6 micro-adjacency-SID flags with bit field";
                 }
                 leaf srv6-micro-adjacency-sid-endpoint-func {
                   type string;
                   description
                     "SRv6 micro-adjacency-SID endpoint function";
                 }
                 leaf srv6-lan-micro-adjacency-sid-nbr-sysid {
                   type string;
                   description
                     "LAN micro-adjacency-SID neighbor system id";
                 }
                 container isis-srv6-sid-structure-info {
                   description
                     "SRv6 sid structure information";
                   leaf isis-srv6-locator-block-length {
                     type uint32;
                     description
                       "Locator block length";
                   }
                   leaf isis-srv6-locator-node-length {
                     type uint32;
                     description
                       "Locator node length";
                   }
                   leaf isis-srv6-sid-function-length {
                     type uint32;
                     description
                       "SID function length";
                   }
                   leaf isis-srv6-sid-argument-length {
                     type uint32;
                     description
                       "SID argument length";
                   }
                 }
               }
               container application-specific-attributes {
                 leaf application-specific-tlv-length {
                   type int32;
                 }
                 leaf standard-application-flags {
                   type string;
                   description
                     "Legacy bit flag for SABM";
                 }
                 leaf standard-application-bitmask-length {
                   type int32;
                 }
                 leaf standard-application-bitmask {
                   type string;
                 }
                 leaf user-application-bitmask-length {
                   type int32;
                 }
                 container isis-reachability-sub-subtlv {
                   leaf max-bandwidth {
                     type int32;
                   }
                   leaf max-reserve-bandwidth {
                     type int32;
                   }
                   leaf current-bandwidth-header {
                     type empty;
                   }
                   leaf te-metric {
                     type int32;
                     description
                       "LSP TE metric";
                   }
                   leaf uni-link-delay {
                     type int32;
                   }
                   leaf min-uni-link-delay {
                     type int32;
                   }
                   leaf max-uni-link-delay {
                     type int32;
                   }
                   leaf uni-link-delay-variation {
                     type int32;
                   }
                   leaf extended-admin-groups {
                     type string;
                   }
                   leaf isis-subtlv-type {
                     type int32;
                   }
                   container admin-groups {
                     leaf color {
                       type int32;
                     }
                     leaf no-group-flag {
                       type empty;
                     }
                     leaf-list admin-group-name {
                       type string;
                       description
                         "Name of the admin group";
                     }
                     leaf admin-group-number {
                       type int32;
                       description
                         "Number of the admin group";
                     }
                   }
                   list priority-reserve-bandwidth {
                     description
                       "Current reserve bandwidth at different priority 
                       levels";
                     leaf bandwidth-priority {
                       type int32;
                     }
                     leaf current-reserve-bandwidth {
                       type int32;
                     }
                   }
                 }
               }
               leaf local-ifindex {
                 type uint32;
                 description
                   "Local interface index";
               }
               leaf remote-ifindex {
                 type uint32;
                 description
                   "Remote interface index";
               }
               leaf flood-ref-node {
                 type string;
                 description
                   "Flood reflector";
               }
               leaf flood-ref-cluster-id {
                 type uint32;
                 description
                   "Flood reflector cluster id";
               }
               leaf max-bandwidth {
                 type int32;
               }
               leaf max-reserve-bandwidth {
                 type int32;
               }
               leaf current-bandwidth-header {
                 type empty;
               }
               leaf address {
                 type jt:ipaddr;
               }
               leaf ipv6-address {
                 type jt:ipv6addr;
               }
               leaf neighbor-prefix {
                 type jt:ipaddr;
               }
               leaf neighbor-ipv6-address {
                 type jt:ipv6addr;
                 description
                   "Neighbor ipv6 address";
               }
               leaf te-metric {
                 type int32;
                 description
                   "LSP TE metric";
               }
               leaf dste-bc-header {
                 type empty;
               }
               leaf dste-bc-model {
                 type string;
                 description
                   "DiffServ TE bandwidth constraint model";
               }
               leaf dste-bc-count {
                 type int32;
                 description
                   "DiffServ TE bandwidth constraint count";
               }
               leaf dste-bc-bw {
                 type int32;
                 description
                   "DiffServ TE bandwidth constraint BW";
               }
               leaf p2p-adj-sid-af {
                 type string;
                 description
                   "Point-to-Point adjacency SID address family";
               }
               leaf p2p-adj-sid-flags {
                 type string;
                 description
                   "Point-to-Point adjacency SID flags";
               }
               leaf p2p-adj-sid-weight {
                 type int32;
                 description
                   "Point-to-Point adjacency SID weight";
               }
               leaf p2p-adj-sid-label {
                 type string;
                 description
                   "Point-to-Point adjacency SID label";
               }
               leaf lan-adj-sid-af {
                 type string;
                 description
                   "LAN adjacency SID address family";
               }
               leaf lan-adj-sid-flags {
                 type string;
                 description
                   "LAN adjacency SID flags";
               }
               leaf lan-adj-sid-weight {
                 type int32;
                 description
                   "LAN adjacency SID weight";
               }
               leaf lan-adj-sid-sysid {
                 type string;
                 description
                   "LAN adjacency SID neighbor system id";
               }
               leaf lan-adj-sid-label {
                 type string;
                 description
                   "LAN adjacency SID label";
               }
               leaf uni-link-delay {
                 type int32;
               }
               leaf min-uni-link-delay {
                 type int32;
               }
               leaf max-uni-link-delay {
                 type int32;
               }
               leaf uni-link-delay-variation {
                 type int32;
               }
               leaf extended-admin-groups {
                 type string;
               }
               leaf isis-subtlv-type {
                 type int32;
               }
               leaf subtlv-length {
                 type int32;
               }
               list priority-reserve-bandwidth {
                 description
                   "Current reserve bandwidth at different priority levels";
                 leaf bandwidth-priority {
                   type int32;
                 }
                 leaf current-reserve-bandwidth {
                   type int32;
                 }
               }
               list adjacency-segment-information {
                 leaf adjacency-segment-type {
                   type string;
                 }
                 leaf ipv4-adjacency-segment-id {
                   type int32;
                 }
                 leaf ipv6-adjacency-segment-id {
                   type int32;
                 }
                 leaf adjacency-segment-weight {
                   type int32;
                 }
                 leaf adjacency-segment-neighbor {
                   type string;
                 }
                 leaf adjacency-segment-flags {
                   type string;
                 }
               }
               list srv6-end-x-segment-information {
                 leaf srv6-end-x-seg-type {
                   type string;
                   description
                     "P2P or LAN End-X-SID segment type";
                 }
                 leaf srv6-end-x-sid {
                   type jt:ipv6addr;
                   description
                     "END-X-SID prefix";
                 }
                 leaf srv6-end-x-sid-flags {
                   type string;
                   description
                     "SRv6 End-X-SID flags";
                 }
                 leaf srv6-end-x-sid-weight {
                   type int32;
                   description
                     "SRv6 End-X-SID weight";
                 }
                 leaf srv6-end-x-sid-algorithm {
                   type int32;
                   description
                     "SRv6 End-X-SID algorithm";
                 }
                 leaf srv6-end-x-sid-flags-detail {
                   type string;
                   description
                     "SRv6 End-X-SID flags with bit field";
                 }
                 leaf srv6-end-x-sid-endpoint-func {
                   type string;
                   description
                     "SRv6 End-X-SID EndPoint Function";
                 }
                 leaf srv6-lan-end-x-sid-nbr-sysid {
                   type string;
                   description
                     "LAN END-X-SID neighbor system id";
                 }
               }
             }
           }
           container isis-iso-prefix-tlv {
             leaf isis-iso-prefix-tlv.heading {
               type string;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf iso-prefix {
               type string;
             }
           }
           container isis-prefix-subtlv {
             container isis-bier-info-sub-tlv {
             }
           }
           container ipv6-reachability-tlv {
             leaf isis-topology-id {
               type string;
             }
             leaf ipv6-reachability-tlv.heading {
               type string;
             }
             leaf ipv6-address {
               type jt:ipv6addr;
             }
             leaf metric {
               type int32;
             }
             leaf prefix-extern {
               type empty;
             }
             leaf prefix-downflag {
               type empty;
             }
             leaf subtlv-size {
               type int32;
             }
             container isis-prefix-subtlv {
               container isis-prefix-tag {
                 leaf isis-prefix-tag-index {
                   type int32;
                 }
                 leaf isis-prefix-tag-value {
                   type int32;
                 }
               }
               container isis-prefix-sid {
                 leaf isis-prefix-sid-type {
                   type string;
                 }
                 leaf isis-prefix-sid-flags {
                   type string;
                 }
                 leaf isis-prefix-sid-algorithm {
                   type string;
                 }
                 leaf isis-prefix-sid-value {
                   type string;
                 }
               }
               container isis-flex-algo-prefix-metric {
                 leaf isis-flex-algorithm-metric {
                   type string;
                 }
                 leaf isis-flex-algorithm-id {
                   type string;
                 }
               }
               container isis-crh-sid {
                 leaf isis-crh-sid-type {
                   type string;
                 }
                 leaf isis-crh-sid-flags {
                   type string;
                 }
                 leaf isis-crh-sid-algorithm {
                   type string;
                 }
                 leaf isis-crh-sid-value {
                   type string;
                 }
               }
               container isis-prefix-attribute-sub-tlv {
                 leaf isis-prefix-attribute-flags {
                   type string;
                 }
               }
               container isis-prefix-ipv4-source-rtrid-sub-tlv {
                 leaf isis-prefix-ipv4-source-rtrid {
                   type string;
                 }
               }
               container isis-prefix-ipv6-source-rtrid-sub-tlv {
                 leaf isis-prefix-ipv6-source-rtrid {
                   type string;
                 }
               }
               container isis-bier-info-sub-tlv {
                 leaf isis-bier-info-subdomain-id {
                   type string;
                 }
                 leaf isis-bier-info-bfr-id {
                   type string;
                 }
                 leaf isis-bier-info-bier-algo {
                   type string;
                 }
                 leaf isis-bier-info-igp-algo {
                   type string;
                 }
                 container isis-bier-mpls-encap-sub-tlv {
                   leaf isis-bier-mpls-max-si {
                     type string;
                   }
                   leaf isis-bier-mpls-bs-len {
                     type string;
                   }
                   leaf isis-bier-mpls-label {
                     type string;
                   }
                 }
               }
             }
           }
           list isis-reachability-subtlv {
             leaf local-ifindex {
               type uint32;
               description
                 "Local interface index";
             }
             leaf remote-ifindex {
               type uint32;
               description
                 "Remote interface index";
             }
             leaf flood-ref-node {
               type string;
               description
                 "Flood reflector";
             }
             leaf flood-ref-cluster-id {
               type uint32;
               description
                 "Flood reflector cluster id";
             }
             leaf max-bandwidth {
               type int32;
             }
             leaf max-reserve-bandwidth {
               type int32;
             }
             leaf current-bandwidth-header {
               type empty;
             }
             leaf address {
               type jt:ipaddr;
             }
             leaf ipv6-address {
               type jt:ipv6addr;
             }
             leaf neighbor-prefix {
               type jt:ipaddr;
             }
             leaf neighbor-ipv6-address {
               type jt:ipv6addr;
               description
                 "Neighbor ipv6 address";
             }
             leaf te-metric {
               type int32;
               description
                 "LSP TE metric";
             }
             leaf dste-bc-header {
               type empty;
             }
             leaf dste-bc-model {
               type string;
               description
                 "DiffServ TE bandwidth constraint model";
             }
             leaf dste-bc-count {
               type int32;
               description
                 "DiffServ TE bandwidth constraint count";
             }
             leaf dste-bc-bw {
               type int32;
               description
                 "DiffServ TE bandwidth constraint BW";
             }
             leaf p2p-adj-sid-af {
               type string;
               description
                 "Point-to-Point adjacency SID address family";
             }
             leaf p2p-adj-sid-flags {
               type string;
               description
                 "Point-to-Point adjacency SID flags";
             }
             leaf p2p-adj-sid-weight {
               type int32;
               description
                 "Point-to-Point adjacency SID weight";
             }
             leaf p2p-adj-sid-label {
               type string;
               description
                 "Point-to-Point adjacency SID label";
             }
             leaf lan-adj-sid-af {
               type string;
               description
                 "LAN adjacency SID address family";
             }
             leaf lan-adj-sid-flags {
               type string;
               description
                 "LAN adjacency SID flags";
             }
             leaf lan-adj-sid-weight {
               type int32;
               description
                 "LAN adjacency SID weight";
             }
             leaf lan-adj-sid-sysid {
               type string;
               description
                 "LAN adjacency SID neighbor system id";
             }
             leaf lan-adj-sid-label {
               type string;
               description
                 "LAN adjacency SID label";
             }
             leaf uni-link-delay {
               type int32;
             }
             leaf min-uni-link-delay {
               type int32;
             }
             leaf max-uni-link-delay {
               type int32;
             }
             leaf uni-link-delay-variation {
               type int32;
             }
             leaf extended-admin-groups {
               type string;
             }
             leaf isis-subtlv-type {
               type int32;
             }
             leaf subtlv-length {
               type int32;
             }
             leaf address-prefix {
               type jt:ipaddr;
             }
             leaf prefix-err-message {
               type empty;
             }
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
             list priority-reserve-bandwidth {
               description
                 "Current reserve bandwidth at different priority levels";
               leaf bandwidth-priority {
                 type int32;
               }
               leaf current-reserve-bandwidth {
                 type int32;
               }
             }
             container link-msd-adv-sub-tlv {
               description
                 "Link Maximum SID Depth TLV";
               leaf link-msd-adv-sub-tlv.heading {
                 type string;
                 description
                   "Link Maximum SID Depth TLV";
               }
               leaf link-msd-adv-sub-tlv-type {
                 type uint32;
               }
               leaf link-msd-adv-sub-tlv-length {
                 type uint32;
               }
               list mpls-link-msd {
                 leaf-list mpls-link-msd.heading {
                   type string;
                 }
                 leaf mpls-link-msd-type {
                   type uint32;
                 }
                 leaf mpls-link-msd-value {
                   type uint32;
                 }
               }
             }
             list adjacency-segment-information {
               leaf adjacency-segment-type {
                 type string;
               }
               leaf ipv4-adjacency-segment-id {
                 type int32;
               }
               leaf ipv6-adjacency-segment-id {
                 type int32;
               }
               leaf adjacency-segment-weight {
                 type int32;
               }
               leaf adjacency-segment-neighbor {
                 type string;
               }
               leaf adjacency-segment-flags {
                 type string;
               }
             }
             list srv6-end-x-segment-information {
               leaf srv6-end-x-seg-type {
                 type string;
                 description
                   "P2P or LAN End-X-SID segment type";
               }
               leaf srv6-end-x-sid {
                 type jt:ipv6addr;
                 description
                   "END-X-SID prefix";
               }
               leaf srv6-end-x-sid-flags {
                 type string;
                 description
                   "SRv6 End-X-SID flags";
               }
               leaf srv6-end-x-sid-weight {
                 type int32;
                 description
                   "SRv6 End-X-SID weight";
               }
               leaf srv6-end-x-sid-algorithm {
                 type int32;
                 description
                   "SRv6 End-X-SID algorithm";
               }
               leaf srv6-end-x-sid-flags-detail {
                 type string;
                 description
                   "SRv6 End-X-SID flags with bit field";
               }
               leaf srv6-end-x-sid-endpoint-func {
                 type string;
                 description
                   "SRv6 End-X-SID EndPoint Function";
               }
               leaf srv6-lan-end-x-sid-nbr-sysid {
                 type string;
                 description
                   "LAN END-X-SID neighbor system id";
               }
             }
             list srv6-micro-adjacency-segment-information {
               leaf srv6-micro-adjacency-seg-type {
                 type string;
                 description
                   "P2P or LAN micro-adjacency segment type";
               }
               leaf srv6-micro-adjacency-sid {
                 type jt:ipv6addr;
                 description
                   "Micro-adjacency-SID address";
               }
               leaf srv6-micro-adjacency-sid-flags {
                 type string;
                 description
                   "SRv6 micro-adjacency-SID flags";
               }
               leaf srv6-micro-adjacency-sid-weight {
                 type int32;
                 description
                   "SRv6 micro-adjacency-SID weight";
               }
               leaf srv6-micro-adjacency-sid-algorithm {
                 type int32;
                 description
                   "SRv6 micro-adjacency-SID algorithm";
               }
               leaf srv6-micro-adjacency-sid-flags-detail {
                 type string;
                 description
                   "SRv6 micro-adjacency-SID flags with bit field";
               }
               leaf srv6-micro-adjacency-sid-endpoint-func {
                 type string;
                 description
                   "SRv6 micro-adjacency-SID endpoint function";
               }
               leaf srv6-lan-micro-adjacency-sid-nbr-sysid {
                 type string;
                 description
                   "LAN micro-adjacency-SID neighbor system id";
               }
               container isis-srv6-sid-structure-info {
                 description
                   "SRv6 sid structure information";
                 leaf isis-srv6-locator-block-length {
                   type uint32;
                   description
                     "Locator block length";
                 }
                 leaf isis-srv6-locator-node-length {
                   type uint32;
                   description
                     "Locator node length";
                 }
                 leaf isis-srv6-sid-function-length {
                   type uint32;
                   description
                     "SID function length";
                 }
                 leaf isis-srv6-sid-argument-length {
                   type uint32;
                   description
                     "SID argument length";
                 }
               }
             }
             container application-specific-attributes {
               leaf application-specific-tlv-length {
                 type int32;
               }
               leaf standard-application-flags {
                 type string;
                 description
                   "Legacy bit flag for SABM";
               }
               leaf standard-application-bitmask-length {
                 type int32;
               }
               leaf standard-application-bitmask {
                 type string;
               }
               leaf user-application-bitmask-length {
                 type int32;
               }
               container isis-reachability-sub-subtlv {
                 leaf max-bandwidth {
                   type int32;
                 }
                 leaf max-reserve-bandwidth {
                   type int32;
                 }
                 leaf current-bandwidth-header {
                   type empty;
                 }
                 leaf te-metric {
                   type int32;
                   description
                     "LSP TE metric";
                 }
                 leaf uni-link-delay {
                   type int32;
                 }
                 leaf min-uni-link-delay {
                   type int32;
                 }
                 leaf max-uni-link-delay {
                   type int32;
                 }
                 leaf uni-link-delay-variation {
                   type int32;
                 }
                 leaf extended-admin-groups {
                   type string;
                 }
                 leaf isis-subtlv-type {
                   type int32;
                 }
                 container admin-groups {
                   leaf color {
                     type int32;
                   }
                   leaf no-group-flag {
                     type empty;
                   }
                   leaf-list admin-group-name {
                     type string;
                     description
                       "Name of the admin group";
                   }
                   leaf admin-group-number {
                     type int32;
                     description
                       "Number of the admin group";
                   }
                 }
                 list priority-reserve-bandwidth {
                   description
                     "Current reserve bandwidth at different priority levels";
                   leaf bandwidth-priority {
                     type int32;
                   }
                   leaf current-reserve-bandwidth {
                     type int32;
                   }
                 }
               }
             }
           }
           container node-msd-adv-sub-tlv {
           }
           container rtr-capability-tlv {
             leaf rtr-capability-tlv.heading {
               type string;
             }
             leaf router-id {
               type jt:ipaddr;
             }
             leaf rtr-cap-flags {
               type string;
             }
             container spring-capability-sub-tlv {
               leaf spring-capability-flags {
                 type string;
               }
               leaf spring-capability-range {
                 type uint32;
               }
               leaf spring-capability-sid-label {
                 type uint32;
               }
             }
             container spring-algorithm-sub-tlv {
               leaf spring-algorithm-type {
                 type uint32;
               }
             }
             container crh-capability-sub-tlv {
               leaf crh-capability-type {
                 type uint32;
               }
             }
             container flex-algorithm-sub-tlv {
               leaf system-name {
                 type string;
                 description
                   "Hostname for a system";
               }
               leaf flex-algorithm-id {
                 type uint32;
                 description
                   "SRV6 locator flex algorithm";
               }
               leaf flex-algorithm-subtlv-length {
                 type uint32;
               }
               leaf flex-algorithm-metric-str {
                 type string;
               }
               leaf flex-algorithm-calc-str {
                 type string;
               }
               leaf flex-algorithm-metric-type {
                 type uint32;
               }
               leaf flex-algorithm-calc-type {
                 type uint32;
               }
               leaf flex-algorithm-priority {
                 type uint32;
               }
               leaf flex-algorithm-flags {
                 type string;
               }
               leaf flex-algorithm-include-any {
                 type string;
               }
               leaf flex-algorithm-include-all {
                 type string;
               }
               leaf flex-algorithm-exclude {
                 type string;
               }
               leaf flex-algorithm-srlg-exclude {
                 type string;
               }
               leaf participation-reason {
                 type string;
               }
               leaf flex-algorithm-po-flags {
                 type uint32;
               }
               leaf flex-algorithm-po-res {
                 type uint32;
               }
               leaf flex-algorithm-po-offset {
                 type uint32;
               }
               container flex-algorithm-include-any-detail {
                 container admin-groups {
                   leaf color {
                     type int32;
                   }
                   leaf no-group-flag {
                     type empty;
                   }
                   leaf-list admin-group-name {
                     type string;
                     description
                       "Name of the admin group";
                   }
                   leaf admin-group-number {
                     type int32;
                     description
                       "Number of the admin group";
                   }
                 }
               }
               container flex-algorithm-include-all-detail {
                 container admin-groups {
                   leaf color {
                     type int32;
                   }
                   leaf no-group-flag {
                     type empty;
                   }
                   leaf-list admin-group-name {
                     type string;
                     description
                       "Name of the admin group";
                   }
                   leaf admin-group-number {
                     type int32;
                     description
                       "Number of the admin group";
                   }
                 }
               }
               container flex-algorithm-exclude-detail {
                 container admin-groups {
                   leaf color {
                     type int32;
                   }
                   leaf no-group-flag {
                     type empty;
                   }
                   leaf-list admin-group-name {
                     type string;
                     description
                       "Name of the admin group";
                   }
                   leaf admin-group-number {
                     type int32;
                     description
                       "Number of the admin group";
                   }
                 }
               }
               container flex-algorithm-srlg-exclude-detail {
                 leaf flex-algorithm-srlg-exclude-detail.heading {
                   type string;
                 }
                 leaf-list srlg-name {
                   type string;
                   description
                     "Name of the srlg";
                 }
               }
             }
             container ipv6-te-router-id-sub-tlv {
               leaf ipv6-te-router-id {
                 type jt:ipv6addr;
               }
             }
             container srv6-cap-sub-tlv {
               leaf srv6-cap-flags {
                 type uint32;
               }
             }
             container node-msd-adv-sub-tlv {
               leaf node-msd-adv-sub-tlv.heading {
                 type string;
               }
               leaf msd-type {
                 type uint32;
               }
               leaf msd-length {
                 type uint32;
               }
               container srh-max-sl-sub-tlv {
                 leaf srh-max-sl-sub-tlv.heading {
                   type string;
                 }
                 leaf sl-max-type {
                   type uint32;
                 }
                 leaf sl-max-value {
                   type uint32;
                 }
               }
               container mpls-node-msd {
                 leaf mpls-node-msd.heading {
                   type string;
                 }
                 leaf mpls-node-msd-type {
                   type uint32;
                 }
                 leaf mpls-node-msd-value {
                   type uint32;
                 }
               }
             }
             container srms-preference-sub-tlv {
               leaf srms-preference {
                 type uint32;
               }
             }
             container unknown-sub-tlv {
               leaf isis-tlv-type {
                 type int32;
               }
               leaf tlv-length {
                 type int32;
               }
             }
           }
           container authentication-tlv {
             leaf tlv-length {
               type int32;
             }
           }
           container idrp-tlv {
             leaf tlv-length {
               type int32;
             }
           }
           list ip-prefix-tlv {
             leaf isis-topology-id {
               type string;
             }
             leaf-list ip-prefix-tlv.heading {
               type string;
             }
             leaf address-prefix {
               type jt:ipaddr;
             }
             leaf metric {
               type int32;
             }
             leaf prefix-status {
               type string;
             }
             leaf subtlv-size {
               type int32;
             }
             container isis-prefix-subtlv {
               container isis-prefix-tag {
                 leaf isis-prefix-tag-index {
                   type int32;
                 }
                 leaf isis-prefix-tag-value {
                   type int32;
                 }
               }
               container isis-prefix-sid {
                 leaf isis-prefix-sid-type {
                   type string;
                 }
                 leaf isis-prefix-sid-flags {
                   type string;
                 }
                 leaf isis-prefix-sid-algorithm {
                   type string;
                 }
                 leaf isis-prefix-sid-value {
                   type string;
                 }
               }
               container isis-flex-algo-prefix-metric {
                 leaf isis-flex-algorithm-metric {
                   type string;
                 }
                 leaf isis-flex-algorithm-id {
                   type string;
                 }
               }
               container isis-prefix-attribute-sub-tlv {
                 leaf isis-prefix-attribute-flags {
                   type string;
                 }
               }
               container isis-prefix-ipv4-source-rtrid-sub-tlv {
                 leaf isis-prefix-ipv4-source-rtrid {
                   type string;
                 }
               }
               container isis-prefix-ipv6-source-rtrid-sub-tlv {
                 leaf isis-prefix-ipv6-source-rtrid {
                   type string;
                 }
               }
               container isis-bier-info-sub-tlv {
                 leaf isis-bier-info-subdomain-id {
                   type string;
                 }
                 leaf isis-bier-info-bfr-id {
                   type string;
                 }
                 leaf isis-bier-info-bier-algo {
                   type string;
                 }
                 leaf isis-bier-info-igp-algo {
                   type string;
                 }
                 container isis-bier-mpls-encap-sub-tlv {
                   leaf isis-bier-mpls-max-si {
                     type string;
                   }
                   leaf isis-bier-mpls-bs-len {
                     type string;
                   }
                   leaf isis-bier-mpls-label {
                     type string;
                   }
                 }
               }
             }
           }
           list isis-ipv6-srlg-tlv {
             key "ipv6-srlg-address";
             leaf-list isis-ipv6-srlg-tlv.heading {
               type string;
             }
             leaf address-prefix {
               type jt:ipaddr;
             }
             leaf ipv6-srlg-flag {
               type string;
             }
             leaf ipv6-srlg-address {
               type jt:ipv6addr;
             }
             leaf ipv6-srlg-neighbor-address {
               type jt:ipv6addr;
             }
             container isis-ipv6-srlg-value {
               leaf isis-ipv6-srlg-value.heading {
                 type string;
               }
               leaf-list isis-ipv6-srlg-name {
                 type string;
               }
             }
           }
           container isis-srlg-tlv {
             leaf isis-srlg-tlv.heading {
               type string;
             }
             leaf address-prefix {
               type jt:ipaddr;
             }
             leaf srlg-flag {
               type string;
             }
             leaf srlg-address {
               type jt:ipaddr;
             }
             leaf srlg-neighbor-prefix {
               type jt:ipaddr;
             }
             leaf srlg-local-ifindex {
               type uint32;
               description
                 "Local interface index";
             }
             leaf srlg-remote-ifindex {
               type uint32;
               description
                 "Remote interface index";
             }
             container isis-srlg-value {
               leaf isis-srlg-value.heading {
                 type string;
               }
               leaf-list isis-srlg-name {
                 type string;
               }
             }
           }
           container isis-as-srlg-tlv {
             leaf as-srlg-tlv-length {
               type int32;
             }
             leaf as-srlg-address-prefix {
               type string;
               description
                 "Legacy bit flag for SABM";
             }
             leaf as-srlg-flags {
               type string;
               description
                 "Legacy bit flag for SABM";
             }
             leaf as-srlg-standard-application-bitmask-length {
               type int32;
             }
             leaf as-srlg-standard-application-bitmask {
               type string;
             }
             leaf as-srlg-user-application-bitmask-length {
               type int32;
             }
             leaf as-srlg-address {
               type jt:ipaddr;
             }
             leaf as-srlg-neighbor-prefix {
               type jt:ipaddr;
             }
             leaf as-srlg-ipv6-address {
               type jt:ipv6addr;
             }
             leaf as-srlg-ipv6-neighbor-prefix {
               type jt:ipv6addr;
             }
             leaf as-srlg-local-ifindex {
               type uint32;
               description
                 "Local interface index";
             }
             leaf as-srlg-remote-ifindex {
               type uint32;
               description
                 "Remote interface index";
             }
             container isis-as-srlg-value {
               leaf isis-as-srlg-value.heading {
                 type string;
               }
               leaf-list isis-as-srlg-name {
                 type string;
               }
             }
           }
           container label-binding-tlv {
             leaf protocol-name {
               type string;
             }
             leaf address-prefix {
               type jt:ipaddr;
             }
             leaf label-binding-flags {
               type string;
             }
             leaf label-binding-weight {
               type int32;
             }
             leaf label-binding-range {
               type int32;
             }
             leaf isis-label {
               type int32;
             }
             container isis-prefix-sid {
               leaf isis-prefix-sid-type {
                 type string;
               }
               leaf isis-prefix-sid-flags {
                 type string;
               }
               leaf isis-prefix-sid-algorithm {
                 type string;
               }
               leaf isis-prefix-sid-value {
                 type string;
               }
             }
           }
           container unknown-tlv {
             leaf isis-tlv-type {
               type int32;
             }
             leaf tlv-length {
               type int32;
             }
           }
           container tlv-stragglers {
             leaf bytes-left {
               type int32;
             }
           }
           container srv6-locator-micro-sid-tlv {
           }
           container isis-srv6-locator-tlv {
             leaf isis-srv6-locator-tlv.heading {
               type string;
             }
             leaf address-prefix {
               type jt:ipaddr;
             }
             leaf srv6-metric {
               type uint32;
             }
             leaf srv6-mtid {
               type uint32;
             }
             leaf srv6-flags {
               type uint32;
             }
             leaf srv6-algorithm {
               type uint32;
             }
             leaf sid-flags {
               type uint32;
             }
             leaf micro-sid-flags {
               type uint32;
             }
             leaf isis-prefix-attribute-flags {
               type string;
             }
             leaf isis-subtlv-type {
               type int32;
             }
             leaf subtlv-length {
               type int32;
             }
             container isis-srv6-locator-tag {
               leaf isis-srv6-locator-tag-index {
                 type int32;
               }
               leaf isis-srv6-locator-tag-value {
                 type int32;
               }
             }
             container srv6-locator-sid-tlv {
               leaf isis-srv6-locator-sid-address {
                 type jt:ipv6addr;
               }
               leaf isis-srv6-locator-sid-func {
                 type string;
               }
             }
             container srv6-locator-micro-sid-tlv {
               leaf isis-srv6-locator-micro-sid-address {
                 type jt:ipv6addr;
               }
               leaf isis-srv6-locator-micro-sid-func {
                 type string;
               }
               container isis-srv6-sid-structure-info {
                 description
                   "SRv6 sid structure information";
                 leaf isis-srv6-locator-block-length {
                   type uint32;
                   description
                     "Locator block length";
                 }
                 leaf isis-srv6-locator-node-length {
                   type uint32;
                   description
                     "Locator node length";
                 }
                 leaf isis-srv6-sid-function-length {
                   type uint32;
                   description
                     "SID function length";
                 }
                 leaf isis-srv6-sid-argument-length {
                   type uint32;
                   description
                     "SID argument length";
                 }
               }
             }
           }
           leaf isis-tlv.heading {
             type string;
           }
         }
         container isis-es-neighbor {
           leaf reachability-delay {
             type empty;
           }
           leaf reachability-expense {
             type empty;
           }
           leaf reachability-error {
             type empty;
           }
           leaf es-neighbor-id {
             type string;
           }
           leaf metric {
             type int32;
           }
           leaf es-neighbor-status {
             type string;
           }
         }
         container isis-label-binding {
           leaf protocol-name {
             type string;
           }
           leaf address-prefix {
             type jt:ipaddr;
           }
           leaf isis-label {
             type int32;
           }
           leaf binding-flags {
             type string;
           }
         }
         container isis-srv6-locator-tlv {
           container srv6-locator-micro-sid-tlv {
             leaf isis-srv6-locator-micro-sid-address {
               type jt:ipv6addr;
             }
             leaf isis-srv6-locator-micro-sid-func {
               type string;
             }
             container isis-srv6-sid-structure-info {
               description
                 "SRv6 sid structure information";
               leaf isis-srv6-locator-block-length {
                 type uint32;
                 description
                   "Locator block length";
               }
               leaf isis-srv6-locator-node-length {
                 type uint32;
                 description
                   "Locator node length";
               }
               leaf isis-srv6-sid-function-length {
                 type uint32;
                 description
                   "SID function length";
               }
               leaf isis-srv6-sid-argument-length {
                 type uint32;
                 description
                   "SID argument length";
               }
             }
           }
           leaf isis-srv6-locator-tlv.heading {
             type string;
           }
           leaf address-prefix {
             type jt:ipaddr;
           }
           leaf srv6-metric {
             type uint32;
           }
           leaf srv6-mtid {
             type uint32;
           }
           leaf srv6-flags {
             type uint32;
           }
           leaf srv6-algorithm {
             type uint32;
           }
           leaf sid-flags {
             type uint32;
           }
           leaf micro-sid-flags {
             type uint32;
           }
           leaf isis-prefix-attribute-flags {
             type string;
           }
           leaf isis-subtlv-type {
             type int32;
           }
           leaf subtlv-length {
             type int32;
           }
           container isis-srv6-locator-tag {
             leaf isis-srv6-locator-tag-index {
               type int32;
             }
             leaf isis-srv6-locator-tag-value {
               type int32;
             }
           }
           container srv6-locator-sid-tlv {
             leaf isis-srv6-locator-sid-address {
               type jt:ipv6addr;
             }
             leaf isis-srv6-locator-sid-func {
               type string;
             }
           }
         }
         leaf lsp-stub {
           type empty;
         }
         container transmission-status {
           leaf transmit-count {
             type int32;
           }
           leaf message {
             type string;
           }
           leaf interface-name {
             type string;
             description
               "Name of interface";
           }
           leaf transmit-time {
             type string;
             description
               "Time at which this message is queued for transmission";
           }
         }
       }
     }
   }
   grouping isis-hostname-information-block {
     list isis-hostname {
       key "system-id";
       description
         "Entry in the system-ID-to-hostname mapping table";
       leaf system-id {
         type string;
         description
           "Six-octet ISO system ID for a system";
       }
       leaf system-name {
         type string;
         description
           "Hostname for a system";
       }
       leaf isis-hostname-type {
         type string;
         description
           "Type of system-ID-to-hostname mapping";
       }
     }
   }
   grouping isis-interface-information-block {
     list isis-interface {
       key "interface-name";
       leaf interface-name {
         type string;
         description
           "Name of interface";
       }
       leaf circuit-type {
         type int32;
       }
       leaf circuit-id {
         type int32;
       }
       leaf isis-interface-state-one {
         type string;
       }
       leaf dr-id-one {
         type string;
       }
       leaf isis-interface-state-two {
         type string;
       }
       leaf dr-id-two {
         type string;
       }
       leaf metric-one {
         type int32;
       }
       leaf metric-two {
         type int32;
       }
       leaf isis-flood-reduction-enabled {
         type string;
         description
           "Distributed Optimized flood reduction";
       }
       leaf isis-flood-reduction-hash-reflooder-enabled {
         type string;
         description
           "Distributed Optimized flood reduction hash reflooder";
       }
       list interface-level-data {
         key "level";
         leaf igp-metric {
           type uint32;
         }
         leaf level {
           type int32;
           description
             "IS-IS Level";
         }
         leaf adjacency-count {
           type int32;
         }
         leaf interface-priority {
           type int32;
         }
         leaf metric {
           type int32;
         }
         leaf passive {
           type string;
         }
         leaf hello-time {
           type jt:unsigned-float;
         }
         leaf holdtime {
           type int32;
           description
             "Delay before timing out the adjacency (default is 180 seconds)";
         }
         leaf dr-id-one {
           type string;
         }
         leaf dr-id-two {
           type string;
         }
         leaf dr-flag {
           type string;
         }
         leaf te-metric {
           type int32;
           description
             "LSP TE metric";
         }
         leaf flex-algo-te-metric {
           type int32;
         }
         leaf tilfa-prot-link {
           type string;
         }
         leaf tilfa-prot-fate {
           type string;
         }
         leaf tilfa-prot-srlg {
           type string;
         }
         leaf tilfa-prot-node {
           type int32;
         }
         list isis-interface-level-topology {
           key "isis-topology-id";
           description
             "Topology-specific information for an interface level";
           leaf isis-topology-id {
             type string;
           }
           leaf isis-topology-metric {
             type int32;
             description
               "Metric for a topology";
           }
         }
       }
       leaf-list isis-interface.heading {
         type string;
       }
       leaf interface-index {
         type int32;
       }
       leaf interface-state-value {
         type int32;
       }
       leaf interface-disabled-flag {
         type empty;
       }
       leaf lsp-interval {
         type int32;
       }
       leaf csnp-interval {
         type int32;
       }
       leaf system-name {
         type string;
         description
           "Hostname for a system";
       }
       leaf mesh-group {
         type string;
       }
       leaf adjacency-advertisement {
         type string;
         description
           "State of the adjacency advertisment";
       }
       leaf isis-layer2-map-enabled {
         type string;
         description
           "IS-IS controls kernel ARP/ND entries for its nexthops";
       }
       leaf interface-protection-type {
         type string;
       }
       leaf no-eligible-backup {
         type empty;
       }
       leaf level {
         type int32;
         description
           "IS-IS Level";
       }
       leaf flood-ref-node {
         type string;
         description
           "Flood reflector";
       }
       leaf flood-ref-cluster-id {
         type uint32;
         description
           "Flood reflector cluster id";
       }
       leaf hello-padding {
         type string;
       }
       leaf max-hello-size {
         type int32;
       }
       leaf flood-group-iso-address {
         type string;
         description
           "ISO address of an interface LSP filter";
       }
       leaf igp-ldp-sync-state {
         type string;
         description
           "State of synchronization between Label Distribution Protocol 
           (LDP) and the interior gateway protocol (IGP)";
       }
       leaf igp-ldp-sync-last-change {
         type string;
         description
           "Time since the state of synchronization between Label 
           Distribution Protocol (LDP) and the interior gateway protocol 
           (IGP) last changed";
       }
       leaf igp-ldp-sync-reason {
         type string;
         description
           "Reason for the change in the state of synchronization between 
           Label Distribution Protocol (LDP) and the interior gateway 
           protocol (IGP)";
       }
       leaf igp-ldp-sync-holdtime {
         type string;
         description
           "Length of time during which the maximum metric is advertised for
           an interface that is in the hold-down state because 
           synchronization was lost between Label Distribution Protocol 
           (LDP) and the interior gateway protocol (IGP)";
       }
       leaf igp-ldp-sync-timeleft {
         type int32;
         description
           "Remaining amount of time the interface will remain in the 
           hold-down state because synchronization was lost between Label 
           Distribution Protocol (LDP) and the interior gateway protocol 
           (IGP)";
       }
       leaf interface-group-holddown-delay {
         type int32;
       }
       leaf interface-group-holddown-left {
         type int32;
       }
       leaf-list interface-srlg-name {
         type string;
       }
       leaf min-unidirectional-link-delay-simulated {
         type uint32;
       }
       leaf unidirectional-link-delay {
         type uint32;
       }
       leaf min-unidirectional-link-delay {
         type uint32;
       }
       leaf max-unidirectional-link-delay {
         type uint32;
       }
       leaf unidirectional-delay-variation {
         type uint32;
       }
       leaf link-delay-normalization-interval {
         type uint32;
       }
       leaf link-delay-normalization-offset {
         type uint32;
       }
       leaf link-normalized-delay {
         type uint32;
       }
       leaf link-normalized-delay-time {
         type string;
       }
       container interface-strict-bfd {
         description
           "Interface strict bfd config";
         leaf interface-bfd-family {
           type string;
         }
         leaf interface-bfdv6-family {
           type string;
         }
         leaf strict-bfd {
           type string;
         }
       }
     }
   }
   grouping isis-interface-group-information-block {
     container isis-interface-group {
       description
         "Interface-group information for an IS-IS instance";
       leaf isis-interface-group-name {
         type string;
       }
       leaf interface-name {
         type string;
         description
           "Name of interface";
       }
       leaf isis-interface-bandwidth {
         type string;
       }
       leaf isis-interface-state-updown {
         type string;
       }
       leaf isis-interface-state-ignore {
         type string;
       }
       leaf isis-interface-state-degrade {
         type string;
       }
       leaf isis-interface-weight {
         type uint32;
       }
       leaf isis-interface-group-bandwidth-nominal {
         type string;
       }
       leaf isis-interface-group-bandwidth-actual {
         type string;
       }
       list isis-level-information {
         description
           "IS-IS Level Information";
         leaf level {
           type int32;
           description
             "IS-IS Level";
         }
         container isis-bbm-information {
           leaf isis-topology-id {
             type string;
           }
           leaf isis-topology-metric-default {
             type uint32;
           }
           leaf isis-topology-metric-actual {
             type uint32;
           }
           leaf isis-bbm-bandwidth {
             type uint64;
           }
           leaf isis-bbm-metric {
             type uint32;
           }
         }
         list adjacency-segment-information {
           key "adjacency-segment-level";
           leaf adjacency-segment-level {
             type int32;
           }
           leaf ipv4-protected-adjacency-segment-id {
             type int32;
           }
           leaf ipv4-unprotected-adjacency-segment-id {
             type int32;
           }
           leaf ipv6-protected-adjacency-segment-id {
             type int32;
           }
           leaf ipv6-unprotected-adjacency-segment-id {
             type int32;
           }
           leaf adjacency-segment-flags {
             type string;
           }
         }
         container isis-adjsid-information {
           leaf isis-adjacency-segment {
             type string;
           }
           leaf isis-adjsid-type {
             type string;
           }
           leaf isis-adjsid-value {
             type uint32;
           }
           leaf isis-adjsid-nbr {
             type string;
           }
         }
       }
     }
   }
   grouping isis-layer2-map-information-block {
     list isis-layer2-map-database {
       key "instance-name";
       leaf instance-name {
         type string;
       }
       leaf ip-entry-count {
         type uint32;
       }
       leaf ip6-entry-count {
         type uint32;
       }
       list isis-layer2-map-entry {
         key "ip-address";
         leaf ip-address {
           type jt:ipaddr;
         }
         leaf interface-name2 {
           type string;
         }
         leaf-list snpa {
           type string;
         }
         leaf snpa-type {
           type string;
           description
             "Type of SNPA";
         }
         list pfe-port-snpa {
           key "pfe-id";
           description
             "PFE Port SNPA";
           leaf pfe-id {
             type int32;
           }
           leaf port-id {
             type int32;
           }
         }
         container network-element-port-snpa {
           description
             "Network Element Port SNPA";
           leaf port-id {
             type int32;
           }
         }
         container mstp-root-snpa {
           description
             "Multiple Spanning Tree Protocol Root SNPA";
           leaf mstp-root-id {
             type int32;
           }
         }
         list gateway-snpa {
           key "gateway-addr";
           description
             "Gateway SNPA";
           leaf gateway-addr {
             type jt:ipaddr;
           }
         }
         container layer2-domain-port-snpa {
           description
             "Layer-2 Domain Port SNPA";
           leaf port-id {
             type int32;
           }
         }
         container replication-block-snpa {
           description
             "Replication Block SNPA";
           leaf replication-block-id {
             type int32;
           }
         }
         container replication-route-snpa {
           description
             "Replication Route SNPA";
           leaf network-element-id {
             type jt:ipaddr;
           }
         }
         container layer2-multicast-port-snpa {
           description
             "Layer-2 Multicast Port SNPA";
           leaf layer2-multicast-port-id {
             type int32;
           }
         }
         container inh-snpa {
           description
             "Indirection SNPA";
           leaf inh-id {
             type int32;
           }
         }
         leaf isis-layer2-map-next-refresh {
           type string;
         }
         leaf-list isis-layer2-map-state {
           type string;
         }
       }
     }
   }
   grouping isis-overview-information-logical-system-all-block {
     list logical-system {
       key "name";
       leaf name {
         type string;
       }
       container route-prefix-length-distribution {
         list route-table {
           key "table-name";
           leaf table-name {
             type string;
             description
               "Unicast routing table";
           }
           list protocols {
             key "protocol-name";
             leaf protocol-name {
               type string;
             }
             leaf protocol-route-count {
               type int32;
               description
                 "Total protocol routes";
             }
             leaf active-route-count {
               type int32;
               description
                 "Active routes";
             }
           }
           list rt-prefix-dist {
             key "rt-prefix-length";
             leaf rt-prefix-length {
               type string;
             }
             leaf rt-prefix-count {
               type int32;
             }
           }
           list rt {
             key "rt-destination";
             leaf rt-destination {
               type string;
               description
                 "Route prefixes awaiting ACK";
             }
             leaf rt-prefix-length {
               type string;
             }
             list rt-entry {
               leaf active-tag {
                 type string;
                 description
                   "Visual indication of active state of this route entry";
               }
               leaf validation-state {
                 type string;
                 description
                   "Validation-state of a route";
               }
               leaf protocol-name {
                 type string;
               }
               leaf preference {
                 type int32;
                 description
                   "Preference for the route";
               }
               leaf metric {
                 type int32;
               }
               leaf metric2 {
                 type int32;
               }
               leaf nh-type {
                 type string;
                 description
                   "Special next hop: Reject, Blackhole, Receive, Multicast,
                   Local, or Unused";
               }
               leaf as-path {
                 type string;
                 description
                   "Name of AS path regular expression (BGP only)";
               }
               leaf last-active {
                 type empty;
                 description
                   "This route entry was the last active route entry";
               }
               leaf current-active {
                 type empty;
                 description
                   "This route entry is currently active";
               }
               leaf bgp-rt-mult-nh-idx {
                 type uint32;
                 description
                   "BGP multipath nexthop index";
               }
               leaf deleted {
                 type empty;
               }
               leaf nh-erc-btid-id {
                 type string;
                 description
                   "ERC Backtrace ID";
               }
               leaf nh-erc-btid-op {
                 type string;
                 description
                   "ERC BTID Operation";
               }
               leaf nh-erc-btid-nreference {
                 type int32;
                 description
                   "ERC Number of BTID References";
               }
               leaf nh-erc-btid-bt {
                 type string;
                 description
                   "ERC BTID Backtrace ";
               }
               container route-record {
                 leaf rt-recorded {
                   type string;
                 }
                 leaf nh-address {
                   type string;
                   description
                     "Address of next hop";
                 }
                 leaf as-index {
                   type int32;
                 }
                 leaf as-recorded {
                   type string;
                 }
                 leaf com-index {
                   type int32;
                 }
                 leaf com-recorded {
                   type string;
                 }
               }
               list route-data-dcf {
                 key "trunk-id snmp-idx";
                 leaf trunk-id {
                   type int32;
                   description
                     "Trunk Identifier associated with the LAG port";
                 }
                 leaf snmp-idx {
                   type int32;
                   description
                     "IFD SNMP index";
                 }
                 leaf ts {
                   type int32;
                   description
                     "Timestamp associated with the route";
                 }
                 leaf class-id {
                   type int32;
                   description
                     "Class identifier associated with the route";
                 }
                 leaf rt-flags {
                   type string;
                   description
                     "Flags associated with the route";
                 }
                 leaf rt-type {
                   type string;
                   description
                     "Route type associated with the route";
                 }
                 leaf rt-proto {
                   type string;
                   description
                     "Protocol associated with the route";
                 }
                 leaf rt-l2domain {
                   type int32;
                   description
                     "L2domain associated with the route";
                 }
                 leaf rt-mac-addr {
                   type jt:mac-addr;
                   description
                     "Mac address associated with the route";
                 }
                 list snpa {
                   key "snpa-type";
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 leaf snpa-count {
                   type int32;
                   description
                     "Number of SNPAs in this route";
                 }
                 leaf snpa-length {
                   type int32;
                   description
                     "Total length of the SNPAs, in bytes";
                 }
                 container multicast-member-map-data {
                   description
                     "Multicast member map";
                   leaf multicast-root-hash {
                     type int32;
                   }
                   leaf multicast-core-hash {
                     type int32;
                   }
                   leaf multicast-edge-hash {
                     type int32;
                   }
                   leaf multicast-member-map {
                     type string;
                   }
                 }
                 container layer3-multicast-data {
                   description
                     "Layer3 multicast core key";
                   leaf layer3-multicast-corekey {
                     type int32;
                   }
                 }
                 container multicast-vsg-corekey-data {
                   description
                     "Vsg multicast core key";
                   leaf multicast-vsg-corekey-key {
                     type int32;
                   }
                   leaf multicast-vsg-corekey-len {
                     type int32;
                   }
                 }
               }
               container rtd-flow-dep {
                 leaf flow-dep-state {
                   type string;
                 }
                 leaf flow-origin {
                   type jt:ipaddr;
                   description
                     "Originator of the flow information";
                 }
                 leaf flow-next-as {
                   type uint32;
                   description
                     "Neighbor AS of the flow information";
                 }
                 container flow-ucast-rt {
                   description
                     "Unicast route used for resolution";
                   leaf flow-rtn-dest {
                     type jt:ipaddr;
                     description
                       "Destination address";
                   }
                   leaf flow-rtn-plen {
                     type int32;
                     description
                       "Prefix length";
                   }
                   leaf flow-rtn-state {
                     type string;
                     description
                       "Validation entry state";
                   }
                 }
               }
               container bgp-path-attributes {
                 container attr-as-path {
                   description
                     "AS Path Attribute";
                   leaf attr-length {
                     type string;
                   }
                   leaf flags {
                     type string;
                     description
                       "Enabled trace flags";
                   }
                   leaf path-length {
                     type string;
                   }
                   leaf attr-value {
                     type string;
                   }
                 }
                 container attr-as4-path {
                   description
                     "4-byte AS Path Attribute";
                   leaf attr-length {
                     type string;
                   }
                   leaf path-length {
                     type string;
                   }
                   leaf flags {
                     type string;
                     description
                       "Enabled trace flags";
                   }
                   leaf attr-value {
                     type string;
                   }
                 }
                 container attr-as-path-effective {
                   description
                     "Effective AS-Path Attribute";
                   leaf attr-length {
                     type string;
                   }
                   leaf aspath-effective-string {
                     type string;
                   }
                   leaf path-length {
                     type string;
                   }
                   leaf attr-value {
                     type string;
                   }
                   leaf flags {
                     type string;
                     description
                       "Enabled trace flags";
                   }
                 }
                 container attr-aggregator {
                   description
                     "Aggregator Attribute";
                   leaf attr-length {
                     type string;
                   }
                   leaf flags {
                     type string;
                     description
                       "Enabled trace flags";
                   }
                   leaf aggr-as-number {
                     type string;
                   }
                   leaf aggr-router-id {
                     type string;
                   }
                 }
                 container attr-aggregator4 {
                   description
                     "Aggregator4 Attribute";
                   leaf attr-length {
                     type string;
                   }
                   leaf flags {
                     type string;
                     description
                       "Enabled trace flags";
                   }
                   leaf aggr-as-number {
                     type string;
                   }
                   leaf aggr-router-id {
                     type string;
                   }
                 }
                 container attr-cluster-list {
                   description
                     "Cluster List Attribute";
                   leaf attr-length {
                     type string;
                   }
                   leaf attr-value {
                     type string;
                   }
                 }
                 container attr-originator-id {
                   description
                     "Originator Attribute";
                   leaf attr-length {
                     type string;
                   }
                   leaf attr-value {
                     type string;
                   }
                 }
                 leaf domain-path {
                   type string;
                 }
                 leaf attr-otc {
                   type int32;
                   description
                     "Only-to-customer attribute";
                 }
                 container attr-unrecognized {
                   description
                     "Unrecognized attributes";
                   leaf attr-length {
                     type string;
                   }
                   leaf attr-flags {
                     type string;
                   }
                   leaf attr-code {
                     type string;
                   }
                   leaf attr-value {
                     type string;
                   }
                 }
               }
               container communities {
                 leaf-list community {
                   type string;
                   description
                     "Basic community";
                 }
                 leaf-list extended-community {
                   type string;
                   description
                     "Extended community";
                 }
                 leaf-list ipv6-extended-community {
                   type string;
                   description
                     "IPv6 extended community";
                 }
               }
               list bgp-tunnel-attribute {
                 key "tunnel-attribute-type";
                 description
                   "Tunne encap attribute information";
                 leaf tunnel-attribute-type {
                   type string;
                 }
                 leaf tunnel-attribute-rpf {
                   type empty;
                 }
                 leaf tunnel-attribute-color {
                   type uint32;
                 }
                 leaf tunnel-attribute-destination {
                   type jt:ipaddr;
                 }
               }
               container attrset {
                 container bgp-prefix-sid-attr {
                   description
                     "BGP Prefix SID Attribute";
                   container bgp-prefix-sid-attr-label-idx-tlv {
                     leaf bgp-prefix-sid-label-idx-index {
                       type int32;
                     }
                     leaf bgp-prefix-sid-attr-status {
                       type string;
                     }
                   }
                   container bgp-prefix-sid-attr-srgb-tlv {
                     list bgp-prefix-sid-srgb-block {
                       key "bgp-prefix-sid-srgb-block-start-label";
                       leaf bgp-prefix-sid-srgb-block-start-label {
                         type int32;
                       }
                       leaf bgp-prefix-sid-srgb-block-range {
                         type int32;
                       }
                     }
                   }
                   container bgp-prefix-sid-attr-service-tlv {
                     leaf bgp-prefix-sid-srv6-sid-value {
                       type jt:ipaddr;
                     }
                     leaf bgp-prefix-sid-attr-service-tlv-type {
                       type uint32;
                     }
                     leaf bgp-prefix-sid-attr-tlv-type {
                       type uint32;
                     }
                     leaf bgp-prefix-sid-srv6-sid-bh {
                       type uint32;
                     }
                     leaf bgp-prefix-sid-srv6-sid-bl {
                       type uint32;
                     }
                     leaf bgp-prefix-sid-srv6-sid-nl {
                       type uint32;
                     }
                     leaf bgp-prefix-sid-srv6-sid-fl {
                       type uint32;
                     }
                     leaf bgp-prefix-sid-srv6-sid-al {
                       type uint32;
                     }
                     leaf bgp-prefix-sid-srv6-sid-tl {
                       type uint32;
                     }
                     leaf bgp-prefix-sid-srv6-sid-to {
                       type uint32;
                     }
                   }
                   container bgp-prefix-sid-attr-unknown-tlvs {
                     list bgp-prefix-sid-attr-unknown-tlv {
                       key "bgp-prefix-sid-unknown-tlv-type";
                       leaf bgp-prefix-sid-unknown-tlv-type {
                         type uint32;
                       }
                       leaf bgp-prefix-sid-unknown-tlv-len {
                         type uint32;
                       }
                     }
                   }
                 }
                 leaf attrset-as {
                   type int32;
                   description
                     "Originator AS";
                 }
                 leaf med {
                   type int32;
                   description
                     "Multiple exit discriminator";
                 }
                 leaf local-preference {
                   type int32;
                 }
                 leaf as-path {
                   type string;
                   description
                     "Name of AS path regular expression (BGP only)";
                 }
                 leaf pmsi {
                   type string;
                   description
                     "P-multicast service interface";
                 }
                 leaf cluster-id {
                   type string;
                 }
                 leaf originator {
                   type string;
                 }
                 leaf connector {
                   type string;
                 }
                 container communities {
                   leaf-list community {
                     type string;
                     description
                       "Basic community";
                   }
                   leaf-list extended-community {
                     type string;
                     description
                       "Extended community";
                   }
                   leaf-list ipv6-extended-community {
                     type string;
                     description
                       "IPv6 extended community";
                   }
                 }
                 list bgp-tunnel-attribute {
                   key "tunnel-attribute-type";
                   description
                     "Tunne encap attribute information";
                   leaf tunnel-attribute-type {
                     type string;
                   }
                   leaf tunnel-attribute-rpf {
                     type empty;
                   }
                   leaf tunnel-attribute-color {
                     type uint32;
                   }
                   leaf tunnel-attribute-destination {
                     type jt:ipaddr;
                   }
                 }
               }
               container link-state-information {
                 container link-state-link {
                   leaf link-name {
                     type string;
                   }
                   leaf color {
                     type int32;
                   }
                   leaf metric {
                     type int32;
                   }
                   leaf te-metric {
                     type int32;
                     description
                       "LSP TE metric";
                   }
                   leaf link-avg-delay {
                     type uint32;
                   }
                   leaf link-min-delay {
                     type uint32;
                   }
                   leaf link-max-delay {
                     type uint32;
                   }
                   leaf link-avg-delay-var {
                     type uint32;
                   }
                   leaf ldp-support {
                     type string;
                   }
                   leaf rsvpte-support {
                     type string;
                   }
                   leaf maximum-bw {
                     type uint64;
                   }
                   leaf reservable-bw {
                     type uint64;
                   }
                   container protections {
                     leaf-list protection-type {
                       type string;
                       description
                         "LSP protection desired";
                     }
                   }
                   container link-srlgs {
                     leaf-list link-srlg {
                       type string;
                     }
                   }
                   container unreserved-bws {
                     list unreserved-bw {
                       key "unreserved-bw-priority";
                       leaf unreserved-bw-priority {
                         type uint32;
                       }
                       leaf unreserved-bw-value {
                         type string;
                       }
                     }
                   }
                   container link-state-link-opaque-attrs {
                     leaf link-state-link-opaque-attrs-length {
                       type uint32;
                     }
                     leaf link-state-link-opaque-attrs-bytes {
                       type string;
                     }
                   }
                   container link-adj-sids {
                     list link-lan-adj-sid {
                       key "link-lan-adj-sid-label";
                       leaf link-lan-adj-sid-af {
                         type string;
                       }
                       leaf link-lan-adj-sid-label {
                         type uint32;
                       }
                       leaf link-lan-adj-sid-flags {
                         type string;
                       }
                       leaf link-lan-adj-sid-weight {
                         type uint32;
                       }
                       leaf link-lan-adj-sid-neighbor {
                         type string;
                       }
                     }
                     list link-p2p-adj-sid {
                       key "link-p2p-adj-sid-label";
                       leaf link-p2p-adj-sid-af {
                         type string;
                       }
                       leaf link-p2p-adj-sid-label {
                         type uint32;
                       }
                       leaf link-p2p-adj-sid-flags {
                         type string;
                       }
                       leaf link-p2p-adj-sid-weight {
                         type uint32;
                       }
                     }
                   }
                   container link-bgp-peer-sids {
                     list link-bgp-peer-sid {
                       key "link-bgp-peer-sid-label";
                       leaf link-bgp-peer-sid-label {
                         type uint32;
                       }
                       leaf link-bgp-peer-sid-flags {
                         type string;
                       }
                       leaf link-bgp-peer-sid-weight {
                         type uint32;
                       }
                     }
                   }
                   container link-srv6-end-x-sids {
                     list link-srv6-end-x-sid {
                       key "link-srv6-end-x-sid-val";
                       leaf link-srv6-end-x-sid-type {
                         type string;
                       }
                       leaf link-srv6-end-x-sid-val {
                         type jt:ipv6addr;
                       }
                       leaf link-srv6-end-x-sid-flags {
                         type string;
                       }
                       leaf link-srv6-end-x-sid-weight {
                         type int32;
                       }
                       leaf link-srv6-end-x-sid-algo {
                         type int32;
                       }
                       leaf link-srv6-end-x-sid-func {
                         type string;
                       }
                       leaf link-srv6-end-x-sid-lan-neighbor-id {
                         type string;
                       }
                       container link-srv6-end-x-sid-sstlv {
                         leaf link-srv6-end-x-sid-sstlv-header {
                           type empty;
                         }
                         leaf link-srv6-end-x-sid-sstlv-blen {
                           type uint32;
                         }
                         leaf link-srv6-end-x-sid-sstlv-nlen {
                           type uint32;
                         }
                         leaf link-srv6-end-x-sid-sstlv-flen {
                           type uint32;
                         }
                         leaf link-srv6-end-x-sid-sstlv-alen {
                           type uint32;
                         }
                       }
                     }
                   }
                   container link-msd-types {
                     list link-msd-entry {
                       key "link-msd-type";
                       leaf link-msd-type {
                         type uint32;
                       }
                       leaf link-msd-value {
                         type uint32;
                       }
                     }
                   }
                 }
                 container link-state-node {
                   leaf node-name {
                     type string;
                   }
                   leaf area-border-router {
                     type string;
                   }
                   leaf external-router {
                     type string;
                   }
                   leaf attached {
                     type string;
                   }
                   leaf overload {
                     type string;
                   }
                   container node-areas {
                     leaf-list node-area {
                       type string;
                     }
                   }
                   container node-ipv4-router-ids {
                     leaf-list node-ipv4-router-id {
                       type jt:ipaddr;
                     }
                   }
                   container node-ipv6-router-ids {
                     leaf-list node-ipv6-router-id {
                       type jt:ipaddr;
                     }
                   }
                   container node-topologies {
                     list node-topology {
                       key "id";
                       leaf id {
                         type uint32;
                       }
                     }
                   }
                   container link-state-node-opaque-attrs {
                     leaf link-state-node-opaque-attrs-length {
                       type uint32;
                     }
                     leaf link-state-node-opaque-attrs-bytes {
                       type string;
                     }
                   }
                   container node-spring-capability {
                     list node-spring-srgb-block {
                       key "node-spring-srgb-block-start node-spring-srgb-block-range";
                       leaf node-spring-srgb-block-start {
                         type uint32;
                       }
                       leaf node-spring-srgb-block-range {
                         type uint32;
                       }
                       leaf node-spring-srgb-block-flags {
                         type string;
                       }
                     }
                   }
                   container node-msd-types {
                     list node-msd-entry {
                       key "node-msd-type";
                       leaf node-msd-type {
                         type uint32;
                       }
                       leaf node-msd-value {
                         type uint32;
                       }
                     }
                   }
                   container node-srv6-capability {
                     leaf node-srv6-capability-flag {
                       type uint32;
                     }
                   }
                   container node-spring-algorithms {
                     list node-spring-algorithm {
                       key "node-spring-algorithm-type";
                       leaf node-spring-algorithm-type {
                         type uint32;
                       }
                     }
                   }
                   container node-spring-falgo-defs {
                     list node-spring-falgo-def {
                       key "node-spring-falgo-def-algo";
                       leaf node-spring-falgo-def-algo {
                         type uint32;
                       }
                       leaf node-spring-falgo-def-metric-type {
                         type uint32;
                       }
                       leaf node-spring-falgo-def-calculation-type {
                         type uint32;
                       }
                       leaf node-spring-falgo-def-priority {
                         type uint32;
                       }
                       leaf node-spring-falgo-def-flags {
                         type string;
                       }
                       leaf node-spring-falgo-def-include-any {
                         type string;
                       }
                       leaf node-spring-falgo-def-exclude {
                         type string;
                       }
                       leaf node-spring-falgo-def-include-all {
                         type string;
                       }
                     }
                   }
                 }
                 list link-state-te-policy-cp-segment {
                 }
                 container link-state-te-policy-cp {
                   leaf link-state-te-policy-cp-name {
                     type string;
                   }
                   leaf link-state-te-policy-cp-flags {
                     type string;
                   }
                   leaf link-state-te-policy-cp-preference {
                     type uint32;
                   }
                   leaf link-state-te-policy-cp-priority {
                     type uint32;
                   }
                   leaf link-state-te-policy-cp-constraint-header {
                     type empty;
                   }
                   leaf link-state-te-policy-cp-constraint-flags {
                     type string;
                   }
                   leaf link-state-te-policy-cp-mtid {
                     type uint32;
                   }
                   leaf link-state-te-policy-cp-algo {
                     type uint32;
                   }
                   leaf link-state-te-policy-cp-exclude-any {
                     type string;
                   }
                   leaf link-state-te-policy-cp-include-any {
                     type string;
                   }
                   leaf link-state-te-policy-cp-include-all {
                     type string;
                   }
                   leaf link-state-te-policy-cp-bandwidth {
                     type uint32;
                   }
                   leaf link-state-te-policy-cp-bsid-flags {
                     type string;
                   }
                   leaf link-state-te-policy-cp-mpls-bsid {
                     type uint32;
                   }
                   leaf link-state-te-policy-cp-mpls-spec-bsid {
                     type uint32;
                   }
                   leaf link-state-te-policy-cp-segment-list-count {
                     type int32;
                   }
                   container link-state-te-policy-cp-srv6-bsid-info {
                     leaf link-state-te-policy-cp-srv6-bsid-flags {
                       type string;
                       description
                         "SRv6 BSID flags";
                     }
                     leaf link-state-te-policy-cp-srv6-bsid {
                       type jt:ipv6addr;
                       description
                         "SRv6 BSID";
                     }
                     leaf link-state-te-policy-cp-srv6-spec-bsid {
                       type jt:ipv6addr;
                       description
                         "Specified SRv6 BSID";
                     }
                     leaf link-state-te-policy-cp-srv6-bsid-ep-bhv {
                       type uint32;
                       description
                         "SRv6 BSID endpoint behavior";
                     }
                     leaf link-state-te-policy-cp-srv6-bsid-ep-bhv-flags {
                       type string;
                       description
                         "SRv6 BSID endpoint behavior flags";
                     }
                     leaf link-state-te-policy-cp-srv6-bsid-ep-bhv-algo {
                       type uint32;
                       description
                         "SRv6 BSID endpoint behavior algo";
                     }
                     leaf link-state-te-policy-cp-srv6-bsid-sstlv {
                       type string;
                       description
                         "SRv6 BSID endpoint behavior SSTLV";
                     }
                   }
                   list link-state-te-policy-cp-segment-list {
                     key "link-state-te-policy-cp-segment-list-index";
                     leaf link-state-te-policy-cp-segment-list-index {
                       type int32;
                     }
                     leaf link-state-te-policy-cp-segment-list-flags {
                       type string;
                     }
                     leaf link-state-te-policy-cp-segment-list-mtid {
                       type uint32;
                     }
                     leaf link-state-te-policy-cp-segment-list-weight {
                       type uint32;
                     }
                     leaf link-state-te-policy-cp-segment-list-algo {
                       type uint32;
                     }
                     leaf link-state-te-policy-cp-segment-list-metric-type {
                       type string;
                     }
                     leaf link-state-te-policy-cp-segment-list-metric-value {
                       type uint32;
                     }
                     leaf link-state-te-policy-cp-segment-count {
                       type int32;
                     }
                     leaf link-state-te-policy-cp-segment-header {
                       type empty;
                     }
                     list link-state-te-policy-cp-segment {
                       leaf link-state-te-policy-cp-mpls-segment-id {
                         type uint32;
                       }
                       leaf link-state-te-policy-cp-srv6-segment-id {
                         type jt:ipv6addr;
                       }
                       leaf link-state-te-policy-cp-segment-descriptor {
                         type jt:ipaddr;
                       }
                       leaf link-state-te-policy-cp-segment-flags {
                         type string;
                       }
                       leaf link-state-te-policy-cp-segment-ep-bhv {
                         type string;
                       }
                       leaf link-state-te-policy-cp-segment-ep-bhv-flags {
                         type uint32;
                       }
                       leaf link-state-te-policy-cp-segment-ep-bhv-algo {
                         type uint32;
                       }
                       container link-state-te-policy-cp-segment-sstlv {
                         leaf link-state-te-policy-cp-segment-sstlv-header {
                           type empty;
                         }
                         leaf link-state-te-policy-cp-segment-sstlv-blen {
                           type uint32;
                         }
                         leaf link-state-te-policy-cp-segment-sstlv-nlen {
                           type uint32;
                         }
                         leaf link-state-te-policy-cp-segment-sstlv-flen {
                           type uint32;
                         }
                         leaf link-state-te-policy-cp-segment-sstlv-alen {
                           type uint32;
                         }
                       }
                     }
                   }
                 }
                 container link-state-prefix {
                   leaf link-state-prefix-attr-flags {
                     type string;
                   }
                   leaf link-state-prefix-metric {
                     type uint32;
                   }
                   list link-state-prefix-sid {
                     key "link-state-prefix-sid-index link-state-prefix-sid-flags link-state-prefix-sid-algo";
                     leaf link-state-prefix-sid-index {
                       type uint32;
                     }
                     leaf link-state-prefix-sid-flags {
                       type string;
                     }
                     leaf link-state-prefix-sid-algo {
                       type string;
                     }
                   }
                   container link-state-prefix-srv6-locator {
                     leaf link-state-prefix-srv6-locator-flags {
                       type string;
                     }
                     leaf link-state-prefix-srv6-locator-algo {
                       type string;
                     }
                     leaf link-state-prefix-srv6-locator-metric {
                       type string;
                     }
                   }
                   list link-state-prefix-fapm {
                     key "link-state-prefix-fapm-algo";
                     leaf link-state-prefix-fapm-algo {
                       type uint32;
                     }
                     leaf link-state-prefix-fapm-metric {
                       type uint32;
                     }
                   }
                 }
                 container link-state-srv6-endsid {
                   container link-state-srv6-endsid-info {
                     leaf link-state-srv6-endsid-epb {
                       type string;
                     }
                     leaf link-state-srv6-endsid-flags {
                       type string;
                     }
                     leaf link-state-srv6-endsid-algo {
                       type string;
                     }
                     container link-state-srv6-endsid-sstlv {
                       leaf link-state-srv6-endsid-sstlv-header {
                         type empty;
                       }
                       leaf link-state-srv6-endsid-sstlv-blen {
                         type uint32;
                       }
                       leaf link-state-srv6-endsid-sstlv-nlen {
                         type uint32;
                       }
                       leaf link-state-srv6-endsid-sstlv-flen {
                         type uint32;
                       }
                       leaf link-state-srv6-endsid-sstlv-alen {
                         type uint32;
                       }
                     }
                   }
                 }
                 container link-state-unknown-tlvs {
                   list link-state-unknown-tlv {
                     key "unknown-type";
                     leaf unknown-type {
                       type uint32;
                     }
                     leaf unknown-length {
                       type uint32;
                     }
                     leaf unknown-bytes {
                       type string;
                     }
                   }
                 }
               }
               container aggregate {
                 leaf aggregate-truncate {
                   type string;
                 }
                 container aggregate-as-path {
                   container bgp-path-attributes {
                     container attr-as-path {
                       description
                         "AS Path Attribute";
                       leaf attr-length {
                         type string;
                       }
                       leaf flags {
                         type string;
                         description
                           "Enabled trace flags";
                       }
                     }
                     container attr-as4-path {
                       description
                         "4-byte AS Path Attribute";
                       leaf attr-length {
                         type string;
                       }
                     }
                     container attr-as-path-effective {
                       description
                         "Effective AS-Path Attribute";
                       leaf attr-length {
                         type string;
                       }
                     }
                     container attr-aggregator {
                       description
                         "Aggregator Attribute";
                       leaf attr-length {
                         type string;
                       }
                     }
                     container attr-aggregator4 {
                       description
                         "Aggregator4 Attribute";
                       leaf attr-length {
                         type string;
                       }
                     }
                     container attr-cluster-list {
                       description
                         "Cluster List Attribute";
                       leaf attr-length {
                         type string;
                       }
                     }
                     container attr-originator-id {
                       description
                         "Originator Attribute";
                       leaf attr-length {
                         type string;
                       }
                     }
                   }
                   leaf as-path {
                     type string;
                     description
                       "Name of AS path regular expression (BGP only)";
                   }
                   leaf reference-count {
                     type int32;
                     description
                       "Reference count";
                   }
                   leaf as-path-length {
                     type int32;
                   }
                   leaf aggregate-truncate {
                     type string;
                   }
                 }
                 leaf aggregate-flags {
                   type string;
                   description
                     "Flags on this aggregate route entry";
                 }
                 leaf aggregate-depth {
                   type int32;
                   description
                     "Depth of this aggregate";
                 }
                 leaf aggregate-active {
                   type empty;
                   description
                     "Present if this aggregate is active";
                 }
                 leaf aggregate-algo {
                   type uint32;
                   description
                     "Algorithm number";
                 }
                 leaf contributing-route-count {
                   type int32;
                   description
                     "Number of contributing routes in this aggregate";
                 }
                 leaf aggregate-policy-name {
                   type string;
                 }
                 list aggregated-route {
                   key "destination-prefix";
                   leaf destination-prefix {
                     type string;
                     description
                       "Destination prefix and mask";
                   }
                   leaf protocol-name {
                     type string;
                   }
                 }
               }
               list kern-nhexpand {
                 description
                   "Next-hop gateway information";
                 container srv6-info {
                   leaf srv6-info-srh-sid-mode {
                     type string;
                     description
                       "Reduced/non-reduced mode for SRH";
                   }
                   leaf srv6-info-packet-mode {
                     type string;
                     description
                       "Packet mode for SRV6-Tunnel";
                   }
                   leaf srv6-info-srh-last-sid {
                     type string;
                     description
                       "Remove last sid for ACX";
                   }
                   leaf srv6-info-dyn-tunnel {
                     type string;
                     description
                       "SRv6 tunnel created dynamically";
                   }
                   leaf srv6-cos-propagation {
                     type string;
                     description
                       "SRv6 CoS propagation";
                   }
                   leaf srv6-ttl-propagation {
                     type string;
                     description
                       "SRv6 TTL propagation";
                   }
                   leaf srv6-source {
                     type jt:ipaddr;
                     description
                       "Source IPv6 address";
                   }
                   leaf srv6-destination {
                     type jt:ipaddr;
                     description
                       "Destination IPv6 address";
                   }
                   list srv6-segment-list {
                     key "srv6-segment-list-index";
                     description
                       "SRH Segment list";
                     leaf srv6-segment-list-index {
                       type uint32;
                       description
                         "SRH segment list index";
                     }
                     leaf srv6-segment-list-addr {
                       type jt:ipaddr;
                       description
                         "SRH segment address";
                     }
                   }
                 }
               }
               container kern-nh-platform-layer-input {
                 list kern-nhexpand {
                   description
                     "Next-hop gateway information";
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                 }
               }
               container kern-nh-platform-layer-output {
                 list kern-nhexpand {
                   description
                     "Next-hop gateway information";
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                 }
               }
               list nh {
                 description
                   "Next-hop gateway information";
                 leaf selected-next-hop {
                   type empty;
                   description
                     "Present if this next hop is selected";
                 }
                 leaf to {
                   type string;
                   description
                     "Neighbor address to which to send (next-hop address)";
                 }
                 leaf nh-indirect-fnh-type {
                   type string;
                   description
                     "Indirect pointing to a well-known nexthop";
                 }
                 leaf via {
                   type string;
                   description
                     "Reachable via a local interface";
                 }
                 container vxlan-header-rewrite {
                   description
                     "VXLAN tunnel rewrite information";
                   leaf vxlan-header-rewrite-mtu {
                     type int32;
                     description
                       "VXLAN tunnel MTU";
                   }
                   leaf vxlan-header-rewrite-flags {
                     type int32;
                     description
                       "VXLAN tunnel flags";
                   }
                   leaf vxlan-header-rewrite-encap-rtb-id {
                     type int32;
                     description
                       "VXLAN tunnel encapsulation table ID";
                   }
                   leaf vxlan-header-rewrite-decap-rtb-id {
                     type int32;
                     description
                       "VXLAN tunnel decapsulation table ID";
                   }
                   leaf vxlan-header-rewrite-encap-vnid {
                     type int32;
                     description
                       "VXLAN tunnel encapsulation VNI";
                   }
                   leaf vxlan-header-rewrite-decap-vnid {
                     type int32;
                     description
                       "VXLAN tunnel decapsulation VNI";
                   }
                   leaf vxlan-header-rewrite-svtep {
                     type jt:ipaddr;
                     description
                       "Source VTEP address";
                   }
                   leaf vxlan-header-rewrite-dvtep {
                     type jt:ipaddr;
                     description
                       "Destination VTEP address";
                   }
                   leaf vxlan-header-rewrite-smac {
                     type string;
                     description
                       "Source MAC address";
                   }
                   leaf vxlan-header-rewrite-dmac {
                     type string;
                     description
                       "Destination MAC address";
                   }
                 }
                 container srv6-info {
                   leaf srv6-info-srh-sid-mode {
                     type string;
                     description
                       "Reduced/non-reduced mode for SRH";
                   }
                   leaf srv6-info-packet-mode {
                     type string;
                     description
                       "Packet mode for SRV6-Tunnel";
                   }
                   leaf srv6-info-srh-last-sid {
                     type string;
                     description
                       "Remove last sid for ACX";
                   }
                   leaf srv6-info-dyn-tunnel {
                     type string;
                     description
                       "SRv6 tunnel created dynamically";
                   }
                   leaf srv6-cos-propagation {
                     type string;
                     description
                       "SRv6 CoS propagation";
                   }
                   leaf srv6-ttl-propagation {
                     type string;
                     description
                       "SRv6 TTL propagation";
                   }
                   leaf srv6-source {
                     type jt:ipaddr;
                     description
                       "Source IPv6 address";
                   }
                   leaf srv6-destination {
                     type jt:ipaddr;
                     description
                       "Destination IPv6 address";
                   }
                   list srv6-segment-list {
                     key "srv6-segment-list-index";
                     description
                       "SRH Segment list";
                     leaf srv6-segment-list-index {
                       type uint32;
                       description
                         "SRH segment list index";
                     }
                     leaf srv6-segment-list-addr {
                       type jt:ipaddr;
                       description
                         "SRH segment address";
                     }
                   }
                 }
                 leaf nh-string {
                   type string;
                 }
                 leaf nh-table-receive {
                   type string;
                   description
                     "Destination is a local address";
                 }
                 leaf nh-table {
                   type string;
                   description
                     "Indirect pointing to another table";
                 }
                 leaf nh-table-localized {
                   type string;
                   description
                     "Indirect pointing to a localized table";
                 }
                 leaf nh-localized-ifl {
                   type string;
                   description
                     "Indirect pointing to a localized ifl";
                 }
                 leaf lsp-name {
                   type string;
                   description
                     "Tunneled into an RSVP LSP";
                 }
                 leaf mpls-label {
                   type string;
                   description
                     "Label of MPLS packet";
                 }
                 leaf nh-local-interface {
                   type string;
                   description
                     "Destination is a local interface";
                 }
                 leaf nh-service {
                   type string;
                   description
                     "Next-hop service";
                 }
                 leaf nh-private-comp {
                   type string;
                   description
                     "Private Composite Next-hop";
                 }
                 leaf srv6-prefix-sid {
                   type jt:ipaddr;
                   description
                     "SRv6 prefixe sid value";
                 }
                 leaf srv6-encap-brief {
                   type string;
                   description
                     "IPV6 SR-header encapsulation";
                 }
                 leaf elnh-address {
                   type string;
                   description
                     "Address of Element Next-hop";
                 }
                 leaf localized-table {
                   type string;
                   description
                     "Name of localized table";
                 }
                 leaf ae-member-interface {
                   type string;
                   description
                     "AE Member interface";
                 }
                 leaf weight {
                   type int32;
                   description
                     "Next-hop weight";
                 }
                 leaf balance {
                   type int32;
                   description
                     "Next-hop balance";
                 }
                 leaf uflags {
                   type string;
                   description
                     "Next-hop uflags";
                 }
                 leaf filter {
                   type string;
                   description
                     "Next-hop firewall filter";
                 }
                 leaf session {
                   type string;
                   description
                     "Session ID Associated with this NH";
                 }
                 leaf statistics-id-group-terse {
                   type string;
                   description
                     "Statistics ID Group Associated with this NH";
                 }
                 leaf app-specific-opaque {
                   type string;
                   description
                     "Application specific opaque data dump";
                 }
                 leaf gw-opaque {
                   type string;
                   description
                     "Nexthops gateway opaque data handle";
                 }
                 leaf statistics-pkts-count {
                   type int32;
                   description
                     "Statistics packet count Associated with this NH";
                 }
                 leaf statistics-bytes-count {
                   type int32;
                   description
                     "Statistics bytes count Associated with this NH";
                 }
                 leaf ext-int-type {
                   type string;
                   description
                     "Next-hop type of equal-external-internal multipath";
                 }
                 leaf fc {
                   type int32;
                   description
                     "Forwarding-class";
                 }
                 leaf label-ttl-action {
                   type string;
                   description
                     "TTL action associated with labels";
                 }
                 leaf load-balance-label {
                   type string;
                   description
                     "Load balance action associated with labels";
                 }
                 leaf label-element {
                   type string;
                   description
                     "Pointer to the tag label element";
                 }
                 leaf label-element-parent {
                   type string;
                   description
                     "Pointer to the tag label element parent";
                 }
                 leaf label-element-refcount {
                   type string;
                   description
                     "Number of references to the tag label element";
                 }
                 leaf label-element-childcount {
                   type string;
                   description
                     "Number of child references to the tag label element";
                 }
                 leaf label-element-lspid {
                   type string;
                   description
                     "LSP ID of the tag label element";
                 }
                 leaf nh-service-pkt-dist {
                   type string;
                   description
                     "Multi services packet distribution type";
                 }
                 leaf nh-service-app-data {
                   type string;
                   description
                     "Multi services application specific data";
                 }
                 leaf nh-index {
                   type uint32;
                   description
                     "Next-hop index";
                 }
                 leaf nh-address {
                   type string;
                   description
                     "Address of next hop";
                 }
                 leaf nh-reference-count {
                   type int32;
                   description
                     "Number of references to this next hop";
                 }
                 leaf tunnel-composite-attr-type {
                   type string;
                   description
                     "Tunnel-Type for tunnel-composite-nexthop";
                 }
                 leaf tunnel-composite-attr-subtype {
                   type string;
                   description
                     "Tunnel-Subtype for tunnel-composite-nexthop";
                 }
                 leaf tunnel-composite-attr-reference-count {
                   type int32;
                   description
                     "Tunnel-reference-count for tunnel-composite-nexthop";
                 }
                 leaf tunnel-composite-attr-nh-id {
                   type int32;
                   description
                     "Tunnel-NextHop-Id for tunnel-composite-nexthop";
                 }
                 leaf tunnel-composite-attr-dest {
                   type jt:ipaddr;
                   description
                     "Tunnel-Destination for tunnel-composite-nexthop";
                 }
                 leaf tunnel-composite-attr-src {
                   type jt:ipaddr;
                   description
                     "Tunnel-Source for tunnel-composite-nexthop";
                 }
                 leaf tunnel-composite-attr-tunnel-endpoint {
                   type jt:ipaddr;
                   description
                     "Tunnel-Endpoint for tunnel-composite-nexthop";
                 }
                 leaf tunnel-composite-anchor-pfe {
                   type string;
                   description
                     "Anchor PFE name, if tunnel nexthop is localized";
                 }
                 leaf tunnel-composite-encap-rtb-id {
                   type int32;
                   description
                     "Tunnel encap routing table index";
                 }
                 leaf tunnel-composite-decap-rtb-id {
                   type int32;
                   description
                     "Tunnel decap routing table index";
                 }
                 leaf tunnel-composite-attr-ttl {
                   type int32;
                   description
                     "Tunnel-TTL for tunnel-composite-nexthop";
                 }
                 leaf tunnel-composite-attr-udp-port {
                   type int32;
                   description
                     "Tunnel-UDP-Destination port for 
                     tunnel-composite-nexthop";
                 }
                 leaf tunnel-composite-attr-fc-id {
                   type int32;
                   description
                     "Tunnel-Forwarding-Class-ID for 
                     tunnel-composite-nexthop";
                 }
                 leaf tunnel-composite-attr-tid {
                   type int32;
                   description
                     "Tunnel-Id for tunnel-composite-nexthop";
                 }
                 leaf tunnel-composite-attr-label {
                   type string;
                   description
                     "Tunnel-VPN-Label for tunnel-composite-nexthop";
                 }
                 leaf tunnel-composite-attr-label-ttl {
                   type string;
                   description
                     "Tunnel-VPN-Label-TTL for tunnel-composite-nexthop";
                 }
                 leaf tunnel-composite-attr-gre-key {
                   type int32;
                   description
                     "GRE key for tunnel-composite-nexthop";
                 }
                 leaf-list tunnel-composite-attr-segment-addr {
                   type jt:ipaddr;
                   description
                     "IPv6 segment-address";
                 }
                 leaf-list tunnel-composite-attr-sid {
                   type int32;
                   description
                     "IPv6 segment-sid";
                 }
                 leaf tunnel-composite-attr-vni {
                   type int32;
                   description
                     "Tunnel-VNI for tunnel-composite-nexthop in VxLAN";
                 }
                 leaf tunnel-composite-attr-dest-mac {
                   type string;
                   description
                     "Tunnel-Dest-Mac for tunnel-composite-nexthop in VxLAN";
                 }
                 leaf translate-composite-attr-type {
                   type string;
                   description
                     "Translation type for translate-composite-nexthop";
                 }
                 leaf translate-composite-attr-flags {
                   type string;
                   description
                     "Flags for translate-composite-nexthop";
                 }
                 leaf translate-composite-attr-reference-count {
                   type int32;
                   description
                     "Reference count for translate-composite-nexthop";
                 }
                 leaf translate-composite-attr-nh-id {
                   type int32;
                   description
                     "NextHop id for translate-composite-nexthop";
                 }
                 leaf translate-composite-attr-dest {
                   type jt:ipaddr;
                   description
                     "Translation destination for 
                     translate-composite-nexthop";
                 }
                 leaf translate-composite-attr-dest-plen {
                   type int32;
                   description
                     "Translation destination prefix length for 
                     translate-composite-nexthop";
                 }
                 leaf translate-composite-attr-src {
                   type jt:ipaddr;
                   description
                     "Translation source for translate-composite-nexthop";
                 }
                 leaf translate-composite-attr-src-plen {
                   type int32;
                   description
                     "Translation source prefix length for 
                     translate-composite-nexthop";
                 }
                 leaf translate-composite-attr-dest-alg-type {
                   type string;
                   description
                     "Destination algorithm type for 
                     translate-composite-nexthop";
                 }
                 leaf translate-composite-attr-src-alg-type {
                   type string;
                   description
                     "Source algorithm type for translate-composite-nexthop";
                 }
                 leaf translate-composite-attr-dest-vrf-id {
                   type int32;
                   description
                     "Destination vrf id for translate-composite-nexthop";
                 }
                 leaf translate-composite-attr-src-vrf-id {
                   type int32;
                   description
                     "Source vrf id for translate-composite-nexthop";
                 }
                 leaf translate-composite-attr-hoplimit {
                   type int32;
                   description
                     "Hoplimit for translate-composite-nexthop";
                 }
                 leaf translate-composite-attr-traffic-class {
                   type int32;
                   description
                     "Traffic class for translate-composite-nexthop";
                 }
                 leaf translate-composite-attr-ttl {
                   type int32;
                   description
                     "Ttl for translate-composite-nexthop";
                 }
                 leaf translate-composite-attr-tos {
                   type int32;
                   description
                     "Tos for translate-composite-nexthop";
                 }
               }
               container protocol-nh {
                 description
                   "Protocol next hop";
                 list nh {
                   description
                     "Next-hop gateway information";
                   container vxlan-header-rewrite {
                     description
                       "VXLAN tunnel rewrite information";
                     leaf vxlan-header-rewrite-mtu {
                       type int32;
                       description
                         "VXLAN tunnel MTU";
                     }
                     leaf vxlan-header-rewrite-flags {
                       type int32;
                       description
                         "VXLAN tunnel flags";
                     }
                     leaf vxlan-header-rewrite-encap-rtb-id {
                       type int32;
                       description
                         "VXLAN tunnel encapsulation table ID";
                     }
                     leaf vxlan-header-rewrite-decap-rtb-id {
                       type int32;
                       description
                         "VXLAN tunnel decapsulation table ID";
                     }
                     leaf vxlan-header-rewrite-encap-vnid {
                       type int32;
                       description
                         "VXLAN tunnel encapsulation VNI";
                     }
                     leaf vxlan-header-rewrite-decap-vnid {
                       type int32;
                       description
                         "VXLAN tunnel decapsulation VNI";
                     }
                     leaf vxlan-header-rewrite-svtep {
                       type jt:ipaddr;
                       description
                         "Source VTEP address";
                     }
                     leaf vxlan-header-rewrite-dvtep {
                       type jt:ipaddr;
                       description
                         "Destination VTEP address";
                     }
                     leaf vxlan-header-rewrite-smac {
                       type string;
                       description
                         "Source MAC address";
                     }
                     leaf vxlan-header-rewrite-dmac {
                       type string;
                       description
                         "Destination MAC address";
                     }
                   }
                   container srv6-info {
                     leaf srv6-info-srh-sid-mode {
                       type string;
                       description
                         "Reduced/non-reduced mode for SRH";
                     }
                     leaf srv6-info-packet-mode {
                       type string;
                       description
                         "Packet mode for SRV6-Tunnel";
                     }
                     leaf srv6-info-srh-last-sid {
                       type string;
                       description
                         "Remove last sid for ACX";
                     }
                     leaf srv6-info-dyn-tunnel {
                       type string;
                       description
                         "SRv6 tunnel created dynamically";
                     }
                     leaf srv6-cos-propagation {
                       type string;
                       description
                         "SRv6 CoS propagation";
                     }
                     leaf srv6-ttl-propagation {
                       type string;
                       description
                         "SRv6 TTL propagation";
                     }
                     leaf srv6-source {
                       type jt:ipaddr;
                       description
                         "Source IPv6 address";
                     }
                     leaf srv6-destination {
                       type jt:ipaddr;
                       description
                         "Destination IPv6 address";
                     }
                     list srv6-segment-list {
                       key "srv6-segment-list-index";
                       description
                         "SRH Segment list";
                       leaf srv6-segment-list-index {
                         type uint32;
                         description
                           "SRH segment list index";
                       }
                       leaf srv6-segment-list-addr {
                         type jt:ipaddr;
                         description
                           "SRH segment address";
                       }
                     }
                   }
                   leaf nh-string {
                     type string;
                   }
                   leaf elnh-address {
                     type string;
                     description
                       "Address of Element Next-hop";
                   }
                   leaf to {
                     type string;
                     description
                       "Neighbor address to which to send (next-hop address)";
                   }
                   leaf via {
                     type string;
                     description
                       "Reachable via a local interface";
                   }
                   leaf localized-table {
                     type string;
                     description
                       "Name of localized table";
                   }
                   leaf ae-member-interface {
                     type string;
                     description
                       "AE Member interface";
                   }
                   leaf weight {
                     type int32;
                     description
                       "Next-hop weight";
                   }
                   leaf balance {
                     type int32;
                     description
                       "Next-hop balance";
                   }
                   leaf uflags {
                     type string;
                     description
                       "Next-hop uflags";
                   }
                   leaf filter {
                     type string;
                     description
                       "Next-hop firewall filter";
                   }
                   leaf selected-next-hop {
                     type empty;
                     description
                       "Present if this next hop is selected";
                   }
                   leaf session {
                     type string;
                     description
                       "Session ID Associated with this NH";
                   }
                   leaf statistics-id-group-terse {
                     type string;
                     description
                       "Statistics ID Group Associated with this NH";
                   }
                   leaf app-specific-opaque {
                     type string;
                     description
                       "Application specific opaque data dump";
                   }
                   leaf gw-opaque {
                     type string;
                     description
                       "Nexthops gateway opaque data handle";
                   }
                   leaf statistics-pkts-count {
                     type int32;
                     description
                       "Statistics packet count Associated with this NH";
                   }
                   leaf statistics-bytes-count {
                     type int32;
                     description
                       "Statistics bytes count Associated with this NH";
                   }
                   leaf ext-int-type {
                     type string;
                     description
                       "Next-hop type of equal-external-internal multipath";
                   }
                   leaf fc {
                     type int32;
                     description
                       "Forwarding-class";
                   }
                   leaf lsp-name {
                     type string;
                     description
                       "Tunneled into an RSVP LSP";
                   }
                   leaf mpls-label {
                     type string;
                     description
                       "Label of MPLS packet";
                   }
                   leaf label-ttl-action {
                     type string;
                     description
                       "TTL action associated with labels";
                   }
                   leaf load-balance-label {
                     type string;
                     description
                       "Load balance action associated with labels";
                   }
                   leaf label-element {
                     type string;
                     description
                       "Pointer to the tag label element";
                   }
                   leaf label-element-parent {
                     type string;
                     description
                       "Pointer to the tag label element parent";
                   }
                   leaf label-element-refcount {
                     type string;
                     description
                       "Number of references to the tag label element";
                   }
                   leaf label-element-childcount {
                     type string;
                     description
                       "Number of child references to the tag label element";
                   }
                   leaf label-element-lspid {
                     type string;
                     description
                       "LSP ID of the tag label element";
                   }
                   leaf nh-table-receive {
                     type string;
                     description
                       "Destination is a local address";
                   }
                   leaf nh-table {
                     type string;
                     description
                       "Indirect pointing to another table";
                   }
                   leaf nh-localized-ifl {
                     type string;
                     description
                       "Indirect pointing to a localized ifl";
                   }
                   leaf nh-local-interface {
                     type string;
                     description
                       "Destination is a local interface";
                   }
                   leaf nh-service {
                     type string;
                     description
                       "Next-hop service";
                   }
                   leaf nh-service-pkt-dist {
                     type string;
                     description
                       "Multi services packet distribution type";
                   }
                   leaf nh-service-app-data {
                     type string;
                     description
                       "Multi services application specific data";
                   }
                   leaf nh-private-comp {
                     type string;
                     description
                       "Private Composite Next-hop";
                   }
                   leaf nh-index {
                     type uint32;
                     description
                       "Next-hop index";
                   }
                   leaf nh-address {
                     type string;
                     description
                       "Address of next hop";
                   }
                   leaf nh-reference-count {
                     type int32;
                     description
                       "Number of references to this next hop";
                   }
                   leaf tunnel-composite-attr-type {
                     type string;
                     description
                       "Tunnel-Type for tunnel-composite-nexthop";
                   }
                   leaf tunnel-composite-attr-subtype {
                     type string;
                     description
                       "Tunnel-Subtype for tunnel-composite-nexthop";
                   }
                   leaf tunnel-composite-attr-reference-count {
                     type int32;
                     description
                       "Tunnel-reference-count for tunnel-composite-nexthop";
                   }
                   leaf tunnel-composite-attr-nh-id {
                     type int32;
                     description
                       "Tunnel-NextHop-Id for tunnel-composite-nexthop";
                   }
                   leaf tunnel-composite-attr-dest {
                     type jt:ipaddr;
                     description
                       "Tunnel-Destination for tunnel-composite-nexthop";
                   }
                   leaf tunnel-composite-attr-src {
                     type jt:ipaddr;
                     description
                       "Tunnel-Source for tunnel-composite-nexthop";
                   }
                   leaf tunnel-composite-attr-tunnel-endpoint {
                     type jt:ipaddr;
                     description
                       "Tunnel-Endpoint for tunnel-composite-nexthop";
                   }
                   leaf tunnel-composite-anchor-pfe {
                     type string;
                     description
                       "Anchor PFE name, if tunnel nexthop is localized";
                   }
                   leaf tunnel-composite-encap-rtb-id {
                     type int32;
                     description
                       "Tunnel encap routing table index";
                   }
                   leaf tunnel-composite-decap-rtb-id {
                     type int32;
                     description
                       "Tunnel decap routing table index";
                   }
                   leaf tunnel-composite-attr-ttl {
                     type int32;
                     description
                       "Tunnel-TTL for tunnel-composite-nexthop";
                   }
                   leaf tunnel-composite-attr-udp-port {
                     type int32;
                     description
                       "Tunnel-UDP-Destination port for 
                       tunnel-composite-nexthop";
                   }
                   leaf tunnel-composite-attr-fc-id {
                     type int32;
                     description
                       "Tunnel-Forwarding-Class-ID for 
                       tunnel-composite-nexthop";
                   }
                   leaf tunnel-composite-attr-tid {
                     type int32;
                     description
                       "Tunnel-Id for tunnel-composite-nexthop";
                   }
                   leaf tunnel-composite-attr-label {
                     type string;
                     description
                       "Tunnel-VPN-Label for tunnel-composite-nexthop";
                   }
                   leaf tunnel-composite-attr-label-ttl {
                     type string;
                     description
                       "Tunnel-VPN-Label-TTL for tunnel-composite-nexthop";
                   }
                   leaf tunnel-composite-attr-gre-key {
                     type int32;
                     description
                       "GRE key for tunnel-composite-nexthop";
                   }
                   leaf-list tunnel-composite-attr-segment-addr {
                     type jt:ipaddr;
                     description
                       "IPv6 segment-address";
                   }
                   leaf-list tunnel-composite-attr-sid {
                     type int32;
                     description
                       "IPv6 segment-sid";
                   }
                   leaf tunnel-composite-attr-vni {
                     type int32;
                     description
                       "Tunnel-VNI for tunnel-composite-nexthop in VxLAN";
                   }
                   leaf tunnel-composite-attr-dest-mac {
                     type string;
                     description
                       "Tunnel-Dest-Mac for tunnel-composite-nexthop in 
                       VxLAN";
                   }
                   leaf translate-composite-attr-type {
                     type string;
                     description
                       "Translation type for translate-composite-nexthop";
                   }
                   leaf translate-composite-attr-flags {
                     type string;
                     description
                       "Flags for translate-composite-nexthop";
                   }
                   leaf translate-composite-attr-reference-count {
                     type int32;
                     description
                       "Reference count for translate-composite-nexthop";
                   }
                   leaf translate-composite-attr-nh-id {
                     type int32;
                     description
                       "NextHop id for translate-composite-nexthop";
                   }
                   leaf translate-composite-attr-dest {
                     type jt:ipaddr;
                     description
                       "Translation destination for 
                       translate-composite-nexthop";
                   }
                   leaf translate-composite-attr-dest-plen {
                     type int32;
                     description
                       "Translation destination prefix length for 
                       translate-composite-nexthop";
                   }
                   leaf translate-composite-attr-src {
                     type jt:ipaddr;
                     description
                       "Translation source for translate-composite-nexthop";
                   }
                   leaf translate-composite-attr-src-plen {
                     type int32;
                     description
                       "Translation source prefix length for 
                       translate-composite-nexthop";
                   }
                   leaf translate-composite-attr-dest-alg-type {
                     type string;
                     description
                       "Destination algorithm type for 
                       translate-composite-nexthop";
                   }
                   leaf translate-composite-attr-src-alg-type {
                     type string;
                     description
                       "Source algorithm type for 
                       translate-composite-nexthop";
                   }
                   leaf translate-composite-attr-dest-vrf-id {
                     type int32;
                     description
                       "Destination vrf id for translate-composite-nexthop";
                   }
                   leaf translate-composite-attr-src-vrf-id {
                     type int32;
                     description
                       "Source vrf id for translate-composite-nexthop";
                   }
                   leaf translate-composite-attr-hoplimit {
                     type int32;
                     description
                       "Hoplimit for translate-composite-nexthop";
                   }
                   leaf translate-composite-attr-traffic-class {
                     type int32;
                     description
                       "Traffic class for translate-composite-nexthop";
                   }
                   leaf translate-composite-attr-ttl {
                     type int32;
                     description
                       "Ttl for translate-composite-nexthop";
                   }
                   leaf translate-composite-attr-tos {
                     type int32;
                     description
                       "Tos for translate-composite-nexthop";
                   }
                 }
                 leaf to {
                   type string;
                   description
                     "Neighbor address to which to send (next-hop address)";
                 }
                 leaf metric {
                   type int32;
                 }
                 leaf aigp {
                   type string;
                   description
                     "AIGP";
                 }
                 leaf balance {
                   type int32;
                   description
                     "Next-hop balance";
                 }
                 leaf flags {
                   type string;
                   description
                     "Enabled trace flags";
                 }
                 leaf res-state {
                   type string;
                   description
                     "Status of route resolution";
                 }
                 leaf res-tsp-idx {
                   type int32;
                   description
                     "TSP index of the path";
                 }
                 leaf-list res-path-aux {
                   type string;
                 }
                 leaf-list res-path-aux-type {
                   type string;
                 }
                 leaf-list res-path-aux-flags {
                   type string;
                 }
                 leaf-list res-path-aux-rs-name {
                   type string;
                 }
                 leaf-list res-path-aux-rs-ribs {
                   type string;
                 }
                 leaf-list res-path-inode-flags {
                   type string;
                 }
                 leaf-list res-path-flags {
                   type string;
                 }
                 leaf-list res-path-fnh-link {
                   type string;
                 }
                 leaf-list res-path-inh-link {
                   type string;
                 }
                 leaf mpls-label {
                   type string;
                   description
                     "Label of MPLS packet";
                 }
                 leaf label-ttl-action {
                   type string;
                   description
                     "TTL action associated with labels";
                 }
                 leaf load-balance-label {
                   type string;
                   description
                     "Load balance action associated with labels";
                 }
                 leaf-list composite-nh {
                   type string;
                 }
                 leaf-list pnh-statistics-id-group {
                   type string;
                   description
                     "Statistics ID Group Associated with this protocol NH";
                 }
                 leaf-list vpnlabel-nh {
                   type string;
                 }
                 leaf-list indirect-nh {
                   type string;
                 }
                 leaf ext-int-type {
                   type string;
                   description
                     "Next-hop type of equal-external-internal multipath";
                 }
                 leaf gw-opaque {
                   type string;
                   description
                     "Nexthops gateway opaque data handle";
                 }
                 leaf-list forwarding-nh-count {
                   type int32;
                   description
                     "Number of indirect path forwarding next hops";
                 }
                 leaf-list merged-forwarding-nh-count {
                   type int32;
                   description
                     "Number of indirect path forwarding next hops (Merged)";
                 }
                 leaf nh-type {
                   type string;
                   description
                     "Special next hop: Reject, Blackhole, Receive, 
                     Multicast, Local, or Unused";
                 }
                 leaf-list node-prefix {
                   type string;
                 }
                 leaf-list node-prefix-length {
                   type int32;
                 }
                 leaf-list originating-rib {
                   type string;
                   description
                     "Routing table from which this route was learned";
                 }
                 leaf-list node-metric {
                   type int32;
                 }
                 leaf-list node-path-count {
                   type int32;
                   description
                     "Number of paths for this node";
                 }
                 leaf node-flags {
                   type int32;
                   description
                     "Flags for this node";
                 }
                 leaf-list node-address {
                   type string;
                 }
                 leaf-list node-forwarding-nh-count {
                   type int32;
                 }
                 leaf-list nh-subtype {
                   type string;
                   description
                     "Specified nexthop subtype";
                 }
                 leaf indirect-nh-count {
                   type int32;
                   description
                     "Number of indirect next hops";
                 }
                 leaf composite-nh-count {
                   type int32;
                   description
                     "Number of composite next hops";
                 }
                 container eth-header-rewrite {
                   description
                     "Ethernet header rewrite information";
                   leaf eth-header-rewrite-smac {
                     type string;
                     description
                       "Source MAC address";
                   }
                   leaf eth-header-rewrite-dmac {
                     type string;
                     description
                       "Destination MAC address";
                   }
                   leaf eth-header-rewrite-tpid {
                     type int32;
                     description
                       "Ethernet header TPID";
                   }
                   leaf eth-header-rewrite-tci {
                     type int32;
                     description
                       "Ethernet header TCI";
                   }
                   leaf eth-header-rewrite-vlan-id {
                     type int32;
                     description
                       "Ethernet header VLAN ID";
                   }
                   leaf eth-header-rewrite-ethertype {
                     type int32;
                     description
                       "Ethernet header ethertype";
                   }
                 }
                 container vxlan-header-rewrite {
                   description
                     "VXLAN tunnel rewrite information";
                   leaf vxlan-header-rewrite-mtu {
                     type int32;
                     description
                       "VXLAN tunnel MTU";
                   }
                   leaf vxlan-header-rewrite-flags {
                     type int32;
                     description
                       "VXLAN tunnel flags";
                   }
                   leaf vxlan-header-rewrite-encap-rtb-id {
                     type int32;
                     description
                       "VXLAN tunnel encapsulation table ID";
                   }
                   leaf vxlan-header-rewrite-decap-rtb-id {
                     type int32;
                     description
                       "VXLAN tunnel decapsulation table ID";
                   }
                   leaf vxlan-header-rewrite-encap-vnid {
                     type int32;
                     description
                       "VXLAN tunnel encapsulation VNI";
                   }
                   leaf vxlan-header-rewrite-decap-vnid {
                     type int32;
                     description
                       "VXLAN tunnel decapsulation VNI";
                   }
                   leaf vxlan-header-rewrite-svtep {
                     type jt:ipaddr;
                     description
                       "Source VTEP address";
                   }
                   leaf vxlan-header-rewrite-dvtep {
                     type jt:ipaddr;
                     description
                       "Destination VTEP address";
                   }
                   leaf vxlan-header-rewrite-smac {
                     type string;
                     description
                       "Source MAC address";
                   }
                   leaf vxlan-header-rewrite-dmac {
                     type string;
                     description
                       "Destination MAC address";
                   }
                 }
                 container fully-resolved-tunnel {
                   description
                     "GRE or UDP tunnel rewrite information";
                   leaf fully-resolved-tunnel-type {
                     type string;
                     description
                       "Tunnel type";
                   }
                   leaf fully-resolved-tunnel-dest {
                     type jt:ipaddr;
                     description
                       "Tunnel Destination";
                   }
                   leaf fully-resolved-tunnel-src {
                     type jt:ipaddr;
                     description
                       "Tunnel Source";
                   }
                   leaf fully-resolved-tunnel-ep-addr {
                     type jt:ipaddr;
                     description
                       "Tunnel endpoint address";
                   }
                   leaf fully-resolved-tunnel-encap-rtb-id {
                     type int32;
                     description
                       "Tunnel encap routing table id";
                   }
                   leaf fully-resolved-tunnel-decap-rtb-id {
                     type int32;
                     description
                       "Tunnel decap routing table id";
                   }
                 }
               }
               container srte-policy-state {
                 leaf sr-source {
                   type string;
                 }
                 leaf sr-origin {
                   type string;
                 }
                 leaf sr-preference {
                   type uint32;
                 }
                 leaf sr-preference-override {
                   type uint32;
                 }
                 leaf sr-route-distinguisher {
                   type uint32;
                 }
               }
               container srte-policy-information {
                 container srte-policy {
                   leaf srte-path-preference {
                     type uint32;
                   }
                   leaf srte-binding-sid {
                     type string;
                   }
                   leaf srte-adv-policy-name {
                     type string;
                   }
                   leaf srte-priority {
                     type uint32;
                   }
                   leaf srte-enlp {
                     type uint32;
                   }
                   leaf srte-tlv-recv-flags {
                     type string;
                   }
                   leaf srte-binding-sid-label-encoding {
                     type string;
                   }
                   list srte-segment-list {
                     leaf srte-segment-list-weight {
                       type uint32;
                     }
                     list srte-segment {
                       leaf srte-segment-label {
                         type uint32;
                       }
                       leaf srte-segment-label-ttl {
                         type string;
                         description
                           "SR Policy segment label ttl";
                       }
                       leaf srte-segment-type {
                         type string;
                         description
                           "SR Policy segment type";
                       }
                       leaf srte-segment-label-class {
                         type uint32;
                         description
                           "SR Policy segment label traffic-class";
                       }
                     }
                   }
                 }
               }
               container bgp-prefix-sid-attr {
                 description
                   "BGP Prefix SID Attribute";
                 container bgp-prefix-sid-attr-label-idx-tlv {
                   leaf bgp-prefix-sid-label-idx-index {
                     type int32;
                   }
                   leaf bgp-prefix-sid-attr-status {
                     type string;
                   }
                 }
                 container bgp-prefix-sid-attr-srgb-tlv {
                   list bgp-prefix-sid-srgb-block {
                     key "bgp-prefix-sid-srgb-block-start-label";
                     leaf bgp-prefix-sid-srgb-block-start-label {
                       type int32;
                     }
                     leaf bgp-prefix-sid-srgb-block-range {
                       type int32;
                     }
                   }
                 }
                 container bgp-prefix-sid-attr-service-tlv {
                   leaf bgp-prefix-sid-srv6-sid-value {
                     type jt:ipaddr;
                   }
                   leaf bgp-prefix-sid-attr-service-tlv-type {
                     type uint32;
                   }
                   leaf bgp-prefix-sid-attr-tlv-type {
                     type uint32;
                   }
                   leaf bgp-prefix-sid-srv6-sid-bh {
                     type uint32;
                   }
                   leaf bgp-prefix-sid-srv6-sid-bl {
                     type uint32;
                   }
                   leaf bgp-prefix-sid-srv6-sid-nl {
                     type uint32;
                   }
                   leaf bgp-prefix-sid-srv6-sid-fl {
                     type uint32;
                   }
                   leaf bgp-prefix-sid-srv6-sid-al {
                     type uint32;
                   }
                   leaf bgp-prefix-sid-srv6-sid-tl {
                     type uint32;
                   }
                   leaf bgp-prefix-sid-srv6-sid-to {
                     type uint32;
                   }
                 }
                 container bgp-prefix-sid-attr-unknown-tlvs {
                   list bgp-prefix-sid-attr-unknown-tlv {
                     key "bgp-prefix-sid-unknown-tlv-type";
                     leaf bgp-prefix-sid-unknown-tlv-type {
                       type uint32;
                     }
                     leaf bgp-prefix-sid-unknown-tlv-len {
                       type uint32;
                     }
                   }
                 }
               }
               container srte-policy-telemetry-statistics-state {
                 leaf srte-policy-telemetry-statistics-state.heading {
                   type string;
                 }
                 container srte-policy-telemetry-statistics-config {
                   leaf ingress {
                     type empty;
                     description
                       "Flag indicating ingress statistics is configured";
                   }
                   leaf transit {
                     type empty;
                     description
                       "Flag indicating transit statistics is configured";
                   }
                 }
                 list srte-policy-telemetry-statistics-sensor-information {
                   leaf sensor-type {
                     type string;
                   }
                   leaf sensor-status {
                     type string;
                   }
                   leaf sensor-id {
                     type int32;
                     description
                       "Unique identifier for the sensor";
                   }
                 }
               }
               list flex-tunnel-profile {
                 description
                   "Flex V4/V6 route tunnel attribute information";
                 container flex-tunnel-profile-info {
                   description
                     "The tunnel profile information";
                   leaf flex-tunnel-profile-num {
                     type int32;
                     description
                       "The tunnel profile number";
                   }
                   leaf flex-tunnel-profile-action {
                     type string;
                     description
                       "The action that this profile will be used for";
                   }
                   leaf flex-tunnel-profile-vni {
                     type int32;
                     description
                       "VXLAN Network Identifier (VNI)";
                   }
                   leaf flex-tunnel-profile-src-pfx {
                     type string;
                     description
                       "Source address and prefix length";
                   }
                   leaf flex-tunnel-profile-src-udp-port-range {
                     type string;
                     description
                       "Outer source UDP port range";
                   }
                   leaf flex-tunnel-profile-src-mac {
                     type string;
                     description
                       "Source MAC address, a 48-bit MAC value";
                   }
                   leaf flex-tunnel-profile-dest-pfx {
                     type string;
                     description
                       "Destination address";
                   }
                   leaf flex-tunnel-profile-dest-udp-port {
                     type int32;
                     description
                       "Outer destination UDP port";
                   }
                   leaf flex-tunnel-profile-dest-mac {
                     type string;
                     description
                       "Destination MAC address, a 48-bit MAC value";
                   }
                   leaf flex-tunnel-profile-flex-vxlan-flags {
                     type int32;
                     description
                       "Flex VxLAN flags";
                   }
                   leaf flex-tunnel-profile-reserved-24-bit-field {
                     type int32;
                     description
                       "VXLAN 24-bit reserved field as specified in RFC7348";
                   }
                   leaf flex-tunnel-profile-reserved-8-bit-field {
                     type int32;
                     description
                       "VXLAN 8-bit reserved field as specified in RFC7348";
                   }
                   container flex-tunnel-profile-stats {
                     description
                       "Statistics associated with tunnel";
                     leaf flex-tunnel-stats-pkts-count {
                       type int32;
                       description
                         "Packet count";
                     }
                     leaf flex-tunnel-stats-pps {
                       type int32;
                       description
                         "Packets per second";
                     }
                     leaf flex-tunnel-stats-bytes-count {
                       type int32;
                       description
                         "Byte count";
                     }
                     leaf flex-tunnel-stats-bps {
                       type int32;
                       description
                         "Bytes per second";
                     }
                   }
                 }
                 leaf flex-tunnel-profile-string {
                   type string;
                   description
                     "The tunnel profile string";
                 }
               }
               leaf preference2 {
                 type int32;
               }
               leaf age {
                 type string;
               }
               leaf med {
                 type int32;
                 description
                   "Multiple exit discriminator";
               }
               leaf local-preference {
                 type int32;
               }
               leaf rt-tag {
                 type int32;
               }
               leaf rt-tag2 {
                 type int32;
               }
               leaf learned-from {
                 type jt:ipaddr;
                 description
                   "Peer address from which this route was learned";
               }
               leaf peer-as {
                 type int32;
                 description
                   "Peer AS number";
               }
               leaf evpn-remote-mes {
                 type jt:ipaddr;
                 description
                   "Remote PE";
               }
               leaf evpn-routing-instance-name {
                 type string;
                 description
                   "Routing Instance";
               }
               leaf evpn-tag-rt-type {
                 type string;
                 description
                   "Route Type";
               }
               leaf evpn-vlan-id {
                 type int32;
                 description
                   "VLAN-ID";
               }
               leaf evpn-vpws-service-id {
                 type int32;
                 description
                   "VPWS Service-Id";
               }
               leaf rt-evpn-esi {
                 type string;
                 description
                   "ESI";
               }
               leaf evpn-isid {
                 type int32;
                 description
                   "ISID";
               }
               leaf rt-evpn-bmac {
                 type string;
                 description
                   "BMAC";
               }
               leaf bgp-rtarget-type {
                 type string;
                 description
                   "BGP RT-Constrain route type";
               }
               leaf bgp-rtarget-generation {
                 type uint32;
                 description
                   "BGP RT-Constrain generation";
               }
               leaf bgp-rtarget-for {
                 type string;
                 description
                   "BGP RT-Constrain member";
               }
               leaf nh-index {
                 type uint32;
                 description
                   "Next-hop index";
               }
               leaf transport-class {
                 type string;
                 description
                   "Transport class name";
               }
               leaf nh-address {
                 type string;
                 description
                   "Address of next hop";
               }
               leaf nh-reference-count {
                 type int32;
                 description
                   "Number of references to this next hop";
               }
               leaf ext-int-intf-index {
                 type int32;
                 description
                   "Interface index of equal-external-internal multipath";
               }
               leaf nh-session-id {
                 type uint32;
                 description
                   "Nexthop session id";
               }
               leaf nh-key-opaque {
                 type string;
                 description
                   "Nexthop key opaque handle";
               }
               leaf nh-non-key-opaque {
                 type string;
                 description
                   "Nexthop non-key opaque handle";
               }
               leaf nh-key-opaque-dump {
                 type string;
                 description
                   "Nexthop key opaque app dump";
               }
               leaf nh-non-key-opaque-dump {
                 type string;
                 description
                   "Nexthop non-key opaque app dump";
               }
               leaf nh-flood-overflow {
                 type empty;
                 description
                   "Flood nexthop exceeds maximum branches";
               }
               leaf nh-kernel-id {
                 type int32;
                 description
                   "Table Id for this next hop";
               }
               leaf client-data {
                 type string;
                 description
                   "Route server client details";
               }
               leaf route-distinguisher {
                 type string;
                 description
                   "Name of the route-distinguisher";
               }
               leaf reason-for-invalid {
                 type string;
               }
               leaf thread-name {
                 type string;
               }
               leaf pmsi {
                 type string;
                 description
                   "P-multicast service interface";
               }
               leaf connector {
                 type string;
               }
               leaf color {
                 type int32;
               }
               leaf color2 {
                 type int32;
               }
               leaf prefix-segment-index {
                 type int32;
               }
               leaf rt-isis-level {
                 type int32;
               }
               leaf rt-isis-downbit {
                 type int32;
               }
               leaf rt-entry-state {
                 type string;
                 description
                   "State of this route entry";
               }
               leaf rt-fib-install-priority {
                 type string;
                 description
                   "Route FIB installation priority";
               }
               leaf rt-ack-state {
                 type string;
                 description
                   "Route acknowledgement state";
               }
               leaf rt-ack-ll-flag {
                 type string;
                 description
                   "Status of route ACK flags";
               }
               leaf rt-ack-req-ts {
                 type string;
                 description
                   "Time when ack request is sent";
               }
               leaf rt-ack-res-time {
                 type uint32;
                 description
                   "Ack route response time";
               }
               leaf rt-ack-re-flash-time {
                 type string;
                 description
                   "Time when ack is re flashed to protocols";
               }
               leaf rt-ack-re-flash-status {
                 type string;
                 description
                   "Status of ACK re-flash to protocols";
               }
               leaf rt-ack-guid {
                 type uint64;
                 description
                   "Ack route global identifier";
               }
               leaf rt-ack-olc {
                 type uint64;
                 description
                   "Ack route global version";
               }
               leaf rt-ack-local-ver {
                 type uint32;
                 description
                   "Ack route global version";
               }
               leaf rt-ack-and-err-flag {
                 type uint32;
                 description
                   "Route ack and error flag";
               }
               leaf rt-ack-history {
                 type uint32;
                 description
                   "Route ack history";
               }
               leaf pfe-err-state {
                 type string;
                 description
                   "Route error state from PFE";
               }
               leaf pfe-err-time {
                 type uint32;
                 description
                   "Route error receive time";
               }
               leaf rt-ver-id {
                 type uint32;
                 description
                   "Route version ID";
               }
               leaf rt-entry-pim-state {
                 type string;
                 description
                   "PIM state of this route entry";
               }
               leaf inactive-reason {
                 type string;
                 description
                   "HFRR profile Inactive reason (if any)";
               }
               leaf local-as {
                 type int32;
                 description
                   "Local AS number";
               }
               leaf med-plus-igp {
                 type int32;
               }
               leaf rt-aigp {
                 type uint64;
               }
               leaf rt-effective-aigp {
                 type uint64;
                 description
                   "Effective AIGP value used by route selection";
               }
               leaf rt-effective-aigp-reason {
                 type string;
                 description
                   "Reason why the effective AIGP value was selected";
               }
               leaf rt-resolving-aigp {
                 type uint64;
               }
               leaf rt-effective-metric {
                 type uint64;
                 description
                   "Effective metric value used by route selection";
               }
               leaf rt-effective-metric-reason {
                 type string;
                 description
                   "Reason why the effective metric value was selected";
               }
               leaf rt-orr {
                 type uint32;
               }
               leaf rt-actual-igp-metric {
                 type uint32;
               }
               leaf rt-ospf-area {
                 type string;
               }
               leaf task-name {
                 type string;
                 description
                   "Name of this task";
               }
               leaf announce-bits {
                 type int32;
               }
               leaf announce-tasks {
                 type string;
               }
               leaf flow-id {
                 type int32;
               }
               leaf bgp-rt-flag {
                 type string;
                 description
                   "BGP route flag";
               }
               leaf label-base {
                 type int32;
                 description
                   "Label base for l2vpn";
               }
               leaf label-range {
                 type int32;
                 description
                   "Label range for l2vpn";
               }
               leaf l2vpn-status-vector {
                 type string;
               }
               leaf label-offset {
                 type int32;
                 description
                   "Label offset for l2vpn";
               }
               leaf remote-site {
                 type int32;
                 description
                   "Remote site id";
               }
               leaf l2vpn-mesh-group {
                 type string;
               }
               leaf vc-label {
                 type int32;
                 description
                   "VC label";
               }
               leaf context-id {
                 type jt:ipaddr;
                 description
                   "Context Identifier";
               }
               leaf route-control-word {
                 type string;
                 description
                   "Control Word";
               }
               leaf mtu {
                 type int32;
                 description
                   "MTU along an interface";
               }
               leaf cell-bundle-size {
                 type int32;
                 description
                   "Cell bundle size";
               }
               leaf vlan-id {
                 type int32;
               }
               leaf flow-label-transmit {
                 type int32;
               }
               leaf flow-label-receive {
                 type int32;
               }
               leaf tdm-payload-size {
                 type int32;
               }
               leaf tdm-bitrate {
                 type int32;
               }
               leaf pw-status-code {
                 type int32;
               }
               leaf cac-bandwidth-failure {
                 type empty;
                 description
                   "Call admission control failure due to insufficient 
                   bandwidth";
               }
               leaf vpn-label {
                 type int32;
                 description
                   "VPN label";
               }
               leaf route-label {
                 type int32;
                 description
                   "Route label";
               }
               leaf route-labels {
                 type string;
                 description
                   "Route label";
               }
               leaf mac-route-esi {
                 type string;
                 description
                   "ESI";
               }
               leaf evpn-igmp-flags {
                 type int32;
                 description
                   "IGMP flags";
               }
               leaf evpn-mld-flags {
                 type int32;
                 description
                   "MLD flags";
               }
               leaf evpn-leave-reserved {
                 type int32;
                 description
                   "IGMP Leave Reserved Field";
               }
               leaf evpn-leave-mrt {
                 type int32;
                 description
                   "IGMP Leave Max Response Time";
               }
               leaf overlay-gateway-address {
                 type jt:ipaddr;
                 description
                   "Overlay gateway address";
               }
               leaf reroute-address {
                 type jt:ipaddr;
                 description
                   "Reroute address";
               }
               leaf bgp-otc {
                 type int32;
               }
               leaf peer-id {
                 type jt:ipaddr;
               }
               leaf rt-entry-ext-pfx-attr-flags {
                 type string;
                 description
                   "Route entry extended prefix attribute flags";
               }
               leaf rt-entry-ext-pfx-source-rtrid {
                 type string;
                 description
                   "Route entry extended prefix source rtr id";
               }
               leaf path-id {
                 type string;
               }
               leaf gateway {
                 type string;
                 description
                   "Sourcing gateway";
               }
               leaf rtrib-primary {
                 type string;
                 description
                   "Primary routing table";
               }
               leaf rib-export-rtrib-primary {
                 type string;
                 description
                   "RIB export primary routing table";
               }
               leaf rtrib-secondary {
                 type string;
                 description
                   "Secondary routing table";
               }
               leaf indirect-nh-count {
                 type int32;
                 description
                   "Number of indirect next hops";
               }
               leaf composite-nh-count {
                 type int32;
                 description
                   "Number of composite next hops";
               }
               leaf helper-nhid {
                 type uint32;
                 description
                   "Helper nexthop index";
               }
               leaf helper-refcount {
                 type int32;
                 description
                   "Reference count of those needing helper route";
               }
               leaf backup-pe-group-name {
                 type string;
                 description
                   "Name of the backup PE group";
               }
               leaf designated-forwarder {
                 type string;
                 description
                   "Indicates if we are the designated forwarder for this 
                   route";
               }
               leaf rt-entry-opaque-data {
                 type string;
                 description
                   "Opaque data associated with the route entry";
               }
               leaf rt-stats-id-grp-single-line {
                 type string;
                 description
                   "Stats-id-group associated with the route entry";
               }
               leaf rt-entry-ext-pfx-sid-data {
                 type string;
                 description
                   "Route entry extended prefix sid data";
               }
               leaf hidden-reason {
                 type string;
                 description
                   "Protocol's reason for hiding the route";
               }
               leaf bgp-bmp-send-flag-start {
                 type string;
               }
               leaf bgp-bmp-send-flag-pre {
                 type string;
               }
               leaf bgp-bmp-send-flag-post {
                 type string;
               }
               leaf bgp-bmp-send-flag-ribout-prepolicy {
                 type string;
               }
               leaf bgp-bmp-send-flag-ribout-postpolicy {
                 type string;
               }
               leaf bgp-bmp-send-flag-station {
                 type string;
               }
               leaf bgp-nnh-nodes {
                 type string;
                 description
                   "Next-next-hop nodes";
               }
               leaf bgp-nh-nnh-map {
                 type string;
                 description
                   "Next-hop to next-next-hop map";
               }
               leaf bgp-profile-creation-failure-reason {
                 type string;
                 description
                   "Reason for failing to create profile for next-next-hop 
                   map";
               }
               leaf bgp-nh-nnh-entry {
                 type string;
                 description
                   "Next-hop to next-next-hop entry";
               }
               leaf glb-profile {
                 type string;
                 description
                   "GLB Profile";
               }
               leaf glb-profile-id {
                 type uint32;
                 description
                   "GLB Profile ID";
               }
               leaf rt-entry-stats {
                 type string;
                 description
                   "Route entry statistics data";
               }
               container connection-bandwidth {
                 description
                   "Bandwidth of a layer 2 connection";
                 leaf connection-bandwidth.heading {
                   type string;
                   description
                     "Bandwidth of a layer 2 connection";
                 }
                 leaf bandwidth {
                   type string;
                 }
                 leaf class-type {
                   type int32;
                 }
                 leaf class-bandwidth {
                   type int32;
                 }
               }
               container route-flap-damping {
                 leaf last-merit {
                   type int32;
                   description
                     "Last merit value";
                 }
                 leaf merit {
                   type int32;
                   description
                     "Current merit value";
                 }
                 leaf damping-parameters {
                   type string;
                 }
                 leaf default-damping-parameters {
                   type empty;
                   description
                     "Default damping parameters used";
                 }
                 leaf last-update {
                   type string;
                 }
                 leaf first-update {
                   type string;
                 }
                 leaf route-flap-count {
                   type int32;
                   description
                     "Number of times this route has flapped";
                 }
                 leaf suppressed {
                   type empty;
                   description
                     "This route is suppressed";
                 }
                 leaf reuse-time {
                   type string;
                   description
                     "Time until this route is reusable";
                 }
                 leaf reuse-preference {
                   type int32;
                   description
                     "Preference to use when this route is reused";
                 }
                 leaf expire-time {
                   type string;
                   description
                     "Time when this damping entry expires";
                 }
               }
               container nhh {
                 leaf nh-type {
                   type string;
                   description
                     "Special next hop: Reject, Blackhole, Receive, 
                     Multicast, Local, or Unused";
                 }
                 leaf nh-index {
                   type uint32;
                   description
                     "Next-hop index";
                 }
                 leaf transport-class {
                   type string;
                   description
                     "Transport class name";
                 }
                 leaf nh-address {
                   type string;
                   description
                     "Address of next hop";
                 }
                 leaf nh-reference-count {
                   type int32;
                   description
                     "Number of references to this next hop";
                 }
                 leaf ext-int-intf-index {
                   type int32;
                   description
                     "Interface index of equal-external-internal multipath";
                 }
                 leaf nh-session-id {
                   type uint32;
                   description
                     "Nexthop session id";
                 }
                 leaf nh-key-opaque {
                   type string;
                   description
                     "Nexthop key opaque handle";
                 }
                 leaf nh-non-key-opaque {
                   type string;
                   description
                     "Nexthop non-key opaque handle";
                 }
                 leaf nh-key-opaque-dump {
                   type string;
                   description
                     "Nexthop key opaque app dump";
                 }
                 leaf nh-non-key-opaque-dump {
                   type string;
                   description
                     "Nexthop non-key opaque app dump";
                 }
                 leaf nh-flood-overflow {
                   type empty;
                   description
                     "Flood nexthop exceeds maximum branches";
                 }
                 leaf nh-kernel-id {
                   type int32;
                   description
                     "Table Id for this next hop";
                 }
               }
               list nh-expand {
                 key "nhe-name nhe-handle";
                 description
                   "Next-hop gateway information";
                 leaf nhe-name {
                   type string;
                   description
                     "Name of next-hop";
                 }
                 leaf nhe-handle {
                   type string;
                   description
                     "Nexthop pointer";
                 }
                 leaf nhe-index {
                   type int32;
                   description
                     "Next-hop index";
                 }
                 leaf nhe-to {
                   type string;
                   description
                     "Nexthop address";
                 }
                 leaf nhe-mbr-count {
                   type int32;
                   description
                     "Number of child nexhops";
                 }
                 leaf nhe-mpls-label {
                   type string;
                   description
                     "Label of MPLS packet";
                 }
               }
               list rt-session-id {
                 key "rt-session-id-value";
                 description
                   "Session-IDs associated with route";
                 leaf rt-session-id-value {
                   type int32;
                   description
                     "Value of session-id";
                 }
                 leaf rt-session-id-version {
                   type int32;
                   description
                     "Version of session-id";
                 }
               }
               container flex-rt-statistics {
                 description
                   "Statistics associated with route";
                 leaf flex-rt-statistics-pkts-count {
                   type int32;
                   description
                     "Packet count";
                 }
                 leaf flex-rt-statistics-pps {
                   type int32;
                   description
                     "Pps";
                 }
                 leaf flex-rt-statistics-bytes-count {
                   type int32;
                   description
                     "Byte count";
                 }
                 leaf flex-rt-statistics-bps {
                   type int32;
                   description
                     "Bps";
                 }
               }
               leaf bgp-group-name {
                 type string;
               }
               leaf bgp-no-label-reason {
                 type string;
               }
               leaf sr-policy-distinguisher {
                 type uint32;
               }
               leaf sr-policy-color {
                 type uint32;
               }
               leaf sr-policy-endpoint {
                 type jt:ipaddr;
               }
               leaf bgp-metric-flags {
                 type string;
                 description
                   "BGP metrics flags";
               }
               leaf bgp-output-queue-class {
                 type string;
                 description
                   "BGP output queue class";
               }
               leaf cluster-id {
                 type string;
               }
               leaf originator {
                 type string;
               }
               leaf bgp-aigp {
                 type string;
                 description
                   "Accumulated IGP Metric";
               }
               leaf bgp-elc {
                 type empty;
                 description
                   "Entropy label capable";
               }
               leaf bgp-elc-v2 {
                 type empty;
                 description
                   "Entropy label capable version 2";
               }
               leaf bgp-elc-v3 {
                 type empty;
                 description
                   "Entropy label capable version 3";
               }
               leaf bgp-nhc-unknown-characteristics-len {
                 type uint32;
                 description
                   "Total length of NHC unknown characteristics";
               }
               leaf bgp-nhc-nh-valid {
                 type string;
                 description
                   "Whether next hop field matches route next hop";
               }
               leaf bgp-nhc-characteristic-code {
                 type uint32;
                 description
                   "NHC characteristic code";
               }
               leaf bgp-nhc-characteristic-len {
                 type uint32;
                 description
                   "NHC characteristic length";
               }
               leaf bgp-nhc-characteristic-val {
                 type string;
                 description
                   "NHC characteristic value";
               }
             }
             list kern-nhexpand {
               key "kern-nhe-name kern-nhe-handle";
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf kern-nhe-platform-layer-input {
                 type empty;
                 description
                   "Platform layer input nexthop";
               }
               leaf kern-nhe-platform-layer-output {
                 type empty;
                 description
                   "Platform layer output nexthop";
               }
               leaf kern-nhe-in-kernel {
                 type empty;
                 description
                   "Nexthop install in kernel";
               }
               leaf kern-nhe-fib-channel {
                 type string;
                 description
                   "Fib channel in which route is installed";
               }
               leaf kern-nhe-name {
                 type string;
                 description
                   "Name of next-hop";
               }
               leaf kern-nhe-subtype {
                 type string;
                 description
                   "Nexthop Subtype";
               }
               leaf kern-nhe-handle {
                 type string;
                 description
                   "Nexthop pointer";
               }
               leaf kern-nhe-index {
                 type int32;
                 description
                   "Next-hop index";
               }
               leaf kern-gw-flags {
                 type string;
                 description
                   "Nexthop gateway flags";
               }
               leaf kern-gw-opaque {
                 type string;
                 description
                   "Nexthop gateway opaque data handle";
               }
               leaf kern-key-opaque {
                 type string;
                 description
                   "Nexthop key opaque data handle";
               }
               leaf kern-nhe-to {
                 type string;
                 description
                   "Nexthop address";
               }
               leaf kern-nhe-mbr-count {
                 type int32;
                 description
                   "Number of child nexhops";
               }
               leaf kern-nhe-mpls-label {
                 type string;
                 description
                   "Label of MPLS packet";
               }
               leaf kern-nhe-pnh {
                 type string;
                 description
                   "Protocol Nexthop address";
               }
               leaf kern-nhe-fib-nh-str {
                 type string;
                 description
                   "FIB inh or cnh identifier";
               }
               leaf kern-nhe-sessionid {
                 type int32;
                 description
                   "Session ID";
               }
               leaf kern-nhe-tunnel-type {
                 type string;
                 description
                   "Tunnel type";
               }
               leaf kern-nhe-tunnel-src {
                 type string;
                 description
                   "Tunnel Source address";
               }
               leaf kern-nhe-tunnel-dest {
                 type string;
                 description
                   "Tunnel Destination address";
               }
               leaf kern-nhe-tunnel-ep {
                 type string;
                 description
                   "Tunnel Endpoint address";
               }
               leaf kern-nhe-tunnel-vxlan-encap-vni {
                 type int32;
                 description
                   "VxLAN tunnel encap vni";
               }
               leaf kern-nhe-tunnel-vxlan-decap-vni {
                 type int32;
                 description
                   "VxLAN tunnel decap vni";
               }
               leaf kern-nhe-translate-type {
                 type string;
                 description
                   "Translation type";
               }
               leaf kern-nhe-translate-src {
                 type string;
                 description
                   "Translation Source address";
               }
               leaf kern-nhe-translate-src-plen {
                 type int32;
                 description
                   "Translation Source address prefix length";
               }
               leaf kern-nhe-translate-dest {
                 type string;
                 description
                   "Translation Destination address";
               }
               leaf kern-nhe-translate-dest-plen {
                 type int32;
                 description
                   "Translation Destination address prefix length";
               }
               leaf kern-nhe-tunnel-encap-rtb-id {
                 type int32;
                 description
                   "Tunnel encap routing table id";
               }
               leaf kern-nhe-tunnel-decap-rtb-id {
                 type int32;
                 description
                   "Tunnel decap routing table id";
               }
               leaf kern-nhe-interface {
                 type string;
                 description
                   "Interface";
               }
               leaf kern-nhe-slice-gencfg-id {
                 type int32;
                 description
                   "Slice-Gencfg ID";
               }
               leaf kern-nhe-sliceid {
                 type int32;
                 description
                   "Slice ID";
               }
               leaf kern-nhe-fwf {
                 type string;
                 description
                   "Filter Name";
               }
               leaf kern-nhe-flex-tunnel-info {
                 type string;
                 description
                   "Flex-tunnel information of nexthop";
               }
               leaf kern-nhe-flags {
                 type string;
                 description
                   "Nexthop flags";
               }
               leaf kern-nhe-stats-id-group {
                 type string;
                 description
                   "Statistics ID Group associated with nexthop";
               }
               leaf kern-nhe-reference-count {
                 type int32;
                 description
                   "Nexthop reference count";
               }
               leaf kern-elnh-address {
                 type string;
                 description
                   "Address of Element Next-hop";
               }
             }
             leaf rt-entry-count {
               type int32;
               description
                 "Number of route entries in this route";
             }
             leaf rt-announced-count {
               type int32;
               description
                 "Number of announced route entries";
             }
             leaf rt-state {
               type string;
               description
                 "State of this route";
             }
             leaf-list tsi {
               type string;
               description
                 "Task-specific information";
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
           }
           container route-state-history {
             list route-state-history-elements {
               key "rt-history-time";
               leaf rt-history-time {
                 type string;
               }
               leaf rt-history-event {
                 type string;
               }
             }
           }
         }
       }
       container ospf-neighbor-information {
         description
           "Information about OSPF neighbors in a routing instance";
         list ospf-neighbor {
           key "interface-name neighbor-id ospf-area";
           leaf neighbor-address {
             type jt:ipaddr;
             description
               "IP address of this neighbor";
           }
           leaf interface-name {
             type string;
             description
               "Name of interface";
           }
           leaf ospf-neighbor-state {
             type string;
           }
           leaf neighbor-id {
             type jt:ipaddr;
           }
           leaf neighbor-priority {
             type int32;
           }
           leaf activity-timer {
             type int32;
           }
           leaf ospf-area {
             type string;
             description
               "Area ID";
           }
           leaf options {
             type int32;
           }
           leaf dr-address {
             type jt:ipaddr;
             description
               "IP address of DR";
           }
           leaf bdr-address {
             type jt:ipaddr;
             description
               "IP address of BDR";
           }
           leaf neighbor-secondary {
             type empty;
             description
               "OSPF neighbor is on secondary interface";
           }
           leaf neighbor-up-time {
             type string;
             description
               "Time when neighbor came up";
           }
           leaf neighbor-adjacency-time {
             type string;
             description
               "Time when neighbor became adjacent";
           }
           leaf neighbor-last-out-of-band-resync-time {
             type string;
             description
               "Time since last successful oob-resync";
           }
           leaf neighbor-suppress-hello {
             type int32;
             description
               "Time when neighbor suppressed hellos";
           }
           leaf adj-sid-list {
             type string;
           }
           leaf master-slave {
             type string;
           }
           leaf sequence-number {
             type int64;
             description
               "History event number";
           }
           leaf dbd-retransmit-time {
             type int32;
             description
               "Seconds until DBD is retransmitted";
           }
           leaf lsreq-retransmit-time {
             type int32;
             description
               "Seconds until LSREQ is retransmitted";
           }
           leaf lsreq-enqueued {
             type empty;
           }
           leaf lsreq-active {
             type empty;
           }
           leaf lsa-list {
             type string;
           }
           list ospf-neighbor-topology {
             key "ospf-topology-name";
             description
               "OSPF topology specific neighbor information";
             leaf ospf-topology-name {
               type string;
               description
                 "OSPF topology name";
             }
             leaf ospf-topology-id {
               type int32;
               description
                 "OSPF topology id";
             }
             leaf ospf-neighbor-topology-state {
               type string;
               description
                 "State of the neighbor in a topology";
             }
           }
         }
       }
       container ospf3-neighbor-information {
         list ospf3-neighbor {
           key "neighbor-id interface-name ospf-area";
           leaf neighbor-id {
             type jt:ipaddr;
           }
           leaf interface-name {
             type string;
             description
               "Name of interface";
           }
           leaf ospf-neighbor-state {
             type string;
           }
           leaf neighbor-priority {
             type int32;
           }
           leaf activity-timer {
             type int32;
           }
           leaf neighbor-address {
             type jt:ipaddr;
             description
               "IP address of this neighbor";
           }
           leaf ospf-area {
             type string;
             description
               "Area ID";
           }
           leaf options {
             type int32;
           }
           leaf neighbor-secondary {
             type empty;
             description
               "OSPF neighbor is on secondary interface";
           }
           leaf ospf3-interface-index {
             type int32;
           }
           leaf neighbor-cost {
             type int32;
             description
               "Cost associated with this neighbor";
           }
           leaf dr-id {
             type jt:ipaddr;
           }
           leaf bdr-id {
             type jt:ipaddr;
           }
           leaf neighbor-up-time {
             type string;
             description
               "Time when neighbor came up";
           }
           leaf neighbor-adjacency-time {
             type string;
             description
               "Time when neighbor became adjacent";
           }
           leaf neighbor-suppress-hello {
             type int32;
             description
               "Time when neighbor suppressed hellos";
           }
           leaf master-slave {
             type string;
           }
           leaf sequence-number {
             type int64;
             description
               "History event number";
           }
           leaf dbd-retransmit-time {
             type int32;
             description
               "Seconds until DBD is retransmitted";
           }
           leaf lsreq-retransmit-time {
             type int32;
             description
               "Seconds until LSREQ is retransmitted";
           }
           leaf lsreq-enqueued {
             type empty;
           }
           leaf lsreq-active {
             type empty;
           }
           leaf lsa-list {
             type string;
           }
         }
       }
       container isis-overview-information {
         description
           "ISIS overview information";
         container isis-overview {
           description
             "Overview information for an IS-IS instance";
           leaf instance-name {
             type string;
           }
           leaf isis-instance-id {
             type uint16;
             description
               "IS-IS Instance ID";
           }
           leaf isis-router-id {
             type jt:ipaddr;
             description
               "IS-IS router ID";
           }
           leaf isis-v6-router-id {
             type jt:ipv6addr;
             description
               "IS-IS IPv6 Router ID";
           }
           leaf isis-router-hostname {
             type string;
             description
               "IS-IS router hostname";
           }
           leaf isis-router-sysid {
             type string;
             description
               "IS-IS router sysid";
           }
           leaf isis-router-areaid {
             type string;
             description
               "IS-IS router areaid";
           }
           leaf isis-max-areas {
             type uint32;
             description
               "Maximum Number of Areas";
           }
           leaf isis-lsp-lifetime {
             type uint32;
             description
               "Maximum LSP lifetime";
           }
           leaf isis-lsp-lifetime-filter {
             type uint32;
             description
               "Low LSP life time filter";
           }
           leaf isis-reference-bandwidth {
             type uint64;
             description
               "Bandwidth for calculating metric defaults";
           }
           leaf isis-adjacency-holddown {
             type string;
             description
               "IS-IS Adjacency holddown status";
           }
           leaf isis-attached-bit-evaluation {
             type string;
             description
               "The IS-IS L1 attached bit evaluation";
           }
           leaf isis-layer2-map-enabled {
             type string;
             description
               "IS-IS controls kernel ARP/ND entries for its nexthops";
           }
           container isis-spf-information {
             description
               "SPF options";
             leaf isis-spf-delay {
               type string;
               description
                 "Delay before performing SPF calculations";
             }
             leaf isis-spf-holddown {
               type string;
               description
                 "Throttling delay between consecutive SPF calculations";
             }
             leaf isis-spf-rapid-runs {
               type uint32;
               description
                 "Number of rapid SPF calculations before SPF holddown.";
             }
             leaf isis-uloop-avoidance {
               type string;
               description
                 "Micro-loop avoidance status";
             }
             leaf isis-uloop-avoidance-method {
               type string;
               description
                 "Micro-loop avoidance mechanism employed";
             }
             leaf isis-route-convergence-delay {
               type string;
               description
                 "Delay before downloading routes to forwarding plane";
             }
             leaf isis-topo-sessid-count {
               type uint32;
               description
                 "Number of Session IDs associated with routes in this 
                 topology";
             }
             container isis-spf {
               leaf node-count {
                 type int32;
               }
               container isis-spf-results-header {
                 leaf isis-topology-id {
                   type string;
                 }
                 leaf level {
                   type int32;
                   description
                     "IS-IS Level";
                 }
               }
               list isis-spf-result {
                 leaf node-id {
                   type string;
                 }
                 leaf metric {
                   type int32;
                 }
                 leaf disconnected {
                   type empty;
                 }
                 leaf no-first-fragment {
                   type empty;
                 }
                 leaf-list node-address {
                   type string;
                 }
                 list next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 list prefix-element {
                   leaf prefix-metric {
                     type int32;
                   }
                   leaf external-prefix-metric {
                     type int32;
                   }
                   leaf address-prefix {
                     type jt:ipaddr;
                   }
                 }
                 list end-system-element {
                   leaf end-system-metric {
                     type int32;
                   }
                   leaf end-system-id {
                     type string;
                     description
                       "Six-octet ISO system ID for a end-system";
                   }
                 }
               }
               container isis-spf-log-header {
                 leaf isis-topology-id {
                   type string;
                 }
                 leaf level {
                   type int32;
                   description
                     "IS-IS Level";
                 }
               }
               container isis-spf-log {
                 leaf start-time {
                   type string;
                 }
                 leaf elapsed-time {
                   type string;
                   description
                     "Time this adjacency or session has been up or down";
                 }
                 leaf spf-trigger-count {
                   type int32;
                 }
                 leaf logging-reason {
                   type string;
                 }
                 leaf lsp-name {
                   type string;
                   description
                     "Tunneled into an RSVP LSP";
                 }
                 leaf system-name {
                   type string;
                   description
                     "Hostname for a system";
                 }
                 leaf interface-name {
                   type string;
                   description
                     "Name of interface";
                 }
                 leaf change-reason {
                   type string;
                 }
                 leaf mla-topo-change-time {
                   type string;
                 }
                 leaf mla-prefix-change-time {
                   type string;
                 }
                 leaf tilfa-topo-change-time {
                   type string;
                 }
                 leaf tilfa-prefix-change-time {
                   type string;
                 }
                 leaf-list route-build-time {
                   type string;
                 }
               }
               container isis-backup-spf-result {
                 leaf node-id {
                   type string;
                 }
                 leaf no-first-fragment {
                   type empty;
                 }
                 leaf backup-root {
                   type string;
                 }
                 leaf backup-root-metric {
                   type int32;
                 }
                 leaf metric {
                   type int32;
                 }
                 leaf backup-root-preference {
                   type int32;
                 }
                 leaf track-item {
                   type string;
                 }
                 leaf track-item-isnbr {
                   type string;
                 }
                 leaf rev-track-item {
                   type string;
                 }
                 leaf rev-track-item-isnbr {
                   type string;
                 }
                 leaf-list node-address {
                   type string;
                 }
                 list next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                 }
                 list backup-next-hop-element {
                   leaf interface-name {
                     type string;
                     description
                       "Name of interface";
                   }
                   leaf isis-next-hop-type {
                     type string;
                   }
                   leaf isis-next-hop {
                     type string;
                   }
                   leaf-list snpa {
                     type string;
                   }
                   leaf snpa-type {
                     type string;
                     description
                       "Type of SNPA";
                   }
                   list pfe-port-snpa {
                     key "pfe-id";
                     description
                       "PFE Port SNPA";
                     leaf pfe-id {
                       type int32;
                     }
                     leaf port-id {
                       type int32;
                     }
                   }
                   container network-element-port-snpa {
                     description
                       "Network Element Port SNPA";
                     leaf port-id {
                       type int32;
                     }
                   }
                   container mstp-root-snpa {
                     description
                       "Multiple Spanning Tree Protocol Root SNPA";
                     leaf mstp-root-id {
                       type int32;
                     }
                   }
                   list gateway-snpa {
                     key "gateway-addr";
                     description
                       "Gateway SNPA";
                     leaf gateway-addr {
                       type jt:ipaddr;
                     }
                   }
                   container layer2-domain-port-snpa {
                     description
                       "Layer-2 Domain Port SNPA";
                     leaf port-id {
                       type int32;
                     }
                   }
                   container replication-block-snpa {
                     description
                       "Replication Block SNPA";
                     leaf replication-block-id {
                       type int32;
                     }
                   }
                   container replication-route-snpa {
                     description
                       "Replication Route SNPA";
                     leaf network-element-id {
                       type jt:ipaddr;
                     }
                   }
                   container layer2-multicast-port-snpa {
                     description
                       "Layer-2 Multicast Port SNPA";
                     leaf layer2-multicast-port-id {
                       type int32;
                     }
                   }
                   container inh-snpa {
                     description
                       "Indirection SNPA";
                     leaf inh-id {
                       type int32;
                     }
                   }
                   leaf isis-backup-prefix-refcount {
                     type uint32;
                     description
                       "Number of prefixes that uses this nexthop as backup";
                   }
                   leaf isis-backup-score {
                     type string;
                   }
                 }
                 list no-coverage-reason-element {
                   leaf isis-next-hop-type {
                     type string;
                   }
                   leaf no-coverage-reason {
                     type string;
                   }
                 }
               }
             }
           }
           container isis-overload-information {
             description
               "Overload bit behaviour at startup";
             leaf isis-overload-enabled {
               type empty;
               description
                 "Overload bit upon startup is set";
             }
             leaf isis-overload-high-metrics {
               type string;
               description
                 "High metrics are used for Overload signaling";
             }
             leaf isis-overload-allow-route-leaking {
               type string;
               description
                 "Allow route leaking when configured to be in overload";
             }
             leaf isis-overload-internal-prefixes {
               type string;
               description
                 "Allow internal prefixes to be advertised with high metric";
             }
             leaf isis-overload-external-prefixes {
               type string;
               description
                 "Allow external prefixes to be advertised with high metric";
             }
             leaf isis-overload-timeout {
               type int32;
               description
                 "Clearance of the Overload bit after startup";
             }
             leaf isis-overload-remaining-time {
               type string;
               description
                 "Time remaining on configured overload timeout";
             }
           }
           container isis-routing {
             description
               "List of routed IS-IS address families";
             leaf isis-routing-ipv4 {
               type empty;
               description
                 "Routing IPv4 prefixes is enabled";
             }
             leaf isis-routing-ipv6 {
               type empty;
               description
                 "Routing IPv6 prefixes is enabled";
             }
             leaf isis-routing-clns {
               type empty;
               description
                 "Routing CLNS prefixes is enabled";
             }
             leaf isis-routing-spring-mpls {
               type empty;
               description
                 "Routing CLNS prefixes is enabled";
             }
           }
           container isis-traffic-engineering {
             description
               "Traffic engineering";
             leaf isis-te-status {
               type string;
               description
                 "Traffic engineering status";
             }
             leaf isis-ted-ipv6 {
               type string;
               description
                 "Traffic Engineering v6 status";
             }
             leaf isis-te-shortcuts-ipv4 {
               type empty;
               description
                 "IPv4 Traffic engineering shortcuts are enabled";
             }
             leaf isis-te-shortcuts-ipv6 {
               type empty;
               description
                 "IPv6 Traffic engineering shortcuts are enabled";
             }
             leaf isis-te-shortcuts-ipv4-mpls {
               type empty;
               description
                 "IPv4-MPLS Traffic engineering shortcuts are enabled";
             }
             leaf isis-te-shortcuts-ipv6-mpls {
               type empty;
               description
                 "IPv6-MPLS Traffic engineering shortcuts are enabled";
             }
             leaf isis-te-shortcuts-clns {
               type empty;
               description
                 "CLNS Traffic engineering shortcuts are enabled";
             }
             leaf isis-ipv4-multicast-rpf-routes {
               type empty;
               description
                 "IPv4 routes for multicast RPF checks are installed into 
                 inet.2";
             }
             leaf isis-ignore-lsp-metrics {
               type empty;
               description
                 "Label-switched path metrics when doing shortcuts are 
                 ignored";
             }
             leaf isis-ted-credibility-preference {
               type empty;
               description
                 "Credibility follows protocol preference";
             }
           }
           container isis-restart {
             description
               "IS-IS restart parameters";
             leaf isis-restart-enabled {
               type string;
               description
                 "IS-IS restart mode";
             }
             leaf isis-restart-duration {
               type uint32;
               description
                 "Duration of IS-IS restart";
             }
             leaf isis-restart-helper-mode-enabled {
               type string;
               description
                 "IS-IS helper mode";
             }
           }
           container isis-tilfa {
             description
               "IS-IS Post Convergence Backup parameters";
             leaf isis-tilfa-enabled {
               type string;
               description
                 "Post Convergence Backup";
             }
             leaf isis-tilfa-max-labels {
               type int32;
               description
                 "Max labels";
             }
             leaf isis-tilfa-max-srv6-sids {
               type int32;
               description
                 "Max SRV6 SIDs";
             }
             leaf isis-tilfa-max-spf {
               type int32;
               description
                 "Max spf";
             }
             leaf isis-tilfa-ecmp-backup {
               type int32;
               description
                 "Post Convergence Max Ecmp Backup";
             }
           }
           container isis-spring {
             description
               "IS-IS SPRING parameters";
             leaf isis-spring-enabled {
               type string;
               description
                 "Source Packet Routing";
             }
             leaf isis-srgb-allocation {
               type string;
               description
                 "SRGB Block Allocation";
             }
             leaf isis-node-segment-enabled {
               type string;
               description
                 "Node Segments Enabled";
             }
             leaf isis-srv6-enabled {
               type string;
               description
                 "SRv6 Enabled";
             }
             container isis-srgb-config {
               description
                 "SRGB block configuration related information";
               leaf isis-srgb-config-block-header {
                 type string;
                 description
                   "SRGB Config Block";
               }
               leaf isis-srgb-start-label {
                 type int32;
                 description
                   "Configuration of SRGB start label";
               }
               leaf isis-srgb-index-range {
                 type int32;
                 description
                   "Configuration of SRGB index range";
               }
             }
             container isis-srgb-block {
               description
                 "SRGB block related information";
               leaf isis-srgb-start-index {
                 type int32;
                 description
                   "Starting Index for SRGB Block";
               }
               leaf isis-srgb-size {
                 type int32;
                 description
                   "Size of the specific SRGB Block";
               }
               leaf isis-srgb-first-label {
                 type int32;
                 description
                   "First label allocated for SRGB Block";
               }
               leaf isis-srgb-last-label {
                 type int32;
                 description
                   "Last label allocated for SRGB Block";
               }
             }
             container isis-node-segment {
               leaf isis-node-segment-ipv4-index {
                 type int32;
                 description
                   "IPv4 Node Segment index for this device";
               }
               leaf isis-node-segment-ipv6-index {
                 type int32;
                 description
                   "IPv6 Node Segment index for this device";
               }
               leaf isis-node-segment-index-range {
                 type int32;
                 description
                   "Range of Node Segment indices configured";
               }
               leaf isis-node-segment-block-header {
                 type empty;
                 description
                   "Node Segment Blocks";
               }
               list isis-node-segment-block {
                 key "isis-node-segment-block-start-index";
                 description
                   "Node Segment Blocks related information";
                 leaf isis-node-segment-block-start-index {
                   type int32;
                   description
                     "Starting Index for the specific Node Segment Block";
                 }
                 leaf isis-node-segment-block-size {
                   type int32;
                   description
                     "Size of the specific Node Segment Block";
                 }
                 leaf isis-node-segment-block-first-label {
                   type int32;
                   description
                     "First label allocated for the specific Node Segment 
                     Block";
                 }
                 leaf isis-node-segment-block-last-label {
                   type int32;
                   description
                     "Last label allocated for the specific Node Segment 
                     Block";
                 }
               }
             }
             list isis-srv6-locator {
               key "isis-srv6-locator-address";
               description
                 "SRv6 Locator information";
               leaf isis-srv6-locator-name {
                 type string;
                 description
                   "Locator name";
               }
               leaf isis-srv6-locator-address {
                 type string;
                 description
                   "Locator prefix";
               }
               leaf isis-srv6-locator-algorithm {
                 type uint32;
                 description
                   "Locator algorithm";
               }
               leaf isis-prefix-attribute-flags {
                 type string;
               }
               container isis-srv6-end-sid {
                 description
                   "SRv6 end sid entry";
                 leaf isis-srv6-end-sid-addr {
                   type jt:ipv6addr;
                   description
                     "SRv6 End-SID prefix";
                 }
                 leaf-list isis-srv6-sid-flavor {
                   type string;
                 }
               }
               container isis-srv6-micro-node-sid {
                 description
                   "SRv6 end sid entry";
                 leaf isis-srv6-micro-node-sid-addr {
                   type jt:ipv6addr;
                   description
                     "SRv6 micro-node-SID address";
                 }
                 leaf-list isis-srv6-micro-sid-flavor {
                   type string;
                 }
               }
             }
           }
           list isis-level-information {
             key "isis-level";
             description
               "IS-IS Level Information";
             leaf isis-level {
               type int32;
               description
                 "IS-IS Level";
             }
             leaf isis-preference {
               type uint32;
               description
                 "IS-IS internal route preference";
             }
             leaf isis-external-preference {
               type uint32;
               description
                 "IS-IS external route preference";
             }
             leaf isis-prefix-export-limit {
               type uint32;
               description
                 "IS-IS limit for external route export";
             }
             leaf isis-prefix-export-count {
               type uint32;
               description
                 "Actual number of exported prefixes";
             }
             leaf isis-wide-metrics {
               type empty;
               description
                 "Generation of wide metric TLVs is enabled";
             }
             leaf isis-narrow-metrics {
               type empty;
               description
                 "Generation of narrow metric TLVs is enabled";
             }
             leaf isis-level-spring-enabled {
               type empty;
               description
                 "Source Packet Routing is enabled";
             }
             leaf isis-adjacency-holddown-state {
               type string;
             }
             leaf isis-flood-reduction-enabled {
               type string;
               description
                 "Distributed Optimized flood reduction";
             }
             leaf isis-flood-reduction-hash-reflooder-enabled {
               type string;
               description
                 "Distributed Optimized flood reduction hash reflooder";
             }
             leaf isis-clos-miswiring-warning {
               type string;
             }
             leaf isis-purge-originator-info {
               type string;
               description
                 "Type of POI that gets added to purged LSPs";
             }
           }
         }
       }
       container task-replication-state {
         description
           "Current state of task replication";
         leaf task-gres-state {
           type string;
           description
             "Current state of graceful Routing Engine Switchover";
         }
         leaf task-re-mode {
           type string;
           description
             "Current mastership state of Routing Engine";
         }
         list task-protocol-replication {
           description
             "Current state of task protocol replication";
           leaf task-protocol-replication-name {
             type string;
           }
           leaf task-protocol-replication-state {
             type string;
           }
         }
       }
     }
   }
   grouping isis-overview-information-block {
     container isis-overview {
       description
         "Overview information for an IS-IS instance";
       leaf instance-name {
         type string;
       }
       leaf isis-instance-id {
         type uint16;
         description
           "IS-IS Instance ID";
       }
       leaf isis-router-id {
         type jt:ipaddr;
         description
           "IS-IS router ID";
       }
       leaf isis-v6-router-id {
         type jt:ipv6addr;
         description
           "IS-IS IPv6 Router ID";
       }
       leaf isis-router-hostname {
         type string;
         description
           "IS-IS router hostname";
       }
       leaf isis-router-sysid {
         type string;
         description
           "IS-IS router sysid";
       }
       leaf isis-router-areaid {
         type string;
         description
           "IS-IS router areaid";
       }
       leaf isis-max-areas {
         type uint32;
         description
           "Maximum Number of Areas";
       }
       leaf isis-lsp-lifetime {
         type uint32;
         description
           "Maximum LSP lifetime";
       }
       leaf isis-lsp-lifetime-filter {
         type uint32;
         description
           "Low LSP life time filter";
       }
       leaf isis-reference-bandwidth {
         type uint64;
         description
           "Bandwidth for calculating metric defaults";
       }
       leaf isis-adjacency-holddown {
         type string;
         description
           "IS-IS Adjacency holddown status";
       }
       leaf isis-attached-bit-evaluation {
         type string;
         description
           "The IS-IS L1 attached bit evaluation";
       }
       leaf isis-layer2-map-enabled {
         type string;
         description
           "IS-IS controls kernel ARP/ND entries for its nexthops";
       }
       container isis-spf-information {
         description
           "SPF options";
         leaf isis-spf-delay {
           type string;
           description
             "Delay before performing SPF calculations";
         }
         leaf isis-spf-holddown {
           type string;
           description
             "Throttling delay between consecutive SPF calculations";
         }
         leaf isis-spf-rapid-runs {
           type uint32;
           description
             "Number of rapid SPF calculations before SPF holddown.";
         }
         leaf isis-uloop-avoidance {
           type string;
           description
             "Micro-loop avoidance status";
         }
         leaf isis-uloop-avoidance-method {
           type string;
           description
             "Micro-loop avoidance mechanism employed";
         }
         leaf isis-route-convergence-delay {
           type string;
           description
             "Delay before downloading routes to forwarding plane";
         }
         leaf isis-topo-sessid-count {
           type uint32;
           description
             "Number of Session IDs associated with routes in this topology";
         }
         container isis-spf {
           leaf node-count {
             type int32;
           }
           container isis-spf-results-header {
             leaf isis-topology-id {
               type string;
             }
             leaf level {
               type int32;
               description
                 "IS-IS Level";
             }
           }
           list isis-spf-result {
             leaf node-id {
               type string;
             }
             leaf metric {
               type int32;
             }
             leaf disconnected {
               type empty;
             }
             leaf no-first-fragment {
               type empty;
             }
             leaf-list node-address {
               type string;
             }
             list next-hop-element {
               leaf interface-name {
                 type string;
                 description
                   "Name of interface";
               }
               leaf isis-next-hop-type {
                 type string;
               }
               leaf isis-next-hop {
                 type string;
               }
               leaf-list snpa {
                 type string;
               }
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
             }
             list prefix-element {
               leaf prefix-metric {
                 type int32;
               }
               leaf external-prefix-metric {
                 type int32;
               }
               leaf address-prefix {
                 type jt:ipaddr;
               }
             }
             list end-system-element {
               leaf end-system-metric {
                 type int32;
               }
               leaf end-system-id {
                 type string;
                 description
                   "Six-octet ISO system ID for a end-system";
               }
             }
           }
           container isis-spf-log-header {
             leaf isis-topology-id {
               type string;
             }
             leaf level {
               type int32;
               description
                 "IS-IS Level";
             }
           }
           container isis-spf-log {
             leaf start-time {
               type string;
             }
             leaf elapsed-time {
               type string;
               description
                 "Time this adjacency or session has been up or down";
             }
             leaf spf-trigger-count {
               type int32;
             }
             leaf logging-reason {
               type string;
             }
             leaf lsp-name {
               type string;
               description
                 "Tunneled into an RSVP LSP";
             }
             leaf system-name {
               type string;
               description
                 "Hostname for a system";
             }
             leaf interface-name {
               type string;
               description
                 "Name of interface";
             }
             leaf change-reason {
               type string;
             }
             leaf mla-topo-change-time {
               type string;
             }
             leaf mla-prefix-change-time {
               type string;
             }
             leaf tilfa-topo-change-time {
               type string;
             }
             leaf tilfa-prefix-change-time {
               type string;
             }
             leaf-list route-build-time {
               type string;
             }
           }
           container isis-backup-spf-result {
             leaf node-id {
               type string;
             }
             leaf no-first-fragment {
               type empty;
             }
             leaf backup-root {
               type string;
             }
             leaf backup-root-metric {
               type int32;
             }
             leaf metric {
               type int32;
             }
             leaf backup-root-preference {
               type int32;
             }
             leaf track-item {
               type string;
             }
             leaf track-item-isnbr {
               type string;
             }
             leaf rev-track-item {
               type string;
             }
             leaf rev-track-item-isnbr {
               type string;
             }
             leaf-list node-address {
               type string;
             }
             list next-hop-element {
               leaf interface-name {
                 type string;
                 description
                   "Name of interface";
               }
               leaf isis-next-hop-type {
                 type string;
               }
               leaf isis-next-hop {
                 type string;
               }
               leaf-list snpa {
                 type string;
               }
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
             }
             list backup-next-hop-element {
               leaf interface-name {
                 type string;
                 description
                   "Name of interface";
               }
               leaf isis-next-hop-type {
                 type string;
               }
               leaf isis-next-hop {
                 type string;
               }
               leaf-list snpa {
                 type string;
               }
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
               leaf isis-backup-prefix-refcount {
                 type uint32;
                 description
                   "Number of prefixes that uses this nexthop as backup";
               }
               leaf isis-backup-score {
                 type string;
               }
             }
             list no-coverage-reason-element {
               leaf isis-next-hop-type {
                 type string;
               }
               leaf no-coverage-reason {
                 type string;
               }
             }
           }
         }
       }
       container isis-overload-information {
         description
           "Overload bit behaviour at startup";
         leaf isis-overload-enabled {
           type empty;
           description
             "Overload bit upon startup is set";
         }
         leaf isis-overload-high-metrics {
           type string;
           description
             "High metrics are used for Overload signaling";
         }
         leaf isis-overload-allow-route-leaking {
           type string;
           description
             "Allow route leaking when configured to be in overload";
         }
         leaf isis-overload-internal-prefixes {
           type string;
           description
             "Allow internal prefixes to be advertised with high metric";
         }
         leaf isis-overload-external-prefixes {
           type string;
           description
             "Allow external prefixes to be advertised with high metric";
         }
         leaf isis-overload-timeout {
           type int32;
           description
             "Clearance of the Overload bit after startup";
         }
         leaf isis-overload-remaining-time {
           type string;
           description
             "Time remaining on configured overload timeout";
         }
       }
       container isis-routing {
         description
           "List of routed IS-IS address families";
         leaf isis-routing-ipv4 {
           type empty;
           description
             "Routing IPv4 prefixes is enabled";
         }
         leaf isis-routing-ipv6 {
           type empty;
           description
             "Routing IPv6 prefixes is enabled";
         }
         leaf isis-routing-clns {
           type empty;
           description
             "Routing CLNS prefixes is enabled";
         }
         leaf isis-routing-spring-mpls {
           type empty;
           description
             "Routing CLNS prefixes is enabled";
         }
       }
       container isis-traffic-engineering {
         description
           "Traffic engineering";
         leaf isis-te-status {
           type string;
           description
             "Traffic engineering status";
         }
         leaf isis-ted-ipv6 {
           type string;
           description
             "Traffic Engineering v6 status";
         }
         leaf isis-te-shortcuts-ipv4 {
           type empty;
           description
             "IPv4 Traffic engineering shortcuts are enabled";
         }
         leaf isis-te-shortcuts-ipv6 {
           type empty;
           description
             "IPv6 Traffic engineering shortcuts are enabled";
         }
         leaf isis-te-shortcuts-ipv4-mpls {
           type empty;
           description
             "IPv4-MPLS Traffic engineering shortcuts are enabled";
         }
         leaf isis-te-shortcuts-ipv6-mpls {
           type empty;
           description
             "IPv6-MPLS Traffic engineering shortcuts are enabled";
         }
         leaf isis-te-shortcuts-clns {
           type empty;
           description
             "CLNS Traffic engineering shortcuts are enabled";
         }
         leaf isis-ipv4-multicast-rpf-routes {
           type empty;
           description
             "IPv4 routes for multicast RPF checks are installed into inet.2";
         }
         leaf isis-ignore-lsp-metrics {
           type empty;
           description
             "Label-switched path metrics when doing shortcuts are ignored";
         }
         leaf isis-ted-credibility-preference {
           type empty;
           description
             "Credibility follows protocol preference";
         }
       }
       container isis-restart {
         description
           "IS-IS restart parameters";
         leaf isis-restart-enabled {
           type string;
           description
             "IS-IS restart mode";
         }
         leaf isis-restart-duration {
           type uint32;
           description
             "Duration of IS-IS restart";
         }
         leaf isis-restart-helper-mode-enabled {
           type string;
           description
             "IS-IS helper mode";
         }
       }
       container isis-tilfa {
         description
           "IS-IS Post Convergence Backup parameters";
         leaf isis-tilfa-enabled {
           type string;
           description
             "Post Convergence Backup";
         }
         leaf isis-tilfa-max-labels {
           type int32;
           description
             "Max labels";
         }
         leaf isis-tilfa-max-srv6-sids {
           type int32;
           description
             "Max SRV6 SIDs";
         }
         leaf isis-tilfa-max-spf {
           type int32;
           description
             "Max spf";
         }
         leaf isis-tilfa-ecmp-backup {
           type int32;
           description
             "Post Convergence Max Ecmp Backup";
         }
       }
       container isis-spring {
         description
           "IS-IS SPRING parameters";
         leaf isis-spring-enabled {
           type string;
           description
             "Source Packet Routing";
         }
         leaf isis-srgb-allocation {
           type string;
           description
             "SRGB Block Allocation";
         }
         leaf isis-node-segment-enabled {
           type string;
           description
             "Node Segments Enabled";
         }
         leaf isis-srv6-enabled {
           type string;
           description
             "SRv6 Enabled";
         }
         container isis-srgb-config {
           description
             "SRGB block configuration related information";
           leaf isis-srgb-config-block-header {
             type string;
             description
               "SRGB Config Block";
           }
           leaf isis-srgb-start-label {
             type int32;
             description
               "Configuration of SRGB start label";
           }
           leaf isis-srgb-index-range {
             type int32;
             description
               "Configuration of SRGB index range";
           }
         }
         container isis-srgb-block {
           description
             "SRGB block related information";
           leaf isis-srgb-start-index {
             type int32;
             description
               "Starting Index for SRGB Block";
           }
           leaf isis-srgb-size {
             type int32;
             description
               "Size of the specific SRGB Block";
           }
           leaf isis-srgb-first-label {
             type int32;
             description
               "First label allocated for SRGB Block";
           }
           leaf isis-srgb-last-label {
             type int32;
             description
               "Last label allocated for SRGB Block";
           }
         }
         container isis-node-segment {
           leaf isis-node-segment-ipv4-index {
             type int32;
             description
               "IPv4 Node Segment index for this device";
           }
           leaf isis-node-segment-ipv6-index {
             type int32;
             description
               "IPv6 Node Segment index for this device";
           }
           leaf isis-node-segment-index-range {
             type int32;
             description
               "Range of Node Segment indices configured";
           }
           leaf isis-node-segment-block-header {
             type empty;
             description
               "Node Segment Blocks";
           }
           list isis-node-segment-block {
             key "isis-node-segment-block-start-index";
             description
               "Node Segment Blocks related information";
             leaf isis-node-segment-block-start-index {
               type int32;
               description
                 "Starting Index for the specific Node Segment Block";
             }
             leaf isis-node-segment-block-size {
               type int32;
               description
                 "Size of the specific Node Segment Block";
             }
             leaf isis-node-segment-block-first-label {
               type int32;
               description
                 "First label allocated for the specific Node Segment Block";
             }
             leaf isis-node-segment-block-last-label {
               type int32;
               description
                 "Last label allocated for the specific Node Segment Block";
             }
           }
         }
         list isis-srv6-locator {
           key "isis-srv6-locator-address";
           description
             "SRv6 Locator information";
           leaf isis-srv6-locator-name {
             type string;
             description
               "Locator name";
           }
           leaf isis-srv6-locator-address {
             type string;
             description
               "Locator prefix";
           }
           leaf isis-srv6-locator-algorithm {
             type uint32;
             description
               "Locator algorithm";
           }
           leaf isis-prefix-attribute-flags {
             type string;
           }
           container isis-srv6-end-sid {
             description
               "SRv6 end sid entry";
             leaf isis-srv6-end-sid-addr {
               type jt:ipv6addr;
               description
                 "SRv6 End-SID prefix";
             }
             leaf-list isis-srv6-sid-flavor {
               type string;
             }
           }
           container isis-srv6-micro-node-sid {
             description
               "SRv6 end sid entry";
             leaf isis-srv6-micro-node-sid-addr {
               type jt:ipv6addr;
               description
                 "SRv6 micro-node-SID address";
             }
             leaf-list isis-srv6-micro-sid-flavor {
               type string;
             }
           }
         }
       }
       list isis-level-information {
         key "isis-level";
         description
           "IS-IS Level Information";
         leaf isis-level {
           type int32;
           description
             "IS-IS Level";
         }
         leaf isis-preference {
           type uint32;
           description
             "IS-IS internal route preference";
         }
         leaf isis-external-preference {
           type uint32;
           description
             "IS-IS external route preference";
         }
         leaf isis-prefix-export-limit {
           type uint32;
           description
             "IS-IS limit for external route export";
         }
         leaf isis-prefix-export-count {
           type uint32;
           description
             "Actual number of exported prefixes";
         }
         leaf isis-wide-metrics {
           type empty;
           description
             "Generation of wide metric TLVs is enabled";
         }
         leaf isis-narrow-metrics {
           type empty;
           description
             "Generation of narrow metric TLVs is enabled";
         }
         leaf isis-level-spring-enabled {
           type empty;
           description
             "Source Packet Routing is enabled";
         }
         leaf isis-adjacency-holddown-state {
           type string;
         }
         leaf isis-flood-reduction-enabled {
           type string;
           description
             "Distributed Optimized flood reduction";
         }
         leaf isis-flood-reduction-hash-reflooder-enabled {
           type string;
           description
             "Distributed Optimized flood reduction hash reflooder";
         }
         leaf isis-clos-miswiring-warning {
           type string;
         }
         leaf isis-purge-originator-info {
           type string;
           description
             "Type of POI that gets added to purged LSPs";
         }
       }
     }
   }
   grouping isis-route-information-block {
     container isis-routing-table {
       leaf isis-topology-id {
         type string;
       }
       leaf level-one-version {
         type int32;
       }
       leaf level-two-version {
         type int32;
       }
       container isis-route {
         leaf address-prefix {
           type jt:ipaddr;
         }
         leaf level {
           type int32;
           description
             "IS-IS Level";
         }
         leaf route-version {
           type int32;
         }
         leaf metric {
           type int32;
         }
         leaf metric-type {
           type string;
         }
         leaf interface-name {
           type string;
           description
             "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf prefix-downbit {
           type int32;
         }
         leaf isis-route-priority {
           type string;
         }
         leaf isis-rt-congestion-protection-activate {
           type string;
         }
         leaf isis-rt-congestion-protection-activate-count {
           type uint32;
         }
         list isis-backup-next-hop-sid-info {
           leaf isis-backup-next-hop-label {
             type uint32;
           }
           leaf isis-backup-next-hop-label-type {
             type string;
           }
           leaf isis-backup-next-hop-srv6-sid {
             type jt:ipaddr;
           }
           leaf isis-backup-next-hop-srv6-sid-type {
             type string;
           }
           leaf isis-backup-next-hop-sid-info-node-id {
             type string;
           }
           leaf isis-backup-next-hop-sid-info-adj-local-node-id {
             type string;
           }
           leaf isis-backup-next-hop-sid-info-adj-remote-node-id {
             type string;
           }
           leaf isis-backup-next-hop-sid-info-adj-local-v4-addr {
             type jt:ipaddr;
           }
           leaf isis-backup-next-hop-sid-info-adj-remote-v4-addr {
             type jt:ipaddr;
           }
           leaf isis-backup-next-hop-sid-info-adj-local-v6-addr {
             type jt:ipaddr;
           }
           leaf isis-backup-next-hop-sid-info-adj-remote-v6-addr {
             type jt:ipaddr;
           }
           leaf isis-backup-next-hop-sid-info-adj-local-unnumbered-id {
             type uint32;
           }
           leaf isis-backup-next-hop-sid-info-adj-remote-unnumbered-id {
             type uint32;
           }
         }
         list snpa {
           key "snpa-type";
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
         }
         list isis-rt-sessid {
           description
             "Session ID associated with the route";
           leaf-list isis-rt-sessid-val {
             type uint32;
           }
           leaf-list isis-rt-sessid-ver {
             type uint32;
           }
         }
         container isis-computed-backup-paths {
           leaf isis-computed-backup-paths-type {
             type string;
           }
           leaf isis-computed-backup-paths-count {
             type uint32;
           }
           leaf isis-computed-backup-paths-valid-count {
             type uint32;
           }
           leaf isis-computed-backup-paths-rttype {
             type string;
           }
           list isis-computed-backup-path {
             leaf isis-computed-backup-path-id {
               type uint32;
             }
             leaf isis-computed-backup-path-sid-count {
               type uint32;
             }
             leaf isis-computed-backup-path-error {
               type string;
             }
           }
         }
         leaf igp-metric {
           type uint32;
         }
       }
     }
   }
   grouping isis-upa-information-block {
     list isis-upa-instance-information {
       key "level";
       leaf isis-instance-name {
         type string;
         description
           "Name of ISIS instance";
       }
       leaf isis-routing-instance-name {
         type string;
         description
           "Name of Routing instance";
       }
       leaf level {
         type int32;
         description
           "IS-IS Level";
       }
       list isis-upa-log {
         key "address-prefix";
         leaf upa-time {
           type string;
         }
         leaf address-prefix {
           type jt:ipaddr;
         }
         leaf upa-event {
           type string;
         }
         leaf upa-reason {
           type string;
         }
         leaf lsp-name {
           type string;
           description
             "Tunneled into an RSVP LSP";
         }
       }
     }
   }
   grouping isis-purge-information-block {
     container isis-purge {
       container isis-purge-log-header {
         leaf level {
           type int32;
           description
             "IS-IS Level";
         }
       }
       container isis-purge-log {
         leaf start-time {
           type string;
         }
         leaf lsp-name {
           type string;
           description
             "Tunneled into an RSVP LSP";
         }
         leaf osystem-name {
           type string;
           description
             "Hostname for a system";
         }
         leaf rsystem-name {
           type string;
           description
             "Hostname for a system";
         }
         leaf purge-trigger-count {
           type int32;
         }
       }
     }
   }
   grouping isis-spf-information-block {
     leaf isis-topo-sessid-count {
       type uint32;
       description
         "Number of Session IDs associated with routes in this topology";
     }
     container isis-spf {
       leaf node-count {
         type int32;
       }
       container isis-spf-results-header {
         leaf isis-topology-id {
           type string;
         }
         leaf level {
           type int32;
           description
             "IS-IS Level";
         }
       }
       list isis-spf-result {
         leaf node-id {
           type string;
         }
         leaf metric {
           type int32;
         }
         leaf disconnected {
           type empty;
         }
         leaf no-first-fragment {
           type empty;
         }
         leaf-list node-address {
           type string;
         }
         list next-hop-element {
           leaf interface-name {
             type string;
             description
               "Name of interface";
           }
           leaf isis-next-hop-type {
             type string;
           }
           leaf isis-next-hop {
             type string;
           }
           leaf-list snpa {
             type string;
           }
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
         }
         list prefix-element {
           leaf prefix-metric {
             type int32;
           }
           leaf external-prefix-metric {
             type int32;
           }
           leaf address-prefix {
             type jt:ipaddr;
           }
         }
         list end-system-element {
           leaf end-system-metric {
             type int32;
           }
           leaf end-system-id {
             type string;
             description
               "Six-octet ISO system ID for a end-system";
           }
         }
       }
       container isis-spf-log-header {
         leaf isis-topology-id {
           type string;
         }
         leaf level {
           type int32;
           description
             "IS-IS Level";
         }
       }
       container isis-spf-log {
         leaf start-time {
           type string;
         }
         leaf elapsed-time {
           type string;
           description
             "Time this adjacency or session has been up or down";
         }
         leaf spf-trigger-count {
           type int32;
         }
         leaf logging-reason {
           type string;
         }
         leaf lsp-name {
           type string;
           description
             "Tunneled into an RSVP LSP";
         }
         leaf system-name {
           type string;
           description
             "Hostname for a system";
         }
         leaf interface-name {
           type string;
           description
             "Name of interface";
         }
         leaf change-reason {
           type string;
         }
         leaf mla-topo-change-time {
           type string;
         }
         leaf mla-prefix-change-time {
           type string;
         }
         leaf tilfa-topo-change-time {
           type string;
         }
         leaf tilfa-prefix-change-time {
           type string;
         }
         leaf-list route-build-time {
           type string;
         }
       }
       container isis-backup-spf-result {
         leaf node-id {
           type string;
         }
         leaf no-first-fragment {
           type empty;
         }
         leaf backup-root {
           type string;
         }
         leaf backup-root-metric {
           type int32;
         }
         leaf metric {
           type int32;
         }
         leaf backup-root-preference {
           type int32;
         }
         leaf track-item {
           type string;
         }
         leaf track-item-isnbr {
           type string;
         }
         leaf rev-track-item {
           type string;
         }
         leaf rev-track-item-isnbr {
           type string;
         }
         leaf-list node-address {
           type string;
         }
         list next-hop-element {
           leaf interface-name {
             type string;
             description
               "Name of interface";
           }
           leaf isis-next-hop-type {
             type string;
           }
           leaf isis-next-hop {
             type string;
           }
           leaf-list snpa {
             type string;
           }
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
         }
         list backup-next-hop-element {
           leaf interface-name {
             type string;
             description
               "Name of interface";
           }
           leaf isis-next-hop-type {
             type string;
           }
           leaf isis-next-hop {
             type string;
           }
           leaf-list snpa {
             type string;
           }
           leaf snpa-type {
             type string;
             description
               "Type of SNPA";
           }
           list pfe-port-snpa {
             key "pfe-id";
             description
               "PFE Port SNPA";
             leaf pfe-id {
               type int32;
             }
             leaf port-id {
               type int32;
             }
           }
           container network-element-port-snpa {
             description
               "Network Element Port SNPA";
             leaf port-id {
               type int32;
             }
           }
           container mstp-root-snpa {
             description
               "Multiple Spanning Tree Protocol Root SNPA";
             leaf mstp-root-id {
               type int32;
             }
           }
           list gateway-snpa {
             key "gateway-addr";
             description
               "Gateway SNPA";
             leaf gateway-addr {
               type jt:ipaddr;
             }
           }
           container layer2-domain-port-snpa {
             description
               "Layer-2 Domain Port SNPA";
             leaf port-id {
               type int32;
             }
           }
           container replication-block-snpa {
             description
               "Replication Block SNPA";
             leaf replication-block-id {
               type int32;
             }
           }
           container replication-route-snpa {
             description
               "Replication Route SNPA";
             leaf network-element-id {
               type jt:ipaddr;
             }
           }
           container layer2-multicast-port-snpa {
             description
               "Layer-2 Multicast Port SNPA";
             leaf layer2-multicast-port-id {
               type int32;
             }
           }
           container inh-snpa {
             description
               "Indirection SNPA";
             leaf inh-id {
               type int32;
             }
           }
           leaf isis-backup-prefix-refcount {
             type uint32;
             description
               "Number of prefixes that uses this nexthop as backup";
           }
           leaf isis-backup-score {
             type string;
           }
         }
         list no-coverage-reason-element {
           leaf isis-next-hop-type {
             type string;
           }
           leaf no-coverage-reason {
             type string;
           }
         }
       }
     }
   }
   grouping isis-statistics-information-block {
     container isis-statistics {
       leaf system-name {
         type string;
         description
           "Hostname for a system";
       }
       leaf snp-queue-length {
         type int32;
       }
       leaf snp-queue-drops {
         type int32;
       }
       leaf lsp-queue-length {
         type int32;
       }
       leaf lsp-queue-drops {
         type int32;
       }
       leaf spf-runs {
         type int32;
       }
       leaf flex-full-spf-runs {
         type int32;
       }
       leaf flex-prc-spf-runs {
         type int32;
       }
       leaf fragments-rebuilt {
         type int32;
       }
       leaf lsps-regenerated {
         type int32;
       }
       leaf purges-initiated {
         type int32;
       }
       leaf purges-received {
         type int32;
       }
       leaf duplicate-lsps {
         type int32;
       }
       list isis-pdu-statistics {
         key "isis-pdu-type";
         leaf isis-pdu-type {
           type string;
         }
         leaf packets-received {
           type uint64;
         }
         leaf packets-processed {
           type uint64;
         }
         leaf packets-dropped {
           type uint64;
         }
         leaf packets-sent {
           type uint64;
         }
         leaf packets-retransmitted {
           type uint64;
         }
       }
       container isis-flooding-statistics {
         leaf instance-name {
           type string;
         }
         leaf flood-reduction-cache-hits {
           type int32;
         }
         leaf flood-reduction-cache-misses {
           type int32;
         }
         leaf-list flood-reduction-l1-database-checksum {
           type int32;
         }
         leaf-list flood-reduction-l1-database-checksum-last-changed {
           type string;
         }
         leaf-list flood-reduction-l2-database-checksum {
           type int32;
         }
         leaf-list flood-reduction-l2-database-checksum-last-changed {
           type string;
         }
         leaf flood-reduction-cache-effective {
           type int32;
         }
         leaf flood-reduction-reduction-rate {
           type int32;
         }
         container isis-flooding-statistics-lsps {
           list isis-flooding-statistics-lsp {
             key "lsp-id";
             leaf lsp-id {
               type string;
             }
             leaf level {
               type int32;
               description
                 "IS-IS Level";
             }
             leaf lsp-flooded-hi {
               type uint64;
             }
             leaf lsp-flooded-lo {
               type uint64;
             }
             leaf lsp-suppressed {
               type uint64;
             }
           }
         }
       }
       container totals-information {
         leaf packets-received {
           type uint64;
         }
         leaf packets-sent {
           type uint64;
         }
       }
     }
   }
   grouping isis-interface-statistics-information-block {
     list isis-interface-statistics {
       leaf system-name {
         type string;
         description
           "Hostname for a system";
       }
       leaf isis-duplicate-lsp-on-intf {
         type uint64;
       }
       container isis-interface-statistics-intf {
         leaf isis-interface-name {
           type string;
         }
       }
       container isis-interface-statistics-table {
         list isis-pdu-statistics {
           key "isis-pdu-type";
           leaf isis-pdu-type {
             type string;
           }
           leaf packets-received {
             type uint64;
           }
           leaf packets-processed {
             type uint64;
           }
           leaf packets-dropped {
             type uint64;
           }
           leaf packets-sent {
             type uint64;
           }
           leaf packets-retransmitted {
             type uint64;
           }
         }
       }
       container totals-information {
         leaf packets-received {
           type uint64;
         }
         leaf packets-sent {
           type uint64;
         }
       }
       container isis-interface-statistics-lsp-queue {
         leaf lsp-queue-name {
           type string;
         }
         leaf lsp-queue-entry-count {
           type int32;
         }
         leaf lsp-queue-entry-highwater-mark-count {
           type int32;
         }
         list isis-interface-statistics-lsp-queue-entry {
           leaf lsp-id {
             type string;
           }
           leaf lsp-queue-time {
             type string;
           }
           leaf lsp-queue-expiration-time {
             type string;
           }
         }
       }
       list isis-duplicate-lsp-information {
         key "lsp-id";
         leaf lsp-id {
           type string;
         }
         leaf duplicate-lsp {
           type uint64;
         }
       }
     }
   }
   grouping isis-interface-traffic-statistics-information-block {
     list isis-interface-traffic-statistics {
       key "interface-name";
       description
         "ISIS SPRING aggregate traffic statistics on interface";
       leaf interface-name {
         type string;
         description
           "Name of interface";
       }
       leaf isis-output-bytes {
         type int32;
       }
       leaf isis-output-packets {
         type int32;
       }
     }
   }
   grouping isis-spring-flex-algorithm-information-block {
     list isis-spring-flex-algorithm {
       leaf flex-algorithm-id {
         type uint32;
         description
           "SRV6 locator flex algorithm";
       }
       leaf level {
         type int32;
         description
           "IS-IS Level";
       }
       leaf flex-algorithm-color {
         type uint32;
       }
       leaf flex-algorithm-participation {
         type string;
       }
       leaf participation-reason {
         type string;
       }
       leaf flex-algorithm-stat {
         type uint32;
       }
       leaf isis-topology-id {
         type string;
       }
       leaf flex-full-spf-runs {
         type int32;
       }
       leaf flex-prc-spf-runs {
         type int32;
       }
       leaf flex-algorithm-topo-stat {
         type uint32;
       }
       container flex-algorithm-winner-fad {
         container flex-algorithm-sub-tlv {
           leaf system-name {
             type string;
             description
               "Hostname for a system";
           }
           leaf flex-algorithm-id {
             type uint32;
             description
               "SRV6 locator flex algorithm";
           }
           leaf flex-algorithm-subtlv-length {
             type uint32;
           }
           leaf flex-algorithm-metric-str {
             type string;
           }
           leaf flex-algorithm-calc-str {
             type string;
           }
           leaf flex-algorithm-metric-type {
             type uint32;
           }
           leaf flex-algorithm-calc-type {
             type uint32;
           }
           leaf flex-algorithm-priority {
             type uint32;
           }
           leaf flex-algorithm-flags {
             type string;
           }
           leaf flex-algorithm-include-any {
             type string;
           }
           leaf flex-algorithm-include-all {
             type string;
           }
           leaf flex-algorithm-exclude {
             type string;
           }
           leaf flex-algorithm-srlg-exclude {
             type string;
           }
           leaf participation-reason {
             type string;
           }
           leaf flex-algorithm-po-flags {
             type uint32;
           }
           leaf flex-algorithm-po-res {
             type uint32;
           }
           leaf flex-algorithm-po-offset {
             type uint32;
           }
           container flex-algorithm-include-any-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-include-all-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-exclude-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-srlg-exclude-detail {
             leaf flex-algorithm-srlg-exclude-detail.heading {
               type string;
             }
             leaf-list srlg-name {
               type string;
               description
                 "Name of the srlg";
             }
           }
         }
       }
       container flex-algorithm-loser-fad {
         container flex-algorithm-sub-tlv {
           leaf system-name {
             type string;
             description
               "Hostname for a system";
           }
           leaf flex-algorithm-id {
             type uint32;
             description
               "SRV6 locator flex algorithm";
           }
           leaf flex-algorithm-subtlv-length {
             type uint32;
           }
           leaf flex-algorithm-metric-str {
             type string;
           }
           leaf flex-algorithm-calc-str {
             type string;
           }
           leaf flex-algorithm-metric-type {
             type uint32;
           }
           leaf flex-algorithm-calc-type {
             type uint32;
           }
           leaf flex-algorithm-priority {
             type uint32;
           }
           leaf flex-algorithm-flags {
             type string;
           }
           leaf flex-algorithm-include-any {
             type string;
           }
           leaf flex-algorithm-include-all {
             type string;
           }
           leaf flex-algorithm-exclude {
             type string;
           }
           leaf flex-algorithm-srlg-exclude {
             type string;
           }
           leaf participation-reason {
             type string;
           }
           leaf flex-algorithm-po-flags {
             type uint32;
           }
           leaf flex-algorithm-po-res {
             type uint32;
           }
           leaf flex-algorithm-po-offset {
             type uint32;
           }
           container flex-algorithm-include-any-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-include-all-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-exclude-detail {
             container admin-groups {
               leaf color {
                 type int32;
               }
               leaf no-group-flag {
                 type empty;
               }
               leaf-list admin-group-name {
                 type string;
                 description
                   "Name of the admin group";
               }
               leaf admin-group-number {
                 type int32;
                 description
                   "Number of the admin group";
               }
             }
           }
           container flex-algorithm-srlg-exclude-detail {
             leaf flex-algorithm-srlg-exclude-detail.heading {
               type string;
             }
             leaf-list srlg-name {
               type string;
               description
                 "Name of the srlg";
             }
           }
         }
       }
       container isis-flex-algo-spf-log-header {
         leaf isis-topology-id {
           type string;
         }
         leaf sr-algorithm {
           type int32;
           description
             "SR Algorithm";
         }
         leaf level {
           type int32;
           description
             "IS-IS Level";
         }
       }
       container isis-spf-log {
         leaf start-time {
           type string;
         }
         leaf elapsed-time {
           type string;
           description
             "Time this adjacency or session has been up or down";
         }
         leaf spf-trigger-count {
           type int32;
         }
         leaf logging-reason {
           type string;
         }
         leaf lsp-name {
           type string;
           description
             "Tunneled into an RSVP LSP";
         }
         leaf system-name {
           type string;
           description
             "Hostname for a system";
         }
         leaf interface-name {
           type string;
           description
             "Name of interface";
         }
         leaf change-reason {
           type string;
         }
         leaf mla-topo-change-time {
           type string;
         }
         leaf mla-prefix-change-time {
           type string;
         }
         leaf tilfa-topo-change-time {
           type string;
         }
         leaf tilfa-prefix-change-time {
           type string;
         }
         leaf-list route-build-time {
           type string;
         }
       }
     }
   }
   grouping isis-spring-sensor-information-block {
     leaf isis-spring-sensor-information-attribute {
       type string;
     }
     container isis-sensor-ingress {
       description
         "ISIS SPRING ingress sensor information";
       list isis-sensor-ingress-entries {
         key "ingress-sensor-name";
         leaf ingress-sensor-name {
           type string;
         }
         leaf ingress-sensor-id {
           type int32;
         }
       }
     }
     container isis-sensor-egress {
       description
         "ISIS SPRING egress sensor information";
       list isis-sensor-egress-entries {
         key "egress-sensor-name";
         leaf egress-sensor-name {
           type string;
         }
         leaf egress-sensor-id {
           type int32;
         }
       }
     }
     container isis-sensor-per-sid {
       description
         "ISIS SPRING Per Sid ingress sensor information";
       list isis-sensor-per-sid-entries {
         key "per-sid-sensor-name";
         leaf per-sid-sensor-name {
           type string;
         }
         leaf per-sid-sensor-id {
           type int32;
         }
       }
     }
     container isis-sensor-ip-mpls {
       description
         "ISIS SPRING Per Sid egress sensor information";
       list isis-sensor-ip-mpls-entries {
         key "per-sid-sensor-name";
         leaf per-sid-sensor-name {
           type string;
         }
         leaf per-sid-sensor-id {
           type int32;
         }
       }
     }
   }
   grouping isis-srv6-sensor-information-block {
     leaf isis-srv6-sensor-information-attribute {
       type string;
     }
     leaf srv6-sensor-name {
       type string;
     }
     leaf srv6-sensor-id {
       type int32;
     }
     container isis-srv6-rmt-locs-sensor-ingress {
       description
         "ISIS SRv6 Remote locator ingress sensor information";
       list isis-srv6-rmt-loc-ingress-entries {
         key "srv6-sensor-name";
         leaf srv6-sensor-name {
           type string;
         }
         leaf srv6-sensor-id {
           type int32;
         }
       }
     }
     container isis-srv6-rmt-locs-sensor-egress {
       description
         "ISIS SRv6 Remote locator egress sensor information";
       list isis-srv6-rmt-loc-egress-entries {
         key "srv6-sensor-name";
         leaf srv6-sensor-name {
           type string;
         }
         leaf srv6-sensor-id {
           type int32;
         }
       }
     }
   }
   grouping isis-backup-coverage-information-block {
     list isis-backup-coverage {
       key "isis-topology-id level";
       leaf isis-topology-id {
         type string;
       }
       leaf level {
         type int32;
         description
           "IS-IS Level";
       }
       leaf isis-node-coverage {
         type string;
       }
       leaf isis-route-coverage-ipv4 {
         type string;
       }
       leaf isis-route-coverage-ipv4-mpls {
         type string;
       }
       leaf isis-route-coverage-ipv4-mpls-sspf {
         type string;
       }
       leaf isis-route-coverage-ipv6 {
         type string;
       }
       leaf isis-route-coverage-ipv6-mpls {
         type string;
       }
       leaf isis-route-coverage-ipv6-mpls-sspf {
         type string;
       }
       leaf isis-route-coverage-clns {
         type string;
       }
     }
   }
   grouping isis-backup-mplsp-information-block {
     list isis-backup-mplsp {
       key "lsp-name";
       leaf lsp-name {
         type string;
         description
           "Tunneled into an RSVP LSP";
       }
       leaf lsp-addr {
         type jt:ipaddr;
         description
           "LSP destination address";
       }
       leaf lsp-status {
         type string;
         description
           "LSP status";
       }
       leaf lsp-last-change {
         type string;
         description
           "Time of last LSP change";
       }
       leaf te-metric {
         type int32;
         description
           "LSP TE metric";
       }
       leaf metric {
         type int32;
       }
       leaf lsp-refcount {
         type int32;
       }
     }
   }
   grouping isis-context-information-block {
     list isis-context {
       leaf isis-context-id {
         type jt:ipaddr;
         description
           "Context identifier is an IP address identify protected context";
       }
       leaf isis-context-level {
         type int32;
         description
           "Advertise level";
       }
       leaf isis-context-owner-proto {
         type string;
         description
           "Routing protocols owns context identifier";
       }
       leaf isis-context-role {
         type string;
         description
           "Context role either primary or protector";
       }
       leaf isis-context-primary {
         type string;
         description
           "Context role is primary or protector";
       }
       leaf isis-context-metric {
         type uint32;
         description
           "Metric associate with context-id";
       }
       leaf isis-context-advertiser {
         type string;
         description
           "Context-id advertiser name";
       }
       leaf isis-context-advertiser-router-id {
         type jt:ipaddr;
         description
           "Router Ids of context-id advertiser";
       }
       leaf isis-context-advertiser-metric {
         type uint32;
         description
           "Context-id advertiser metric";
       }
       leaf isis-context-advertiser-level {
         type uint32;
         description
           "Context-id advertiser level";
       }
       leaf isis-not-compatible-mode {
         type empty;
       }
       leaf isis-context-advertiser-tlv {
         type string;
         description
           "Context-id advertiser tlv";
       }
     }
   }
 }
