/*
 * Copyright (c) 2026 Juniper Networks, Inc.
 * All rights reserved.
 */
 module junos-rpc-spring-traffic-engineering {
   namespace "http://yang.juniper.net/junos/rpc/spring-traffic-engineering";

   prefix spring-traffic-engineering;

   import junos-common-types {
     prefix jt;
     revision-date 2026-01-01;
   }

   organization "Juniper Networks, Inc.";

   contact "yang-support@juniper.net";

   description "Junos RPC YANG module for spring-traffic-engineering command(s)";

   revision 2026-01-01 {
     description "Junos: 26.2R1.7";
   }

   rpc get-spring-te-overview-information {
     description "Show overview of ingress SPRING Traffic Engineering";
     input {
       choice daemon-select {
         case logical-system {
           leaf logical-system {
             description "Name of logical system, or 'all'";
             type string {
             }
           }
         }
       }
     }
     output {
       choice output-tags {
         case actual-tag {
           container spring-te-overview-information {
             uses spring-te-overview-information-block;
           }
         }
         case multichassis-tag {
           container multi-routing-engine-results {
             list multi-routing-engine-item {
               leaf re-name {
                 type string;
               }
               choice output-tags {
                 case actual-tag {
                   container spring-te-overview-information {
                     uses spring-te-overview-information-block;
                   }
                 }
               }
             }
           }
         }
       }
     }
   }
   rpc get-spring-te-lsp-information {
     description "Show SPRING Traffic Engineered ingress LSPs";
     input {
       choice daemon-select {
         case logical-system {
           leaf logical-system {
             description "Name of logical system, or 'all'";
             type string {
             }
           }
         }
       }
       leaf regex {
         description "Regular expression for LSP names to match";
         type string;
       }
       leaf tunnel-source {
         description "Source of tunnel creation";
         type enumeration {
           enum "pcep" {
             description "Path computation element protocol";
           }
           enum "static" {
             description "Static configuration";
           }
           enum "dtm" {
             description "Dynamic tunnel module";
           }
           enum "bgp" {
             description "BGP SRTE";
           }
         }
       }
       leaf color {
         description "Tunnel color";
         type union {
           type string {
             pattern "<.*>|$.*";
           }
           type uint64 {
             range "0 .. 4294967296";
           }
         }
       }
       leaf destination {
         description "IPV4/IPV6 to-address of tunnel";
         type jt:ipaddr;
       }
       leaf verbosity_level {
         default "brief";
         type enumeration {
           enum "brief" {
             description "Display brief output (default)";
           }
           enum "detail" {
             description "Display detailed output";
           }
         }
       }
     }
     output {
       choice output-tags {
         case actual-tag {
           container spring-te-lsp-information {
             uses spring-te-lsp-information-block;
           }
         }
         case multichassis-tag {
           container multi-routing-engine-results {
             list multi-routing-engine-item {
               leaf re-name {
                 type string;
               }
               choice output-tags {
                 case actual-tag {
                   container spring-te-lsp-information {
                     uses spring-te-lsp-information-block;
                   }
                 }
               }
             }
           }
         }
       }
     }
   }
   rpc get-spring-te-bfd-session-information {
     description "Show SPRING Traffic Engineered BFD session";
     input {
       choice daemon-select {
         case logical-system {
           leaf logical-system {
             description "Name of logical system, or 'all'";
             type string {
             }
           }
         }
       }
       leaf regex {
         description "Regular expression for BFD session names to match";
         type string;
       }
       leaf verbosity_level {
         default "brief";
         type enumeration {
           enum "brief" {
             description "Display brief output (default)";
           }
           enum "detail" {
             description "Display detailed output";
           }
         }
       }
     }
     output {
       choice output-tags {
         case actual-tag {
           container spring-te-bfd-session-information {
             uses spring-te-bfd-session-information-block;
           }
         }
         case multichassis-tag {
           container multi-routing-engine-results {
             list multi-routing-engine-item {
               leaf re-name {
                 type string;
               }
               choice output-tags {
                 case actual-tag {
                   container spring-te-bfd-session-information {
                     uses spring-te-bfd-session-information-block;
                   }
                 }
               }
             }
           }
         }
       }
     }
   }
   rpc get-spring-te-route-information {
     description "Show spring traffic engineering route information";
     input {
       choice daemon-select {
         case logical-system {
           leaf logical-system {
             description "Name of logical system, or 'all'";
             type string {
             }
           }
         }
       }
       leaf tunnel-source {
         description "Source of tunnel creation";
         type enumeration {
           enum "pcep" {
             description "Path computation element protocol";
           }
           enum "static" {
             description "Static configuration";
           }
           enum "dtm" {
             description "Dynamic tunnel module";
           }
           enum "bgp" {
             description "BGP SRTE";
           }
         }
       }
       leaf destination {
         description "IPV4/IPV6 to-address of tunnel  and optional prefix length of destination";
         type jt:ipprefix-optional;
       }
       leaf match-prefix {
         description "Regular expression to match formatted prefix";
         type string;
       }
       leaf label {
         description "Label of entry in MPLS routing table";
         type union {
           type uint32;
           type string {
             pattern "<.*>|$.*";
           }
         }
       }
       leaf instance {
         description "Name of spring traffic engineering instance";
         type string;
       }
       leaf verbosity_level {
         default "brief";
         type enumeration {
           enum "brief" {
             description "Display brief output (default)";
           }
           enum "detail" {
             description "Display detailed output";
           }
           enum "extensive" {
             description "Display extensive output";
           }
         }
       }
     }
     output {
       choice output-tags {
         case actual-tag {
           container spring-te-route-information {
             uses spring-te-route-information-block;
           }
         }
         case multichassis-tag {
           container multi-routing-engine-results {
             list multi-routing-engine-item {
               leaf re-name {
                 type string;
               }
               choice output-tags {
                 case actual-tag {
                   container spring-te-route-information {
                     uses spring-te-route-information-block;
                   }
                 }
               }
             }
           }
         }
       }
     }
   }
   rpc get-spring-te-binding-sid-database-information {
     description "Show spring traffic engineered binding sid database";
     input {
       choice daemon-select {
         case logical-system {
           leaf logical-system {
             description "Name of logical system, or 'all'";
             type string {
             }
           }
         }
       }
       leaf label {
         description "Show this particular binding sid label information";
         type union {
           type string {
             pattern "<.*>|$.*";
           }
           type uint32 {
             range "1 .. 1048575";
           }
         }
       }
       leaf verbosity_level {
         default "brief";
         type enumeration {
           enum "brief" {
             description "Display brief output (default)";
           }
           enum "detail" {
             description "Display detailed output";
           }
         }
       }
     }
     output {
       choice output-tags {
         case actual-tag {
           container spring-te-binding-sid-database-information {
             uses spring-te-binding-sid-database-information-block;
           }
         }
         case multichassis-tag {
           container multi-routing-engine-results {
             list multi-routing-engine-item {
               leaf re-name {
                 type string;
               }
               choice output-tags {
                 case actual-tag {
                   container spring-te-binding-sid-database-information {
                     uses spring-te-binding-sid-database-information-block;
                   }
                 }
               }
             }
           }
         }
       }
     }
   }
   rpc get-spring-te-srv6-bsid-database-information {
     description "Show traffic engineered SRv6 Binding SID information";
     input {
       choice daemon-select {
         case logical-system {
           leaf logical-system {
             description "Name of logical system, or 'all'";
             type string {
             }
           }
         }
       }
       leaf sid {
         description "Show SRv6 Binding SID matching this prefix";
         type jt:ipv6prefix-optional;
       }
       leaf verbosity_level {
         default "brief";
         type enumeration {
           enum "brief" {
             description "Display brief output (default)";
           }
           enum "detail" {
             description "Display detailed output";
           }
         }
       }
     }
     output {
       choice output-tags {
         case actual-tag {
           container spring-te-srv6-bsid-database-information {
             uses spring-te-srv6-bsid-database-information-block;
           }
         }
         case multichassis-tag {
           container multi-routing-engine-results {
             list multi-routing-engine-item {
               leaf re-name {
                 type string;
               }
               choice output-tags {
                 case actual-tag {
                   container spring-te-srv6-bsid-database-information {
                     uses spring-te-srv6-bsid-database-information-block;
                   }
                 }
               }
             }
           }
         }
       }
     }
   }
   rpc get-spring-te-perf-measurement-information {
     description "Show performance measurement info for spring traffic engineered LSPs";
     input {
       choice daemon-select {
         case logical-system {
           leaf logical-system {
             description "Name of logical system, or 'all'";
             type string {
             }
           }
         }
       }
       leaf tunnel-source {
         description "Source of tunnel creation";
         type enumeration {
           enum "pcep" {
             description "Path computation element protocol";
           }
           enum "static" {
             description "Static configuration";
           }
           enum "dtm" {
             description "Dynamic tunnel module";
           }
           enum "bgp" {
             description "BGP SRTE";
           }
         }
       }
       leaf regex {
         description "Show entry matching with tunnel name";
         type string;
       }
       leaf state {
         description "Show entries matching with session state";
         type enumeration {
           enum "active" {
             description "Show entries with active state";
           }
           enum "failed" {
             description "Show entries with failed state";
           }
           enum "idle" {
             description "Show entries with idle state";
           }
         }
       }
       leaf forward-type {
         type enumeration {
           enum "sr-mpls" {
             description "Show SR-MPLS entries";
           }
           enum "srv6" {
             description "Show SRv6 entries";
           }
         }
       }
       leaf changed-in-last {
         description "Show entries which are changed in last provided seconds";
         units "seconds";
         type union {
           type string {
             pattern "<.*>|$.*";
           }
           type uint32 {
             range "2 .. 3600";
           }
         }
       }
       choice average-delay-filter {
         case avg-delay-greater-than {
           leaf avg-delay-greater-than {
             description "Show entries which has average delay greater than value";
             units "microseconds";
             type union {
               type string {
                 pattern "<.*>|$.*";
               }
               type uint32 {
                 range "0 .. 4294967295";
               }
             }
           }
         }
         case avg-delay-less-than {
           leaf avg-delay-less-than {
             description "Show entries which has average delay less than value";
             units "microseconds";
             type union {
               type string {
                 pattern "<.*>|$.*";
               }
               type uint32 {
                 range "0 .. 4294967295";
               }
             }
           }
         }
         case avg-delay-equal-to {
           leaf avg-delay-equal-to {
             description "Show entries which has average delay equal to value";
             units "microseconds";
             type union {
               type string {
                 pattern "<.*>|$.*";
               }
               type uint32 {
                 range "0 .. 4294967295";
               }
             }
           }
         }
       }
       choice maximum-delay-filter {
         case max-delay-greater-than {
           leaf max-delay-greater-than {
             description "Show entries which has maximum delay greater than value";
             units "microseconds";
             type union {
               type string {
                 pattern "<.*>|$.*";
               }
               type uint32 {
                 range "0 .. 4294967295";
               }
             }
           }
         }
         case max-delay-less-than {
           leaf max-delay-less-than {
             description "Show entries which has maximum delay less than value";
             units "microseconds";
             type union {
               type string {
                 pattern "<.*>|$.*";
               }
               type uint32 {
                 range "0 .. 4294967295";
               }
             }
           }
         }
         case max-delay-equal-to {
           leaf max-delay-equal-to {
             description "Show entries which has maximum delay equal to value";
             units "microseconds";
             type union {
               type string {
                 pattern "<.*>|$.*";
               }
               type uint32 {
                 range "0 .. 4294967295";
               }
             }
           }
         }
       }
       choice minimum-delay-filter {
         case min-delay-greater-than {
           leaf min-delay-greater-than {
             description "Show entries which has minimum delay greater than value";
             units "microseconds";
             type union {
               type string {
                 pattern "<.*>|$.*";
               }
               type uint32 {
                 range "0 .. 4294967295";
               }
             }
           }
         }
         case min-delay-less-than {
           leaf min-delay-less-than {
             description "Show entries which has minimum delay less than value";
             units "microseconds";
             type union {
               type string {
                 pattern "<.*>|$.*";
               }
               type uint32 {
                 range "0 .. 4294967295";
               }
             }
           }
         }
         case min-delay-equal-to {
           leaf min-delay-equal-to {
             description "Show entries which has minimum delay equal to value";
             units "microseconds";
             type union {
               type string {
                 pattern "<.*>|$.*";
               }
               type uint32 {
                 range "0 .. 4294967295";
               }
             }
           }
         }
       }
       choice delay-variance-filter {
         case delay-var-greater-than {
           leaf delay-var-greater-than {
             description "Show entries which has delay variance greater than value";
             units "microseconds";
             type union {
               type string {
                 pattern "<.*>|$.*";
               }
               type uint32 {
                 range "0 .. 4294967295";
               }
             }
           }
         }
         case delay-var-less-than {
           leaf delay-var-less-than {
             description "Show entries which has delay variance less than value";
             units "microseconds";
             type union {
               type string {
                 pattern "<.*>|$.*";
               }
               type uint32 {
                 range "0 .. 4294967295";
               }
             }
           }
         }
         case delay-var-equal-to {
           leaf delay-var-equal-to {
             description "Show entries which has delay variance equal to value";
             units "microseconds";
             type union {
               type string {
                 pattern "<.*>|$.*";
               }
               type uint32 {
                 range "0 .. 4294967295";
               }
             }
           }
         }
       }
       choice result-update-count-filter {
         case result-updates-greater-than {
           leaf result-updates-greater-than {
             description "Show entries which has number of result updates greater than count";
             type union {
               type string {
                 pattern "<.*>|$.*";
               }
               type uint32 {
                 range "0 .. 4294967295";
               }
             }
           }
         }
         case result-updates-less-than {
           leaf result-updates-less-than {
             description "Show entries which has number of result updates less than count";
             type union {
               type string {
                 pattern "<.*>|$.*";
               }
               type uint32 {
                 range "0 .. 4294967295";
               }
             }
           }
         }
         case result-updates-equal-to {
           leaf result-updates-equal-to {
             description "Show entries which has number of result updates equal to count";
             type union {
               type string {
                 pattern "<.*>|$.*";
               }
               type uint32 {
                 range "0 .. 4294967295";
               }
             }
           }
         }
       }
       choice state-transitions-filter {
         case state-transitions-greater-than {
           leaf state-transitions-greater-than {
             description "Show entries which has number of state transitions greater than count";
             type union {
               type string {
                 pattern "<.*>|$.*";
               }
               type uint32 {
                 range "0 .. 4294967295";
               }
             }
           }
         }
         case state-transitions-less-than {
           leaf state-transitions-less-than {
             description "Show entries which has number of state transitions less than count";
             type union {
               type string {
                 pattern "<.*>|$.*";
               }
               type uint32 {
                 range "0 .. 4294967295";
               }
             }
           }
         }
         case state-transitions-equal-to {
           leaf state-transitions-equal-to {
             description "Show entries which has number of state transitions equal to count";
             type union {
               type string {
                 pattern "<.*>|$.*";
               }
               type uint32 {
                 range "0 .. 4294967295";
               }
             }
           }
         }
       }
       leaf history {
         description "Show transaction history information";
         type empty;
       }
       leaf verbosity_level {
         default "brief";
         type enumeration {
           enum "brief" {
             description "Display brief output (default)";
           }
           enum "detail" {
             description "Display detailed output";
           }
         }
       }
     }
     output {
       choice output-tags {
         case actual-tag {
           container spring-te-perf-measurement-information {
             uses spring-te-perf-measurement-information-block;
           }
         }
         case multichassis-tag {
           container multi-routing-engine-results {
             list multi-routing-engine-item {
               leaf re-name {
                 type string;
               }
               choice output-tags {
                 case actual-tag {
                   container spring-te-perf-measurement-information {
                     uses spring-te-perf-measurement-information-block;
                   }
                 }
               }
             }
           }
         }
       }
     }
   }
   rpc get-spring-te-pm-session-information {
     description "Show spring traffic engineering performance measurement sessions";
     input {
       choice daemon-select {
         case logical-system {
           leaf logical-system {
             description "Name of logical system, or 'all'";
             type string {
             }
           }
         }
       }
       leaf session-id {
         description "Show entry matching with session id";
         type union {
           type string {
             pattern "<.*>|$.*";
           }
           type uint32 {
             range "1 .. 4294967295";
           }
         }
       }
     }
     output {
       choice output-tags {
         case actual-tag {
           container spring-te-pm-session-information {
             uses spring-te-pm-session-information-block;
           }
         }
         case multichassis-tag {
           container multi-routing-engine-results {
             list multi-routing-engine-item {
               leaf re-name {
                 type string;
               }
               choice output-tags {
                 case actual-tag {
                   container spring-te-pm-session-information {
                     uses spring-te-pm-session-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping spring-te-overview-information-block {
     container spring-te-overview {
       description
         "Overview of SPRING Traffic-Engineering";
       leaf ste-preference {
         type uint32;
       }
       leaf ste-num-lsps {
         type uint32;
       }
       leaf ste-num-lsps-up {
         type uint32;
       }
       leaf ste-num-lsps-down {
         type uint32;
       }
       leaf ste-num-lsps-initializing {
         type uint32;
       }
       leaf ste-num-ldp-tunnels {
         type uint32;
       }
       container ste-ext-ctrlrs {
         leaf-list ste-ext-ctrlr {
           type string;
         }
       }
       container ste-delay-measurement-overview {
         leaf ste-twamp-client-state {
           type string;
         }
         leaf ste-twamp-client-state-changed {
           type string;
         }
         leaf ste-twamp-client-sessions {
           type uint32;
         }
         leaf ste-twamp-client-sessions-active {
           type uint32;
         }
         leaf ste-twamp-client-sessions-failed {
           type uint32;
         }
         leaf ste-twamp-client-sessions-idle {
           type uint32;
         }
       }
       container ste-sbfd-information {
         description
           "SBFD overview in SPRING Traffic-Engineering";
         leaf ste-num-sbfd-sessions {
           type uint32;
         }
         leaf ste-num-sbfd-sessions-pending-process {
           type uint32;
         }
         leaf ste-num-sbfd-sessions-pending-del {
           type uint32;
         }
         leaf ste-sbfd-frr-enabled {
           type string;
         }
       }
       container ste-bsid-information {
         description
           "BSID overview in SPRING Traffic-Engineering";
         leaf ste-num-bsids {
           type uint32;
         }
         leaf ste-num-unallocated-bsids {
           type uint32;
         }
       }
       container ste-num-route-information {
         description
           "Route overview in SPRING Traffic-Engineering";
         leaf ste-num-v4-routes {
           type uint32;
         }
         leaf ste-num-v4-colored-routes {
           type uint32;
         }
         leaf ste-num-v6-routes {
           type uint32;
         }
         leaf ste-num-v6-colored-routes {
           type uint32;
         }
         leaf ste-num-mpls-bsid-routes {
           type uint32;
         }
       }
       container ste-effective-config-information {
         description
           "Effective configurations in SPRING Traffic-Engineering";
         leaf ste-mpls-seg-list-depth {
           type uint32;
         }
         leaf ste-srv6-seg-list-depth {
           type uint32;
         }
         leaf ste-micro-srv6-seg-list-depth {
           type uint32;
         }
       }
       container ste-global-config-information {
         description
           "Global Configurations in SPRING Traffic-Engineering";
         leaf ste-srv6 {
           type string;
         }
         leaf ste-import-color-only-cross-af {
           type string;
         }
         leaf ste-inet-color-append-exp-null {
           type string;
         }
         leaf ste-inet6-color-append-exp-null {
           type string;
         }
         leaf ste-ipv6-tunnel-append-exp-null {
           type string;
         }
         leaf ste-inherit-label-nhs {
           type string;
         }
         leaf ste-no-cnh {
           type string;
         }
         leaf ste-tunnel-tracking {
           type string;
         }
         leaf ste-traffic-eng-db {
           type string;
         }
         leaf ste-entropy {
           type string;
         }
         leaf ste-srv6-use-ingress-routes-as-transit {
           type string;
         }
       }
       container ste-inherited-config-information {
         description
           "Inherited Configurations in SPRING Traffic-Engineering";
         leaf ste-no-reduced-srh {
           type string;
         }
         leaf ste-srv6-no-propagate-ttl {
           type string;
         }
         leaf ste-ipv6-tunnel {
           type string;
         }
         leaf ste-egress-chaining {
           type string;
         }
         leaf ste-remove-srv6-last-sid {
           type string;
         }
         leaf ste-ext-ctrlr-multipath {
           type string;
         }
       }
       leaf ste-num-policies {
         type uint32;
       }
       leaf ste-num-pending-compute-req {
         type uint32;
       }
       leaf ste-num-templates {
         type uint32;
       }
       leaf ste-num-stats-info {
         type uint32;
       }
     }
   }
   grouping spring-te-lsp-information-block {
     container spring-te-lsp-help-header {
       leaf spring-te-lsp-help-info {
         type string;
       }
     }
     list spring-te-lsp {
       key "stl-lsp-name";
       description
         "SPRING Traffic-Engineered LSP";
       leaf stl-lsp-name {
         type string;
       }
       leaf stl-tunnel-source {
         type string;
       }
       leaf stl-tunnel-template {
         type string;
       }
       leaf stl-dest-address {
         type jt:ipaddr;
       }
       leaf stl-binding-sid-label {
         type string;
       }
       leaf stl-binding-sid-label-type {
         type string;
       }
       leaf stl-binding-sid-label-state {
         type string;
       }
       leaf stl-binding-sid-label-state-reason {
         type string;
       }
       leaf stl-te-group-id {
         type uint32;
       }
       leaf stl-src-address {
         type jt:ipaddr;
       }
       leaf stl-tunnel-type {
         type string;
       }
       leaf stl-lsp-state {
         type string;
       }
       leaf stl-ldp-tunneling {
         type string;
       }
       leaf stl-tunnel-capabilities {
         type string;
       }
       leaf stl-metric {
         type uint32;
       }
       container stl-telemetry-statistics {
         description
           "SPRING Traffic-Engineered Telemetry Statistics ";
         leaf stl-telemetry-statistics.heading {
           type string;
           description
             "SPRING Traffic-Engineered Telemetry Statistics ";
         }
         list stl-telemetry-statistics-info {
           leaf stl-telemetry-statistics-sensor-name {
             type string;
           }
           leaf stl-telemetry-statistics-sensor-id {
             type uint32;
           }
         }
       }
       container stl-path {
         description
           "SPRING Traffic-Engineered Path ";
         leaf stl-path-name {
           type string;
         }
         leaf stl-path-state {
           type string;
         }
         leaf stl-path-ero-valid {
           type string;
         }
         leaf stl-path-out-if {
           type string;
         }
         leaf stl-path-auto-translate-status {
           type string;
         }
         leaf stl-path-auto-translate-result {
           type string;
         }
         leaf stl-path-bfd-status {
           type string;
         }
         leaf stl-path-bfd-name {
           type string;
         }
         leaf stl-path-bfd-up {
           type uint32;
         }
         leaf stl-path-bfd-down {
           type uint32;
         }
         leaf stl-path-bfd-remote-discriminator-string {
           type string;
         }
         leaf stl-path-compute-algo-id {
           type uint32;
         }
         leaf stl-path-compute-status {
           type string;
         }
         leaf stl-path-compute-result {
           type string;
         }
         leaf stl-path-compute-profile {
           type string;
         }
         leaf stl-path-compute-error-reason {
           type string;
         }
         leaf stl-path-compute-igp-instance {
           type string;
         }
         leaf stl-path-compute-igp-topology {
           type string;
         }
         leaf stl-num-computed-paths {
           type uint32;
         }
         leaf stl-lsp-path-bandwidth {
           type uint32;
         }
         leaf stl-lsp-path-bandwidth-prio {
           type uint32;
         }
         leaf stl-sr-segment-index {
           type uint32;
         }
         container str-lsp-path-compute-info {
           leaf str-lsp-path-compute-status {
             type string;
           }
           leaf str-lsp-path-compute-result {
             type string;
           }
           leaf str-lsp-path-compute-profile {
             type string;
           }
           leaf str-lsp-num-computed-paths {
             type uint32;
           }
           leaf str-lsp-path-bandwidth {
             type uint32;
           }
           leaf str-lsp-path-bandwidth-prio {
             type uint32;
           }
         }
         container stl-path-events {
           description
             "Events of sub-candidate-path";
           leaf stl-path-events.heading {
             type string;
             description
               "Events of sub-candidate-path";
           }
           leaf stl-max-events {
             type uint32;
           }
           container events {
             description
               "Events of source-routing-path";
             leaf timestamp {
               type string;
               description
                 "Time when something occurs";
             }
             leaf type-of-event {
               type string;
             }
           }
         }
         container stl-sr-ero-list {
           leaf stl-sr-ero-num-eros {
             type uint32;
           }
           leaf stl-sr-ero-num-eros-pm-path {
             type uint32;
           }
           leaf stl-sr-ero-num-eros-pm-ret-path {
             type uint32;
           }
           list stl-sr-ero {
             key "stl-sr-ero-index";
             leaf stl-sr-ero-index {
               type uint32;
             }
             leaf stl-sr-ero-hop-type {
               type string;
             }
             leaf stl-sr-ero-nai-type {
               type string;
             }
             leaf stl-sr-ero-ip-node-id {
               type jt:ipaddr;
             }
             leaf stl-sr-ero-local-intf-id {
               type jt:ipaddr;
             }
             leaf stl-sr-ero-remote-intf-id {
               type jt:ipaddr;
             }
             leaf stl-sr-ero-unnum-local-router-id {
               type jt:ipaddr;
             }
             leaf stl-sr-ero-unnum-local-id {
               type uint32;
             }
             leaf stl-sr-ero-unnum-remote-router-id {
               type jt:ipaddr;
             }
             leaf stl-sr-ero-unnum-remote-id {
               type uint32;
             }
             leaf stl-sr-ero-sid-type {
               type string;
             }
             leaf stl-sr-ero-sid-value {
               type uint32;
             }
             leaf stl-sr-ero-srv6-sid-value {
               type jt:ipaddr;
             }
             leaf stl-sr-ero-micro-srv6-sid-value {
               type jt:ipaddr;
             }
             leaf stl-sr-ero-sid-ttl {
               type uint32;
             }
             leaf stl-sr-ero-sid-exp {
               type uint32;
             }
             leaf stl-sr-ero-micro-srv6-sid-structure-bl {
               type string;
             }
             leaf stl-sr-ero-micro-srv6-sid-structure-nl {
               type string;
             }
             leaf stl-sr-ero-micro-srv6-sid-structure-fl {
               type string;
             }
             leaf stl-sr-ero-micro-srv6-sid-structure-al {
               type string;
             }
             leaf stl-sr-ero-micro-srv6-sid-endpoint-behavior {
               type string;
             }
           }
         }
         container stl-events {
           description
             "Events of segment-list";
           leaf stl-events.heading {
             type string;
             description
               "Events of segment-list";
           }
           leaf max-events {
             type uint32;
           }
           container events {
             description
               "Events of source-routing-path";
             leaf timestamp {
               type string;
               description
                 "Time when something occurs";
             }
             leaf type-of-event {
               type string;
             }
           }
         }
         container stpm-path-measurement-info {
           description
             "Spring traffic engineered performance measurement data";
           leaf stpm-path-session-state {
             type string;
           }
           leaf stpm-path-session-id {
             type uint32;
           }
           leaf stpm-path-session-last-changed {
             type string;
           }
           leaf stpm-path-session-avg-delay {
             type uint32;
           }
           leaf stpm-path-session-max-delay {
             type uint32;
           }
           leaf stpm-path-session-min-delay {
             type uint32;
           }
           leaf stpm-path-session-delay-variance {
             type uint32;
           }
           leaf stpm-path-session-twamp-owner {
             type string;
           }
           leaf stpm-path-session-twamp-testname {
             type string;
           }
           leaf stpm-path-session-state-transitions {
             type uint32;
           }
           leaf stpm-path-session-result-updates {
             type uint32;
           }
           leaf stpm-path-session-error {
             type string;
           }
         }
         list stl-compute {
           description
             "Computed path parameters";
           leaf stl-computed-path-index {
             type uint32;
           }
           container stl-bfd {
             description
               "SPRING Per LSP-BFD Info";
             leaf stl-bfd-status {
               type string;
             }
             leaf stl-bfd-name {
               type string;
             }
             leaf stl-bfd-up {
               type uint32;
             }
             leaf stl-bfd-down {
               type uint32;
             }
             leaf stl-bfd-remote-discriminator {
               type string;
             }
           }
           container stl-computed-metric {
             leaf stl-computed-te-metric {
               type uint64;
             }
             leaf stl-computed-igp-metric {
               type uint64;
             }
             leaf stl-computed-min-delay-metric {
               type uint64;
             }
             leaf stl-computed-max-delay-metric {
               type uint64;
             }
             leaf stl-computed-avg-delay-metric {
               type uint64;
             }
             leaf stl-optimized-metric-type {
               type string;
             }
             leaf stl-optimized-metric-type-active {
               type string;
             }
           }
           container stl-events {
             description
               "Events of segment-list";
             leaf stl-events.heading {
               type string;
               description
                 "Events of segment-list";
             }
             leaf max-events {
               type uint32;
             }
             container events {
               description
                 "Events of source-routing-path";
               leaf timestamp {
                 type string;
                 description
                   "Time when something occurs";
               }
               leaf type-of-event {
                 type string;
               }
             }
           }
           container stl-sr-computed-segment-list {
             leaf stl-sr-computed-segments-count {
               type uint32;
             }
             list stl-sr-computed-segment {
               leaf stl-sr-computed-segment-index {
                 type uint32;
               }
               leaf stl-sr-computed-segment-type {
                 type string;
               }
               leaf stl-sr-adjacency-segment-label {
                 type string;
               }
               leaf stl-sr-srv6-adjacency-segment {
                 type jt:ipaddr;
               }
               leaf stl-sr-micro-srv6-adjacency-segment {
                 type jt:ipaddr;
               }
               leaf stl-sr-source-router-id {
                 type jt:ipaddr;
               }
               leaf stl-sr-destination-router-id {
                 type jt:ipaddr;
               }
               leaf stl-sr-source-iso-system-id {
                 type string;
               }
               leaf stl-sr-destination-iso-system-id {
                 type string;
               }
               leaf stl-sr-source-interface-address {
                 type jt:ipaddr;
               }
               leaf stl-sr-destination-interface-address {
                 type jt:ipaddr;
               }
               leaf stl-sr-node-segment-label {
                 type string;
               }
               leaf stl-sr-srv6-node-segment {
                 type jt:ipaddr;
               }
               leaf stl-sr-micro-srv6-node-segment {
                 type jt:ipaddr;
               }
               leaf stl-sr-router-id {
                 type jt:ipaddr;
               }
               leaf stl-sr-v6-router-id {
                 type jt:ipaddr;
               }
               leaf stl-sr-iso-system-id {
                 type string;
               }
               leaf stl-sr-prefix-segment-label {
                 type string;
               }
               container stl-sr-ero-srv6-segment-attributes {
                 leaf stl-sr-ero-srv6-sid-structure-bl {
                   type string;
                 }
                 leaf stl-sr-ero-srv6-sid-structure-nl {
                   type string;
                 }
                 leaf stl-sr-ero-srv6-sid-structure-fl {
                   type string;
                 }
                 leaf stl-sr-ero-srv6-sid-structure-al {
                   type string;
                 }
                 leaf stl-sr-ero-srv6-sid-ep-behavior {
                   type string;
                 }
               }
               list stl-sr-prefix-segment-node-info {
                 key "stl-sr-prefix-segment-node-info-index";
                 leaf stl-sr-prefix-segment-node-router-id {
                   type jt:ipaddr;
                 }
                 leaf stl-sr-prefix-segment-node-v6-router-id {
                   type jt:ipaddr;
                 }
                 leaf stl-sr-prefix-segment-node-iso-system-id {
                   type string;
                 }
                 leaf stl-sr-prefix-segment-node-info-index {
                   type uint32;
                 }
               }
             }
           }
         }
         list stl-lsp-telemetry-statistics {
           description
             "SPRING Traffic-Engineered Per LSP Telemetry Statistics ";
           leaf-list stl-lsp-telemetry-statistics.heading {
             type string;
             description
               "SPRING Traffic-Engineered Per LSP Telemetry Statistics ";
           }
           list stl-lsp-telemetry-statistics-info {
             leaf stl-lsp-telemetry-statistics-sensor-name {
               type string;
             }
             leaf stl-lsp-telemetry-statistics-sensor-id {
               type uint32;
             }
           }
         }
         container stl-delegation {
           description
             "SPRING Traffic-Engineered Path Delegation info ";
           leaf stl-delegation.heading {
             type string;
             description
               "SPRING Traffic-Engineered Path Delegation info ";
           }
           leaf stl-delegation-control-status {
             type string;
           }
           leaf stl-delegation-routing-status {
             type string;
           }
         }
         container stl-delegation-compute-constraint-info {
           description
             "SPRING TE compute constraint info ";
           leaf stl-delegation-compute-constraint-info.heading {
             type string;
             description
               "SPRING TE compute constraint info ";
           }
           leaf stl-delegation-compute-constraint-bandwidth-requested-cli {
             type string;
           }
           leaf stl-delegation-compute-constraint-bandwidth-requested-pcupdate {
             type string;
           }
           leaf stl-delegation-compute-constraint-actual-bandwidth-pcupdate {
             type string;
           }
           leaf stl-delegation-compute-constraint-bandwidth-setup-priority {
             type string;
           }
           leaf stl-delegation-compute-constraint-bandwidth-hold-priority {
             type string;
           }
         }
       }
       container stl-srv6-binding-sid-info {
         leaf stl-srv6-binding-sid {
           type string;
         }
         leaf stl-srv6-binding-sid-state {
           type string;
         }
         leaf stl-srv6-binding-sid-locator {
           type string;
         }
         leaf stl-srv6-binding-sid-ep-bhv {
           type string;
         }
         leaf stl-srv6-binding-sid-sstlv {
           type string;
         }
         leaf stl-srv6-binding-sid-state-reason {
           type string;
         }
       }
     }
     container spring-te-lsp-counts {
       leaf stl-total {
         type uint32;
       }
       leaf stl-up {
         type uint32;
       }
       leaf stl-down {
         type uint32;
       }
       leaf stl-initializing {
         type uint32;
       }
     }
   }
   grouping spring-te-bfd-session-information-block {
     list spring-te-bfd-session {
       key "stl-path-bfd-name";
       leaf stl-path-bfd-name {
         type string;
       }
       leaf stl-path-bfd-status {
         type string;
       }
       container ste-bfd-ref-lsps {
         leaf-list ste-bfd-ref-lsp {
           type string;
         }
       }
       container stl-sr-ero-list {
         leaf stl-sr-ero-num-eros {
           type uint32;
         }
         list stl-sr-ero {
           key "stl-sr-ero-index";
           leaf stl-sr-ero-index {
             type uint32;
           }
           leaf stl-sr-ero-hop-type {
             type string;
           }
           leaf stl-sr-ero-nai-type {
             type string;
           }
           leaf stl-sr-ero-ip-node-id {
             type jt:ipaddr;
           }
           leaf stl-sr-ero-local-intf-id {
             type jt:ipaddr;
           }
           leaf stl-sr-ero-remote-intf-id {
             type jt:ipaddr;
           }
           leaf stl-sr-ero-unnum-local-router-id {
             type jt:ipaddr;
           }
           leaf stl-sr-ero-unnum-local-id {
             type uint32;
           }
           leaf stl-sr-ero-unnum-remote-router-id {
             type jt:ipaddr;
           }
           leaf stl-sr-ero-unnum-remote-id {
             type uint32;
           }
           leaf stl-sr-ero-sid-type {
             type string;
           }
           leaf stl-sr-ero-sid-value {
             type uint32;
           }
           leaf stl-sr-ero-srv6-sid-value {
             type jt:ipaddr;
           }
           leaf stl-sr-ero-micro-srv6-sid-value {
             type jt:ipaddr;
           }
           leaf stl-sr-ero-sid-ttl {
             type uint32;
           }
           leaf stl-sr-ero-sid-exp {
             type uint32;
           }
           leaf stl-sr-ero-micro-srv6-sid-structure-bl {
             type string;
           }
           leaf stl-sr-ero-micro-srv6-sid-structure-nl {
             type string;
           }
           leaf stl-sr-ero-micro-srv6-sid-structure-fl {
             type string;
           }
           leaf stl-sr-ero-micro-srv6-sid-structure-al {
             type string;
           }
           leaf stl-sr-ero-micro-srv6-sid-endpoint-behavior {
             type string;
           }
         }
         leaf stl-sr-ero-num-eros-pm-path {
           type uint32;
         }
         leaf stl-sr-ero-num-eros-pm-ret-path {
           type uint32;
         }
       }
       container stl-srv6-bfd-compressed-sid-list {
         leaf stl-srv6-bfd-compressed-num-sid {
           type uint32;
         }
         list stl-srv6-bfd-compressed-sid-info {
           key "stl-srv6-bfd-compressed-sid-index";
           leaf stl-srv6-bfd-compressed-sid-index {
             type string;
           }
           leaf stl-srv6-bfd-compressed-sid {
             type jt:ipaddr;
           }
         }
       }
       leaf stl-path-bfd-destination {
         type jt:ipaddr;
       }
       leaf stl-path-bfd-error-message {
         type string;
       }
       leaf stl-path-bfd-remote-discriminator {
         type uint32;
       }
       leaf stl-path-bfd-local-discriminator {
         type uint32;
       }
     }
     container spring-te-bfd-session-counts {
       leaf ste-bfd-session-total {
         type uint32;
       }
       leaf ste-bfd-session-up {
         type uint32;
       }
       leaf ste-bfd-session-down {
         type uint32;
       }
     }
   }
   grouping spring-te-route-information-block {
     list spring-te-route {
       description
         "SPRING Traffic-Engineered Route";
       leaf str-dest-address {
         type string;
       }
       leaf str-dest-address-len {
         type uint32;
       }
       leaf str-tunnel-source-brief {
         type string;
       }
       leaf str-instance {
         type string;
       }
       list spring-te-route-lsp-brief-info {
         leaf str-sr-preference-override-brief {
           type uint32;
         }
         leaf str-sr-preference-brief {
           type string;
         }
         leaf str-lsp-name-brief {
           type string;
         }
         list spring-te-lsp-path-brief-info {
           leaf str-lsp-path-name-brief {
             type string;
           }
         }
       }
       list str-srv6-binding-sid-info {
         description
           "SRv6 BSID information";
         leaf str-srv6-binding-sid-ep-bhv {
           type string;
         }
         leaf str-srv6-binding-sid-sstlv {
           type string;
         }
       }
       list spring-te-route-node-information {
         leaf str-distinguisher {
           type uint32;
         }
         leaf str-origin {
           type string;
         }
         leaf str-tunnel-source {
           type string;
         }
         leaf str-route-nhtype {
           type string;
         }
         leaf str-route-metric2 {
           type uint32;
         }
         leaf str-route-type {
           type string;
         }
         leaf str-route-encap-mode {
           type string;
         }
         leaf str-using-tc-class {
           type string;
         }
         leaf str-invalid-reason {
           type string;
         }
         list spring-te-route-lsp-information {
           leaf str-lsp-name {
             type string;
           }
           leaf str-sr-preference {
             type string;
           }
           leaf str-sr-preference-override {
             type uint32;
           }
           leaf str-sr-lsp-metric {
             type uint32;
           }
           leaf str-sr-lsp-weight {
             type uint32;
           }
           leaf str-sr-lsp-state {
             type string;
           }
           leaf str-sr-lsp-id {
             type uint32;
           }
           leaf str-sr-lsp-sensor-id {
             type string;
           }
           container stl-telemetry-statistics {
             description
               "SPRING Traffic-Engineered Telemetry Statistics ";
             leaf stl-telemetry-statistics.heading {
               type string;
               description
                 "SPRING Traffic-Engineered Telemetry Statistics ";
             }
             list stl-telemetry-statistics-info {
               leaf stl-telemetry-statistics-sensor-name {
                 type string;
               }
               leaf stl-telemetry-statistics-sensor-id {
                 type uint32;
               }
             }
           }
           list str-sr-segment-list {
             description
               "SPRING Traffic-Engineered Path ";
             leaf str-sr-seg-path-name {
               type string;
             }
             leaf str-sr-path-state {
               type string;
             }
             leaf str-sr-seg-path-bandwidth {
               type uint32;
             }
             leaf str-sr-seg-path-out-if {
               type string;
             }
             leaf str-sr-seg-path-weight {
               type uint32;
             }
             leaf str-sr-seg-path-balance {
               type uint32;
             }
             leaf stl-path-compute-info {
               type string;
             }
             leaf str-sr-seg-path-valid {
               type string;
             }
             container stl-delegation {
               description
                 "SPRING Traffic-Engineered Path Delegation info ";
               leaf stl-delegation.heading {
                 type string;
                 description
                   "SPRING Traffic-Engineered Path Delegation info ";
               }
               leaf stl-delegation-control-status {
                 type string;
               }
               leaf stl-delegation-routing-status {
                 type string;
               }
             }
             container stl-delegation-compute-constraint-info {
               description
                 "SPRING TE compute constraint info ";
               leaf stl-delegation-compute-constraint-bandwidth-requested-cli {
                 type string;
               }
               leaf stl-delegation-compute-constraint-bandwidth-requested-pcupdate {
                 type string;
               }
               leaf stl-delegation-compute-constraint-actual-bandwidth-pcupdate {
                 type string;
               }
               leaf stl-delegation-compute-constraint-bandwidth-setup-priority {
                 type string;
               }
               leaf stl-delegation-compute-constraint-bandwidth-hold-priority {
                 type string;
               }
             }
             list stl-lsp-telemetry-statistics {
               description
                 "SPRING Traffic-Engineered Per LSP Telemetry Statistics ";
               leaf-list stl-lsp-telemetry-statistics.heading {
                 type string;
                 description
                   "SPRING Traffic-Engineered Per LSP Telemetry Statistics ";
               }
               list stl-lsp-telemetry-statistics-info {
                 leaf stl-lsp-telemetry-statistics-sensor-name {
                   type string;
                 }
                 leaf stl-lsp-telemetry-statistics-sensor-id {
                   type uint32;
                 }
               }
             }
             list stl-compute {
               description
                 "Computed path parameters";
               leaf stl-computed-path-index {
                 type uint32;
               }
               container stl-bfd {
                 description
                   "SPRING Per LSP-BFD Info";
                 leaf stl-bfd-status {
                   type string;
                 }
                 leaf stl-bfd-name {
                   type string;
                 }
                 leaf stl-bfd-up {
                   type uint32;
                 }
                 leaf stl-bfd-down {
                   type uint32;
                 }
                 leaf stl-bfd-remote-discriminator {
                   type string;
                 }
               }
               container stl-computed-metric {
                 leaf stl-computed-te-metric {
                   type uint64;
                 }
                 leaf stl-computed-igp-metric {
                   type uint64;
                 }
                 leaf stl-computed-min-delay-metric {
                   type uint64;
                 }
                 leaf stl-computed-max-delay-metric {
                   type uint64;
                 }
                 leaf stl-computed-avg-delay-metric {
                   type uint64;
                 }
                 leaf stl-optimized-metric-type {
                   type string;
                 }
                 leaf stl-optimized-metric-type-active {
                   type string;
                 }
               }
               container stl-events {
                 description
                   "Events of segment-list";
                 leaf stl-events.heading {
                   type string;
                   description
                     "Events of segment-list";
                 }
                 leaf max-events {
                   type uint32;
                 }
                 container events {
                   description
                     "Events of source-routing-path";
                   leaf timestamp {
                     type string;
                     description
                       "Time when something occurs";
                   }
                   leaf type-of-event {
                     type string;
                   }
                 }
               }
               container stl-sr-computed-segment-list {
                 leaf stl-sr-computed-segments-count {
                   type uint32;
                 }
                 list stl-sr-computed-segment {
                   leaf stl-sr-computed-segment-index {
                     type uint32;
                   }
                   leaf stl-sr-computed-segment-type {
                     type string;
                   }
                   leaf stl-sr-adjacency-segment-label {
                     type string;
                   }
                   leaf stl-sr-srv6-adjacency-segment {
                     type jt:ipaddr;
                   }
                   leaf stl-sr-micro-srv6-adjacency-segment {
                     type jt:ipaddr;
                   }
                   leaf stl-sr-source-router-id {
                     type jt:ipaddr;
                   }
                   leaf stl-sr-destination-router-id {
                     type jt:ipaddr;
                   }
                   leaf stl-sr-source-iso-system-id {
                     type string;
                   }
                   leaf stl-sr-destination-iso-system-id {
                     type string;
                   }
                   leaf stl-sr-source-interface-address {
                     type jt:ipaddr;
                   }
                   leaf stl-sr-destination-interface-address {
                     type jt:ipaddr;
                   }
                   leaf stl-sr-node-segment-label {
                     type string;
                   }
                   leaf stl-sr-srv6-node-segment {
                     type jt:ipaddr;
                   }
                   leaf stl-sr-micro-srv6-node-segment {
                     type jt:ipaddr;
                   }
                   leaf stl-sr-router-id {
                     type jt:ipaddr;
                   }
                   leaf stl-sr-v6-router-id {
                     type jt:ipaddr;
                   }
                   leaf stl-sr-iso-system-id {
                     type string;
                   }
                   leaf stl-sr-prefix-segment-label {
                     type string;
                   }
                   container stl-sr-ero-srv6-segment-attributes {
                     leaf stl-sr-ero-srv6-sid-structure-bl {
                       type string;
                     }
                     leaf stl-sr-ero-srv6-sid-structure-nl {
                       type string;
                     }
                     leaf stl-sr-ero-srv6-sid-structure-fl {
                       type string;
                     }
                     leaf stl-sr-ero-srv6-sid-structure-al {
                       type string;
                     }
                     leaf stl-sr-ero-srv6-sid-ep-behavior {
                       type string;
                     }
                   }
                   list stl-sr-prefix-segment-node-info {
                     key "stl-sr-prefix-segment-node-info-index";
                     leaf stl-sr-prefix-segment-node-router-id {
                       type jt:ipaddr;
                     }
                     leaf stl-sr-prefix-segment-node-v6-router-id {
                       type jt:ipaddr;
                     }
                     leaf stl-sr-prefix-segment-node-iso-system-id {
                       type string;
                     }
                     leaf stl-sr-prefix-segment-node-info-index {
                       type uint32;
                     }
                   }
                 }
               }
             }
             container stl-sr-ero-list {
               leaf stl-sr-ero-num-eros {
                 type uint32;
               }
               leaf stl-sr-ero-num-eros-pm-path {
                 type uint32;
               }
               leaf stl-sr-ero-num-eros-pm-ret-path {
                 type uint32;
               }
               list stl-sr-ero {
                 key "stl-sr-ero-index";
                 leaf stl-sr-ero-index {
                   type uint32;
                 }
                 leaf stl-sr-ero-hop-type {
                   type string;
                 }
                 leaf stl-sr-ero-nai-type {
                   type string;
                 }
                 leaf stl-sr-ero-ip-node-id {
                   type jt:ipaddr;
                 }
                 leaf stl-sr-ero-local-intf-id {
                   type jt:ipaddr;
                 }
                 leaf stl-sr-ero-remote-intf-id {
                   type jt:ipaddr;
                 }
                 leaf stl-sr-ero-unnum-local-router-id {
                   type jt:ipaddr;
                 }
                 leaf stl-sr-ero-unnum-local-id {
                   type uint32;
                 }
                 leaf stl-sr-ero-unnum-remote-router-id {
                   type jt:ipaddr;
                 }
                 leaf stl-sr-ero-unnum-remote-id {
                   type uint32;
                 }
                 leaf stl-sr-ero-sid-type {
                   type string;
                 }
                 leaf stl-sr-ero-sid-value {
                   type uint32;
                 }
                 leaf stl-sr-ero-srv6-sid-value {
                   type jt:ipaddr;
                 }
                 leaf stl-sr-ero-micro-srv6-sid-value {
                   type jt:ipaddr;
                 }
                 leaf stl-sr-ero-sid-ttl {
                   type uint32;
                 }
                 leaf stl-sr-ero-sid-exp {
                   type uint32;
                 }
                 leaf stl-sr-ero-micro-srv6-sid-structure-bl {
                   type string;
                 }
                 leaf stl-sr-ero-micro-srv6-sid-structure-nl {
                   type string;
                 }
                 leaf stl-sr-ero-micro-srv6-sid-structure-fl {
                   type string;
                 }
                 leaf stl-sr-ero-micro-srv6-sid-structure-al {
                   type string;
                 }
                 leaf stl-sr-ero-micro-srv6-sid-endpoint-behavior {
                   type string;
                 }
               }
             }
           }
         }
         leaf str-resolved {
           type string;
         }
       }
     }
   }
   grouping spring-te-binding-sid-database-information-block {
     list ste-binding-sid {
       key "ste-bsid-20-bit-label";
       description
         "SPRING Traffic-Engineered Binding Sid";
       leaf ste-bsid-20-bit-label {
         type uint32;
       }
       list ste-bsid-policy-info {
         key "ste-bsid-policy";
         leaf ste-bsid-error {
           type string;
         }
         leaf ste-bsid-policy-active {
           type string;
         }
         leaf ste-bsid-policy {
           type string;
         }
         container ste-bsid-associated-tunnel-info {
           list ste-bsid-associated-tunnel {
             key "ste-bsid-associated-tunnel-name";
             leaf ste-bsid-associated-tunnel-name {
               type string;
             }
             leaf ste-bsid-associated-tunnel-bsid-type {
               type string;
             }
             leaf ste-bsid-associated-tunnel-bsid-s {
               type uint32;
             }
             leaf ste-bsid-associated-tunnel-bsid-cos {
               type uint32;
             }
             leaf ste-bsid-associated-tunnel-bsid-ttl {
               type uint32;
             }
             leaf ste-bsid-associated-tunnel-bsid-unallocation-reason {
               type string;
             }
           }
         }
         leaf ste-bsid-policy-inactive {
           type string;
         }
       }
       leaf ste-bsid-origin {
         type string;
       }
     }
   }
   grouping spring-te-srv6-bsid-database-information-block {
     list ste-srv6-binding-sid {
       key "ste-srv6-bsid ste-srv6-bsid-len";
       description
         "SPRING-TE SRv6 Binding SID";
       leaf ste-srv6-bsid {
         type string;
       }
       leaf ste-srv6-bsid-len {
         type uint32;
       }
       leaf ste-srv6-bsid-ep-bhv {
         type uint32;
       }
       container ste-srv6-bsid-policies {
         description
           "SPRING-TE SRv6 BSID policies";
         list ste-srv6-bsid-policy-info {
           key "ste-srv6-bsid-policy";
           description
             "SPRING-TE SRv6 BSID policy information";
           leaf ste-srv6-bsid-policy-active {
             type string;
           }
           leaf ste-srv6-bsid-policy {
             type string;
           }
           container ste-srv6-bsid-policy-tunnels-info {
             description
               "SPRING-TE SRv6 BSID policy tunnel information";
             list ste-srv6-bsid-policy-tunnel {
               key "ste-srv6-bsid-policy-tunnel-name";
               description
                 "SPRING-TE SRv6 BSID tunnel information";
               leaf ste-srv6-bsid-policy-tunnel-name {
                 type string;
               }
               leaf ste-srv6-bsid-policy-tunnel-unallocation-reason {
                 type string;
               }
             }
           }
           leaf ste-srv6-bsid-policy-inactive {
             type string;
           }
         }
       }
       leaf ste-srv6-bsid-locator {
         type string;
       }
       leaf ste-srv6-bsid-origin {
         type string;
       }
       leaf ste-srv6-bsid-sstlv {
         type string;
       }
     }
   }
   grouping spring-te-perf-measurement-information-block {
     container spring-te-perf-measurement-help-header {
       leaf spring-te-perf-measurement-help-info {
         type string;
       }
     }
     list spring-te-perf-measurement {
       key "stpm-tunnel-name";
       description
         "Spring traffic engineered performance measurement info";
       leaf stpm-tunnel-name {
         type string;
       }
       leaf stpm-tunnel-source {
         type string;
       }
       leaf stpm-tunnel-type {
         type string;
       }
       leaf stpm-tunnel-src {
         type jt:ipaddr;
       }
       leaf stpm-tunnel-dst {
         type jt:ipaddr;
       }
       leaf stpm-tunnel-probe-interval {
         type uint32;
       }
       leaf stpm-tunnel-probe-count {
         type uint32;
       }
       leaf stpm-tunnel-periodic-interval {
         type uint32;
       }
       leaf stpm-tunnel-periodic-threshold {
         type uint32;
       }
       leaf stpm-tunnel-accelerated {
         type string;
       }
       leaf stpm-tunnel-accelerated-threshold {
         type uint32;
       }
       leaf stpm-segment-id {
         type uint32;
       }
       leaf stpm-session-state {
         type string;
       }
       leaf stpm-avg-delay {
         type uint32;
       }
       leaf stpm-max-delay {
         type uint32;
       }
       leaf stpm-min-delay {
         type uint32;
       }
       leaf stpm-delay-variance {
         type uint32;
       }
       leaf stpm-last-changed {
         type string;
       }
       leaf stpm-twamp-owner {
         type string;
       }
       leaf stpm-twamp-testname {
         type string;
       }
       list stpm-sub-cp {
         key "stpm-sub-cp-name";
         description
           "Spring traffic engineered performance measurement sub candidate 
           path info";
         leaf stpm-sub-cp-name {
           type string;
         }
         leaf stpm-sub-cp-ret-name {
           type string;
         }
         list stpm-path-info {
           key "stpm-segment-list-id";
           description
             "Spring traffic engineered performance measurement path info";
           leaf stpm-segment-list-id {
             type uint32;
           }
           container stpm-segment-list {
             description
               "Spring traffic engineered performance measurement segment 
               list info";
             container stl-sr-ero-list {
               leaf stl-sr-ero-num-eros-pm-path {
                 type uint32;
               }
               leaf stl-sr-ero-num-eros {
                 type uint32;
               }
               leaf stl-sr-ero-num-eros-pm-ret-path {
                 type uint32;
               }
               list stl-sr-ero {
                 key "stl-sr-ero-index";
                 leaf stl-sr-ero-index {
                   type uint32;
                 }
                 leaf stl-sr-ero-hop-type {
                   type string;
                 }
                 leaf stl-sr-ero-nai-type {
                   type string;
                 }
                 leaf stl-sr-ero-ip-node-id {
                   type jt:ipaddr;
                 }
                 leaf stl-sr-ero-local-intf-id {
                   type jt:ipaddr;
                 }
                 leaf stl-sr-ero-remote-intf-id {
                   type jt:ipaddr;
                 }
                 leaf stl-sr-ero-unnum-local-router-id {
                   type jt:ipaddr;
                 }
                 leaf stl-sr-ero-unnum-local-id {
                   type uint32;
                 }
                 leaf stl-sr-ero-unnum-remote-router-id {
                   type jt:ipaddr;
                 }
                 leaf stl-sr-ero-unnum-remote-id {
                   type uint32;
                 }
                 leaf stl-sr-ero-sid-type {
                   type string;
                 }
                 leaf stl-sr-ero-sid-value {
                   type uint32;
                 }
                 leaf stl-sr-ero-srv6-sid-value {
                   type jt:ipaddr;
                 }
                 leaf stl-sr-ero-micro-srv6-sid-value {
                   type jt:ipaddr;
                 }
                 leaf stl-sr-ero-sid-ttl {
                   type uint32;
                 }
                 leaf stl-sr-ero-sid-exp {
                   type uint32;
                 }
                 leaf stl-sr-ero-micro-srv6-sid-structure-bl {
                   type string;
                 }
                 leaf stl-sr-ero-micro-srv6-sid-structure-nl {
                   type string;
                 }
                 leaf stl-sr-ero-micro-srv6-sid-structure-fl {
                   type string;
                 }
                 leaf stl-sr-ero-micro-srv6-sid-structure-al {
                   type string;
                 }
                 leaf stl-sr-ero-micro-srv6-sid-endpoint-behavior {
                   type string;
                 }
               }
             }
           }
           container stpm-ret-segment-list {
             description
               "Spring traffic engineered performance measurement return 
               segment list info";
             container stl-sr-ero-list {
               leaf stl-sr-ero-num-eros-pm-ret-path {
                 type uint32;
               }
               leaf stl-sr-ero-num-eros {
                 type uint32;
               }
               leaf stl-sr-ero-num-eros-pm-path {
                 type uint32;
               }
               list stl-sr-ero {
                 key "stl-sr-ero-index";
                 leaf stl-sr-ero-index {
                   type uint32;
                 }
                 leaf stl-sr-ero-hop-type {
                   type string;
                 }
                 leaf stl-sr-ero-nai-type {
                   type string;
                 }
                 leaf stl-sr-ero-ip-node-id {
                   type jt:ipaddr;
                 }
                 leaf stl-sr-ero-local-intf-id {
                   type jt:ipaddr;
                 }
                 leaf stl-sr-ero-remote-intf-id {
                   type jt:ipaddr;
                 }
                 leaf stl-sr-ero-unnum-local-router-id {
                   type jt:ipaddr;
                 }
                 leaf stl-sr-ero-unnum-local-id {
                   type uint32;
                 }
                 leaf stl-sr-ero-unnum-remote-router-id {
                   type jt:ipaddr;
                 }
                 leaf stl-sr-ero-unnum-remote-id {
                   type uint32;
                 }
                 leaf stl-sr-ero-sid-type {
                   type string;
                 }
                 leaf stl-sr-ero-sid-value {
                   type uint32;
                 }
                 leaf stl-sr-ero-srv6-sid-value {
                   type jt:ipaddr;
                 }
                 leaf stl-sr-ero-micro-srv6-sid-value {
                   type jt:ipaddr;
                 }
                 leaf stl-sr-ero-sid-ttl {
                   type uint32;
                 }
                 leaf stl-sr-ero-sid-exp {
                   type uint32;
                 }
                 leaf stl-sr-ero-micro-srv6-sid-structure-bl {
                   type string;
                 }
                 leaf stl-sr-ero-micro-srv6-sid-structure-nl {
                   type string;
                 }
                 leaf stl-sr-ero-micro-srv6-sid-structure-fl {
                   type string;
                 }
                 leaf stl-sr-ero-micro-srv6-sid-structure-al {
                   type string;
                 }
                 leaf stl-sr-ero-micro-srv6-sid-endpoint-behavior {
                   type string;
                 }
               }
             }
           }
           container stpm-path-measurement-info {
             description
               "Spring traffic engineered performance measurement data";
             leaf stpm-path-session-state {
               type string;
             }
             leaf stpm-path-session-id {
               type uint32;
             }
             leaf stpm-path-session-last-changed {
               type string;
             }
             leaf stpm-path-session-avg-delay {
               type uint32;
             }
             leaf stpm-path-session-max-delay {
               type uint32;
             }
             leaf stpm-path-session-min-delay {
               type uint32;
             }
             leaf stpm-path-session-delay-variance {
               type uint32;
             }
             leaf stpm-path-session-twamp-owner {
               type string;
             }
             leaf stpm-path-session-twamp-testname {
               type string;
             }
             leaf stpm-path-session-state-transitions {
               type uint32;
             }
             leaf stpm-path-session-result-updates {
               type uint32;
             }
             leaf stpm-path-session-error {
               type string;
             }
           }
           container stpm-path-measurement-history-info {
             description
               "Spring traffic engineered performance measurement history";
             leaf stpm-max-history-transactions {
               type uint32;
             }
             list stpm-path-measurement-history-entry {
               leaf stpm-history-timestamp {
                 type string;
               }
               leaf stpm-history-session-id {
                 type uint32;
               }
               leaf stpm-history-string {
                 type string;
               }
             }
           }
         }
       }
     }
     container spring-te-perf-measurement-path-counts {
       leaf stpmpc-total-paths {
         type uint32;
       }
       leaf stpmpc-active-paths {
         type uint32;
       }
       leaf stpmpc-failed-paths {
         type uint32;
       }
       leaf stpmpc-idle-paths {
         type uint32;
       }
     }
     container spring-te-perf-measurement-debug-info {
       leaf spring-te-perf-measurement-debug-details {
         type string;
       }
     }
   }
   grouping spring-te-pm-session-information-block {
     list spring-te-pm-session {
       key "stpms-session-id";
       description
         "Spring traffic engineered performance measurement session info";
       leaf stpms-session-id {
         type uint32;
       }
       leaf stpms-session-state {
         type string;
       }
       leaf stpms-avg-delay {
         type uint32;
       }
       leaf stpms-max-delay {
         type uint32;
       }
       leaf stpms-min-delay {
         type uint32;
       }
       leaf stpms-delay-variance {
         type uint32;
       }
       leaf stpms-last-changed {
         type string;
       }
       leaf stpms-twamp-owner {
         type string;
       }
       leaf stpms-twamp-owner-id {
         type uint32;
       }
       leaf stpms-twamp-testname {
         type string;
       }
       leaf stpms-twamp-test-id {
         type uint32;
       }
       leaf stpms-state-transitions {
         type uint32;
       }
       leaf stpms-result-updates {
         type uint32;
       }
       container stpms-session-info {
         leaf stpms-src {
           type jt:ipaddr;
         }
         leaf stpms-dst {
           type jt:ipaddr;
         }
         leaf stpms-forward-type {
           type string;
         }
         list stpms-sr-ero-list {
           key "stpms-sr-ero-list-type";
           leaf stpms-sr-ero-list-type {
             type string;
           }
           leaf stpms-sr-ero-num-eros {
             type uint32;
           }
           list stpms-sr-ero {
             key "stpms-sr-ero-index";
             leaf stpms-sr-ero-index {
               type uint32;
             }
             leaf stpms-sr-ero-sid-value {
               type uint32;
             }
             leaf stpms-sr-ero-srv6-sid-value {
               type jt:ipaddr;
             }
             leaf stpms-sr-ero-sid-ttl {
               type uint32;
             }
             leaf stpms-sr-ero-sid-exp {
               type uint32;
             }
           }
         }
       }
       container stpms-effective-parameters {
         leaf stpms-probe-interval {
           type uint32;
         }
         leaf stpms-probe-count {
           type uint32;
         }
         leaf stpms-periodic-interval {
           type uint32;
         }
         leaf stpms-periodic-threshold {
           type uint32;
         }
         leaf stpms-accelerated {
           type string;
         }
         leaf stpms-accelerated-threshold {
           type uint32;
         }
       }
       container stpms-ref-lsps {
         leaf-list stpms-ref-lsp {
           type string;
         }
       }
     }
     container spring-te-pm-session-counts {
       leaf stpmsc-total-sessions {
         type uint32;
       }
       leaf stpmsc-active-sessions {
         type uint32;
       }
       leaf stpmsc-failed-sessions {
         type uint32;
       }
       leaf stpmsc-idle-sessions {
         type uint32;
       }
     }
   }
 }
