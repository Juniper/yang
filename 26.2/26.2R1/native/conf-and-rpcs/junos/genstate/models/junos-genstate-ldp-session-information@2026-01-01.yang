module junos-genstate-ldp-session-information {
   yang-version 1;
   namespace "http://yang.juniper.net/junos/genstate/ldp-session-information";
   prefix jglsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for ldp-session-information.

      Copyright (c) 2026 Juniper Networks, Inc.
      All rights reserved.";

   revision 2026-01-01 {
     description "Junos: 26.2R1.7";
   }

   grouping ldp-session-information-top {
     description
       "Top-level grouping";
     container ldp-session-information {
       description
         "Top-level container";
       list ldp-session {
         key "ldp-neighbor-address";
         leaf ldp-neighbor-address {
           type jt:ipaddr;
         }
         leaf ldp-session-state {
           type string;
         }
         leaf ldp-connection-state {
           type string;
         }
         leaf ldp-remaining-time {
           type int32;
         }
         leaf ldp-session-adv-mode {
           type string;
         }
         leaf ldp-session-id {
           type string;
         }
         leaf ldp-retry-time {
           type int32;
         }
         leaf ldp-keepalive-time {
           type int32;
         }
         leaf ldp-session-role {
           type string;
         }
         leaf ldp-session-max-pdu {
           type int32;
         }
         leaf ldp-holdtime {
           type int32;
         }
         leaf ldp-neighbor-count {
           type int32;
         }
         leaf ldp-keepalive-interval {
           type int32;
         }
         leaf ldp-retry-interval {
           type int32;
         }
         leaf ldp-local-address {
           type jt:ipaddr;
         }
         leaf ldp-remote-address {
           type jt:ipaddr;
         }
         leaf ldp-up-time {
           type string;
         }
         leaf ldp-last-down-time {
           type int32;
         }
         leaf ldp-down-reason {
           type string;
         }
         leaf ldp-session-flap-count {
           type uint32;
           description
             "Number of times the LDP session has gone down and then come 
             back up";
         }
         leaf ldp-session-deleted {
           type empty;
         }
         leaf ldp-session-close-pending {
           type empty;
         }
         leaf ldp-session-queue-depth {
           type int32;
         }
         leaf ldp-session-read-pending {
           type empty;
         }
         leaf ldp-session-write-pending {
           type empty;
         }
         leaf ldp-session-receive-buffer-bytes {
           type int32;
         }
         leaf ldp-session-transmit-buffer-bytes {
           type int32;
         }
         leaf ldp-session-no-connection {
           type empty;
         }
         leaf ldp-session-authentication {
           type string;
         }
         leaf ldp-graceful-restart-state {
           type string;
         }
         leaf ldp-restart-complete-time {
           type int32;
         }
         leaf ldp-helper-mode-state {
           type string;
           description
             "Helping neighbor during graceful restart";
         }
         leaf ldp-helper-mode-time {
           type int32;
           description
             "Time left for session re-establishment or label recovery";
         }
         leaf ldp-graceful-restart-local {
           type string;
         }
         leaf ldp-local-helper-mode {
           type string;
         }
         leaf ldp-local-reconnect-time {
           type int32;
         }
         leaf ldp-graceful-restart-remote {
           type string;
         }
         leaf ldp-remote-helper-mode {
           type string;
         }
         leaf ldp-remote-reconnect-time {
           type int32;
         }
         leaf ldp-local-maximum-reconnect {
           type int32;
         }
         leaf ldp-local-maximum-recovery {
           type int32;
         }
         leaf ldp-local-label-adv-mode {
           type string;
         }
         leaf ldp-remote-label-adv-mode {
           type string;
         }
         leaf ldp-neg-label-adv-mode {
           type string;
         }
         leaf ldp-mtu-discovery {
           type string;
           description
             "Use LDP mtu discovery";
         }
         leaf ldp-label-request-status-code {
           type string;
           description
             "Status of label request from downstream session";
         }
         leaf ldp-session-nsr-state {
           type string;
           description
             "Synchronization state of nonstop routing for the session";
         }
         container ldp-neighbor-types {
           description
             "LDP neighbor types";
           leaf-list ldp-neighbor-type {
             type string;
             description
               "LDP neighbor type";
           }
         }
         container ldp-session-capabilities-advertised {
           description
             "Capabilities advertised to peer";
           leaf-list ldp-capability {
             type string;
             description
               "LDP capability";
           }
         }
         container ldp-session-capabilities-received {
           description
             "Capabilities received from peer";
           leaf-list ldp-capability {
             type string;
             description
               "LDP capability";
           }
         }
         container ldp-session-protection {
           description
             "LDP session protection information";
           leaf ldp-session-protection-state {
             type string;
             description
               "LDP session protection state";
           }
           leaf ldp-session-protection-remaining-time {
             type int32;
             description
               "Time after which session protection will cease to be active";
           }
         }
         container ldp-session-flags {
           description
             "LDP session flags";
           leaf-list ldp-session-flag {
             type string;
             description
               "LDP session flag";
           }
         }
         container ldp-session-address {
           leaf interface-name {
             type string;
             description
               "Name of interface";
           }
           leaf-list interface-address {
             type jt:ipaddr;
           }
           leaf ldp-session-address-stale {
             type empty;
           }
         }
         list ldp-session-statistics {
           key "ldp-message-type";
           leaf ldp-message-type {
             type string;
           }
           leaf ldp-messages-sent {
             type uint32;
           }
           leaf ldp-messages-received {
             type uint32;
           }
           leaf ldp-messages-sent-5seconds {
             type uint32;
           }
           leaf ldp-messages-received-5seconds {
             type uint32;
           }
         }
       }
     }
   }
   augment "/jgs:genstate" {
     description
       "Adds ldp-session-information container to top-level genstate 
       container";
     uses ldp-session-information-top;
   }
 }
