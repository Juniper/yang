module junos-genstate-bgp-fabric-advertise {
   yang-version 1;
   namespace "http://yang.juniper.net/junos/genstate/bgp-fabric-advertise";
   prefix jgbfa;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for bgp-fabric-advertise.

      Copyright (c) 2026 Juniper Networks, Inc.
      All rights reserved.";

   revision 2026-01-01 {
     description "Junos: 26.2R1.7";
   }

   grouping bgp-fabric-advertise-top {
     description
       "Top-level grouping";
     container bgp-fabric-advertise {
       description
         "BGP fabric advertise routes";
       container fabric-advertise-route {
         description
           "One fabric advertie route";
         leaf rt-destination {
           type string;
           description
             "Route prefixes awaiting ACK";
         }
         leaf rt-prefix-length {
           type string;
         }
         leaf rt-color {
           type string;
         }
         leaf rt-color-community {
           type string;
         }
         leaf rt-backup-color {
           type string;
         }
         leaf rt-backup-color-community {
           type string;
         }
       }
     }
   }
   augment "/jgs:genstate" {
     description
       "Adds bgp-fabric-advertise container to top-level genstate container";
     uses bgp-fabric-advertise-top;
   }
 }
