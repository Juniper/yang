module junos-genstate-mpls-admin-group-information {
   yang-version 1;
   namespace "http://yang.juniper.net/junos/genstate/mpls-admin-group-information";
   prefix jgmagi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for mpls-admin-group-information.

      Copyright (c) 2026 Juniper Networks, Inc.
      All rights reserved.";

   revision 2026-01-01 {
     description "Junos: 26.2R1.7";
   }

   grouping mpls-admin-group-information-top {
     description
       "Top-level grouping";
     container mpls-admin-group-information {
       description
         "Top-level container";
       list mpls-admin-group {
         key "admin-group-name";
         leaf admin-group-name {
           type string;
           description
             "Name of the admin group";
         }
         leaf index {
           type int32;
         }
       }
     }
   }
   augment "/jgs:genstate" {
     description
       "Adds mpls-admin-group-information container to top-level genstate 
       container";
     uses mpls-admin-group-information-top;
   }
 }
