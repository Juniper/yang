module junos-genstate-multicast-scope-information {
   yang-version 1;
   namespace "http://yang.juniper.net/junos/genstate/multicast-scope-information";
   prefix jgmsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-scope-information.

      Copyright (c) 2026 Juniper Networks, Inc.
      All rights reserved.";

   revision 2026-01-01 {
     description "Junos: 26.2R1.7";
   }

   grouping multicast-scope-information-top {
     description
       "Top-level grouping";
     container multicast-scope-information {
       description
         "Top-level container";
       list multicast-scope-policy-interfaces {
         key "instance-name";
         list multicast-scope-policy-interface {
           key "interface-name";
           leaf interface-name {
             type string;
             description
               "Name of interface";
           }
           leaf scope-rejects {
             type uint32;
             description
               "Number of rejects in multicast scope";
           }
         }
         leaf instance-name {
           type string;
         }
         leaf address-family {
           type string;
         }
       }
       list multicast-scope {
         key "scope-name interface-name";
         description
           "Multicast scope to match";
         leaf scope-name {
           type string;
           description
             "Name of multicast scope";
         }
         leaf address-prefix {
           type jt:ipaddr;
         }
         leaf interface-name {
           type string;
           description
             "Name of interface";
         }
         leaf scope-state {
           type string;
         }
         leaf scope-rejects {
           type uint32;
           description
             "Number of rejects in multicast scope";
         }
       }
       leaf multicast-scope-policy {
         type string;
       }
     }
   }
   augment "/jgs:genstate" {
     description
       "Adds multicast-scope-information container to top-level genstate 
       container";
     uses multicast-scope-information-top;
   }
 }
