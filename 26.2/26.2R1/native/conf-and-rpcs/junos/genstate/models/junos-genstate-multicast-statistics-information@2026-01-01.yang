module junos-genstate-multicast-statistics-information {
   yang-version 1;
   namespace "http://yang.juniper.net/junos/genstate/multicast-statistics-information";
   prefix jgmsi;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for multicast-statistics-information.

      Copyright (c) 2026 Juniper Networks, Inc.
      All rights reserved.";

   revision 2026-01-01 {
     description "Junos: 26.2R1.7";
   }

   grouping multicast-statistics-information-top {
     description
       "Top-level grouping";
     container multicast-statistics-information {
       description
         "Top-level container";
       list multicast-statistics {
         key "instance-name address-family";
         leaf instance-name {
           type string;
         }
         leaf address-family {
           type string;
         }
         leaf mc-resolves-no-mc-interface {
           type uint32;
           description
             "Number of resolve requests on non-multicast interfaces";
         }
         leaf mc-global-resolves-no-route {
           type uint32;
           description
             "Number of resolve requests with no route to source";
         }
         leaf mc-notifies-no-mc-interface {
           type uint32;
           description
             "Number of routing notifications on non-multicast interfaces";
         }
         leaf mc-notifies-no-route {
           type uint32;
           description
             "Number of routing notifications with no route to source";
         }
         leaf mc-mismatches-no-mc-interface {
           type uint32;
           description
             "Number of interface mismatches on non-multicast interfaces";
         }
         leaf mc-groups-no-mc-interface {
           type uint32;
           description
             "Number of group memberships on non-multicast interfaces";
         }
         list mc-stats-interface {
           key "interface-name";
           leaf interface-name {
             type string;
             description
               "Name of interface";
           }
           leaf protocol-name {
             type string;
           }
           leaf mc-mismatch-errors {
             type uint32;
             description
               "Number of interface mismatch errors";
           }
           leaf mc-mismatches {
             type uint32;
             description
               "Number of interface mismatches";
           }
           leaf mc-mismatches-no-route {
             type uint32;
             description
               "Number of interface mismatches due to no route to source";
           }
           leaf mc-resolves {
             type uint32;
             description
               "Number of resolve requests";
           }
           leaf mc-routing-notifies {
             type uint32;
             description
               "Number of routing notifications";
           }
           leaf mc-resolves-no-route {
             type uint32;
             description
               "Number of resolve requests with no route to source";
           }
           leaf mc-resolve-errors {
             type uint32;
             description
               "Number of resolve errors";
           }
           leaf mc-resolves-filtered {
             type uint32;
             description
               "Number of resolve requests filtered by policy";
           }
           leaf mc-routing-notifies-filtered {
             type uint32;
             description
               "Number of routing notifications filtered by policy";
           }
           leaf mc-input-kbytes {
             type uint64;
             description
               "Number of input kilobytes";
           }
           leaf mc-input-packets {
             type uint64;
             description
               "Number of input packets";
           }
           leaf mc-output-kbytes {
             type uint64;
             description
               "Number of output kilobytes";
           }
           leaf mc-output-packets {
             type uint64;
             description
               "Number of output packets";
           }
           list mc-stats-interface-p2mp-nbr {
             key "mc-p2mp-nbr-address";
             leaf mc-p2mp-nbr-address {
               type jt:ipaddr;
               description
                 "P2MP Neighbor address";
             }
             leaf mc-p2mp-mismatch-errors {
               type uint32;
               description
                 "Number of interface mismatch errors";
             }
             leaf mc-p2mp-mismatches {
               type uint32;
               description
                 "Number of interface mismatches";
             }
             leaf mc-p2mp-mismatches-no-route {
               type uint32;
               description
                 "Number of interface mismatches due to no route to source";
             }
             leaf mc-p2mp-resolves {
               type uint32;
               description
                 "Number of resolve requests";
             }
             leaf mc-p2mp-routing-notifies {
               type uint32;
               description
                 "Number of routing notifications";
             }
             leaf mc-p2mp-resolves-no-route {
               type uint32;
               description
                 "Number of resolve requests with no route to source";
             }
             leaf mc-p2mp-resolve-errors {
               type uint32;
               description
                 "Number of resolve errors";
             }
             leaf mc-p2mp-resolves-filtered {
               type uint32;
               description
                 "Number of resolve requests filtered by policy";
             }
             leaf mc-p2mp-routing-notifies-filtered {
               type uint32;
               description
                 "Number of routing notifications filtered by policy";
             }
             leaf mc-p2mp-input-kbytes {
               type uint64;
               description
                 "Number of input kilobytes";
             }
             leaf mc-p2mp-input-packets {
               type uint64;
               description
                 "Number of input packets";
             }
             leaf mc-p2mp-output-kbytes {
               type uint64;
               description
                 "Number of output kilobytes";
             }
             leaf mc-p2mp-output-packets {
               type uint64;
               description
                 "Number of output packets";
             }
             leaf protocol-name {
               type string;
             }
           }
         }
       }
     }
   }
   augment "/jgs:genstate" {
     description
       "Adds multicast-statistics-information container to top-level 
       genstate container";
     uses multicast-statistics-information-top;
   }
 }
