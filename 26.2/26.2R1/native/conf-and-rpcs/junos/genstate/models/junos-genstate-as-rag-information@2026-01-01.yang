module junos-genstate-as-rag-information {
   yang-version 1;
   namespace "http://yang.juniper.net/junos/genstate/as-rag-information";
   prefix jgari;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for as-rag-information.

      Copyright (c) 2026 Juniper Networks, Inc.
      All rights reserved.";

   revision 2026-01-01 {
     description "Junos: 26.2R1.7";
   }

   grouping as-rag-information-top {
     description
       "Top-level grouping";
     container as-rag-information {
       description
         "Information about Router Advertisement Guard";
       container rag-summary {
         list rag-entry {
           key "ifd-name";
           leaf ifd-name {
             type string;
             description
               "Interface name on which DAI stat collected";
           }
           leaf packets {
             type uint64;
           }
           leaf pass {
             type uint64;
           }
           leaf fail {
             type uint64;
           }
         }
       }
     }
   }
   augment "/jgs:genstate" {
     description
       "Adds as-rag-information container to top-level genstate container";
     uses as-rag-information-top;
   }
 }
