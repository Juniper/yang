module junos-genstate-database-usage {
   yang-version 1;
   namespace "http://yang.juniper.net/junos/genstate/database-usage";
   prefix jgdu;

   import junos-genstate {
     prefix jgs;
     revision-date 2026-01-01;
   }

   import junos-common-types {
     prefix jt;
     revision-date 2026-01-01;
   }

   organization
     "Juniper Networks, Inc.";

   contact
     "Juniper Networks, Inc.

      1133 Innovation Way
      Sunnyvale, CA 94089

      +1 888 314-5822

      E-mail: yang-support@juniper.net";

   description
      "Junos genstate Yang module for database-usage.

      Copyright (c) 2026 Juniper Networks, Inc.
      All rights reserved.";

   revision 2026-01-01 {
     description "Junos: 26.2R1.7";
   }

   grouping database-usage-top {
     description
       "Top-level grouping";
     container database-usage {
       description
         "Show candidate database usage";
       leaf maximum-size {
         type string;
         description
           "Show maximum size of database";
       }
       leaf current-size {
         type string;
         description
           "Show current database size on disk";
       }
       leaf actual-usage {
         type string;
         description
           "Show actual database usage";
       }
       leaf available-space {
         type string;
         description
           "Show available database space";
       }
       leaf memory-allocator-used {
         type string;
         description
           "Show memory allocator used";
       }
       leaf external-fragmentation {
         type string;
         description
           "Show external fragmentation space of the database";
       }
       leaf internal-fragmentation {
         type string;
         description
           "Show internal fragmentation space of the database";
       }
       leaf total-pages-allocated {
         type string;
         description
           "Show total number of pages allocated";
       }
       leaf total-pages-freed {
         type string;
         description
           "Show total number of pages freed";
       }
       leaf total-pages-reused {
         type string;
         description
           "Show pages reused";
       }
       leaf curr-active-pages {
         type string;
         description
           "Show current active pages";
       }
       leaf curr-free-pages {
         type string;
         description
           "Show current free pages";
       }
     }
   }
   augment "/jgs:genstate" {
     description
       "Adds database-usage container to top-level genstate container";
     uses database-usage-top;
   }
 }
