/*
 * Copyright (c) 2026 Juniper Networks, Inc.
 * All rights reserved.
 */
 module junos-rpc-l2vpn {
   namespace "http://yang.juniper.net/junos/rpc/l2vpn";

   prefix l2vpn;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for l2vpn command(s)";

   revision 2026-01-01 {
     description "Junos: 26.2R1.7";
   }

   rpc get-l2vpn-connection-information {
     description "Show Layer 2 VPN connections information";
     junos:command "show l2vpn connections";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of Layer 2 VPN instance";
         default "all";
         type string;
       }
       leaf local-site {
         description "Name or ID of Layer 2 VPN local site";
         default "all";
         type string;
       }
       leaf remote-site {
         description "ID of Layer 2 VPN remote site";
         default "all";
         type string;
       }
       leaf state {
         junos:cli-feature "nokeyword";
         default "up-down";
         type enumeration {
           enum "down" {
             description "Display nonoperational connections";
           }
           enum "up" {
             description "Display operational connections";
           }
           enum "up-down" {
             description "Display both non- and operational connections (default)";
           }
         }
       }
       leaf level {
         junos:cli-feature "nokeyword";
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and circuit status (default)";
           }
           enum "summary" {
             description "Display summary output";
           }
         }
       }
     }
     output {
       choice output-tags {
         case actual-tag {
           container l2vpn-connection-information {
             uses l2vpn-connection-information-block;
           }
         }
         case multichassis-tag {
           container multi-routing-engine-results {
             list multi-routing-engine-item {
               leaf re-name {
                 type string;
               }
               choice output-tags {
                 case actual-tag {
                   container l2vpn-connection-information {
                     uses l2vpn-connection-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping l2vpn-connection-information-block {
     list instance {
       key "instance-name";
       description
         "Routing protocol instance";
       leaf instance-name {
         type string;
       }
       leaf instance-display-error {
         type string;
       }
       leaf edge-protection {
         type string;
       }
       leaf edge-protector {
         type string;
       }
       list reference-site {
         key "local-site-id vpls-id l2vpn-id";
         leaf automatic-site-name {
           type string;
           description
             "VPLS automatic site name";
         }
         leaf automatic-site-id-status {
           type string;
           description
             "VPLS automatic site identifier status";
         }
         leaf automatic-site-claim-id {
           type int32;
           description
             "Claim site identifier";
         }
         leaf automatic-site-collisions {
           type int32;
           description
             "Number of collisions";
         }
         leaf automatic-site-timer-status {
           type string;
           description
             "VPLS automatic site timer status";
         }
         leaf vpls-signaling-protocol-identifier {
           type string;
         }
         leaf local-site-id {
           type string;
         }
         leaf source-attachment-id {
           type string;
           description
             "Local source attachment identifier";
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         leaf target-attachment-id {
           type string;
           description
             "Remote target attachment identifier";
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list label-block {
           key "label-block-base";
           leaf-list label-block.heading {
             type string;
           }
           leaf label-block-base {
             type int32;
           }
           leaf label-block-offset {
             type int32;
           }
           leaf label-block-size {
             type int32;
           }
           leaf label-block-range {
             type int32;
           }
           leaf label-block-preference {
             type int32;
           }
           leaf label-block-status-vector {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container spe-info {
             leaf spe-info.heading {
               type string;
             }
             leaf local-ip-addr {
               type jt:ipaddr;
             }
             leaf remote-ip-addr {
               type jt:ipaddr;
             }
             leaf pw-status {
               type string;
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container automatic-site-timers {
           leaf automatic-site-timers.heading {
             type string;
           }
           leaf automatic-site-startup-wait-time {
             type string;
           }
           leaf automatic-site-new-site-wait-time {
             type string;
           }
           leaf automatic-site-collision-detect-time {
             type string;
           }
           leaf automatic-site-reclaim-wait-time {
             type string;
           }
         }
         container connections-summary {
           leaf vc-up-count {
             type int32;
           }
           leaf vc-down-count {
             type int32;
           }
         }
       }
       list ldp-vpls-reference-site {
         key "vpls-id";
         description
           "Information about LDP-VPLS";
         leaf vpls-signaling-protocol-identifier {
           type string;
         }
         leaf vpls-id {
           type int32;
           description
             "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         list mesh-group-interfaces {
           key "mesh-group-name";
           description
             "Information about all interfaces associated with a mesh-group";
           leaf mesh-group-name {
             type string;
             description
               "Name of mesh-group";
           }
           leaf mesh-group-state {
             type string;
             description
               "Mesh-group state";
           }
           leaf mesh-group-id {
             type int32;
             description
               "Mesh-group Identifier";
           }
           list interface {
             key "interface-name";
             description
               "Interface name or address";
             leaf interface-name {
               type string;
               description
                 "Name of interface";
             }
             leaf interface-description {
               type string;
             }
             leaf interface-flags-description {
               type string;
             }
             leaf interface-flags {
               type string;
             }
           }
         }
         list interface {
           key "interface-name";
           description
             "Interface name or address";
           leaf interface-name {
             type string;
             description
               "Name of interface";
           }
           leaf interface-id {
             type int32;
           }
           leaf interface-description {
             type string;
           }
           leaf interface-flags-description {
             type string;
           }
           leaf interface-flags {
             type string;
           }
         }
         list connection {
           key "connection-id";
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type string;
           }
           leaf remote-pw-status-code {
             type string;
           }
           leaf connection-protection {
             type string;
           }
           leaf mesh-group-name {
             type string;
             description
               "Name of mesh-group";
           }
           leaf vc-flow-label-transmit {
             type string;
           }
           leaf vc-flow-label-receive {
             type string;
           }
           leaf auto-sensed {
             type empty;
             description
               "Auto-sensed";
           }
           list local-interface {
             key "interface-name";
             leaf interface-name {
               type string;
               description
                 "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description
                 "Name of interface";
             }
             leaf interface-status {
               type string;
             }
             leaf interface-encapsulation {
               type string;
             }
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container vpls-rsvp-te-p2mp-lsp-information {
             description
               "Information about one or more VPLS RSVP-TE 
               point-to-multipoint LSPs";
             leaf vpls-ingress-p2mp-branch-lsp-name {
               type string;
               description
                 "Name of ingress point-to-multipoint branch LSP";
             }
             leaf vpls-ingress-p2mp-branch-lsp-state {
               type string;
               description
                 "State of ingress point-to-multipoint branch LSP";
             }
             leaf vpls-egress-p2mp-branch-lsp-name {
               type string;
               description
                 "Name of egress point-to-multipoint branch LSP";
             }
             leaf vpls-egress-p2mp-branch-lsp-state {
               type string;
               description
                 "State of egress point-to-multipoint branch LSP";
             }
           }
           container history {
             leaf history.category-heading {
               type string;
             }
             leaf history.heading {
               type string;
             }
             list history-element {
               key "log-time-stamp log-event";
               leaf log-time-stamp {
                 type string;
               }
               leaf log-event {
                 type string;
               }
               leaf changed-entity {
                 type string;
               }
             }
           }
         }
         list mesh-group-connection {
           key "mesh-group-name";
           description
             "Information about all vc-connections of a specific mesh-group";
           leaf mesh-group-name {
             type string;
             description
               "Name of mesh-group";
           }
           list connection {
             key "connection-id";
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type string;
             }
             leaf remote-pw-status-code {
               type string;
             }
             leaf connection-protection {
               type string;
             }
             leaf mesh-group-name {
               type string;
               description
                 "Name of mesh-group";
             }
             leaf vc-flow-label-transmit {
               type string;
             }
             leaf vc-flow-label-receive {
               type string;
             }
             leaf auto-sensed {
               type empty;
               description
                 "Auto-sensed";
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description
                   "Name of interface";
               }
               leaf interface-status {
                 type string;
               }
               leaf interface-encapsulation {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
         }
         container connections-summary {
           leaf vc-up-count {
             type int32;
           }
           leaf vc-down-count {
             type int32;
           }
         }
       }
       container vpls-protocol-state {
         leaf vpls-signaling-protocol-identifier {
           type string;
         }
         leaf num-local-interfaces {
           type int32;
         }
         leaf num-local-interfaces-up {
           type int32;
         }
         leaf irb-present {
           type string;
         }
         leaf mesh-group-count {
           type int32;
         }
         leaf mesh-group-up-count {
           type int32;
         }
         list mesh-group-interfaces {
           description
             "Information about all interfaces associated with a mesh-group";
           list interface {
             key "interface-name";
             description
               "Interface name or address";
             leaf interface-name {
               type string;
               description
                 "Name of interface";
             }
             leaf interface-flags {
               type string;
             }
           }
         }
         list interface {
           key "interface-name";
           description
             "Interface name or address";
           leaf interface-name {
             type string;
             description
               "Name of interface";
           }
           leaf interface-flags {
             type string;
           }
         }
         list mesh-group-connection {
           key "mesh-group-name";
           description
             "Information about all vc-connections of a specific mesh-group";
           leaf mesh-group-name {
             type string;
             description
               "Name of mesh-group";
           }
           list connection {
             leaf-list connection.heading {
               type string;
             }
             leaf remote-pe {
               type jt:ipaddr;
             }
             leaf l2vpn-local-site-id {
               type int32;
               description
                 "Local site identifier";
             }
             leaf l2vpn-remote-site-id {
               type int32;
               description
                 "Remote site identifier";
             }
             leaf connection-status {
               type string;
             }
             leaf last-change {
               type string;
             }
             leaf inbound-label {
               type string;
             }
             leaf outbound-label {
               type string;
             }
             list local-interface {
               key "interface-name";
               leaf interface-name {
                 type string;
                 description
                   "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container connection-bandwidth {
               description
                 "Bandwidth of a layer 2 connection";
               leaf connection-bandwidth.heading {
                 type string;
                 description
                   "Bandwidth of a layer 2 connection";
               }
               leaf bandwidth {
                 type string;
               }
               leaf class-type {
                 type int32;
               }
               leaf class-bandwidth {
                 type int32;
               }
             }
             container vpls-rsvp-te-p2mp-lsp-information {
               description
                 "Information about one or more VPLS RSVP-TE 
                 point-to-multipoint LSPs";
               leaf vpls-ingress-p2mp-branch-lsp-name {
                 type string;
                 description
                   "Name of ingress point-to-multipoint branch LSP";
               }
               leaf vpls-ingress-p2mp-branch-lsp-state {
                 type string;
                 description
                   "State of ingress point-to-multipoint branch LSP";
               }
               leaf vpls-egress-p2mp-branch-lsp-name {
                 type string;
                 description
                   "Name of egress point-to-multipoint branch LSP";
               }
               leaf vpls-egress-p2mp-branch-lsp-state {
                 type string;
                 description
                   "State of egress point-to-multipoint branch LSP";
               }
             }
             container history {
               leaf history.category-heading {
                 type string;
               }
               leaf history.heading {
                 type string;
               }
               list history-element {
                 key "log-time-stamp log-event";
                 leaf log-time-stamp {
                   type string;
                 }
                 leaf log-event {
                   type string;
                 }
                 leaf changed-entity {
                   type string;
                 }
               }
             }
           }
           container connections-summary {
             leaf vc-up-count {
               type int32;
             }
             leaf vc-down-count {
               type int32;
             }
           }
         }
         list reference-site {
           key "local-site-id vpls-id l2vpn-id";
           leaf automatic-site-name {
             type string;
             description
               "VPLS automatic site name";
           }
           leaf automatic-site-id-status {
             type string;
             description
               "VPLS automatic site identifier status";
           }
           leaf automatic-site-claim-id {
             type int32;
             description
               "Claim site identifier";
           }
           leaf automatic-site-collisions {
             type int32;
             description
               "Number of collisions";
           }
           leaf automatic-site-timer-status {
             type string;
             description
               "VPLS automatic site timer status";
           }
           leaf vpls-signaling-protocol-identifier {
             type string;
           }
           leaf local-site-id {
             type string;
           }
           leaf source-attachment-id {
             type string;
             description
               "Local source attachment identifier";
           }
           leaf vpls-id {
             type int32;
             description
               "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           leaf target-attachment-id {
             type string;
             description
               "Remote target attachment identifier";
           }
           list mesh-group-interfaces {
             key "mesh-group-name";
             description
               "Information about all interfaces associated with a 
               mesh-group";
             leaf mesh-group-name {
               type string;
               description
                 "Name of mesh-group";
             }
             leaf mesh-group-state {
               type string;
               description
                 "Mesh-group state";
             }
             leaf mesh-group-id {
               type int32;
               description
                 "Mesh-group Identifier";
             }
             list interface {
               key "interface-name";
               description
                 "Interface name or address";
               leaf interface-name {
                 type string;
                 description
                   "Name of interface";
               }
               leaf interface-description {
                 type string;
               }
               leaf interface-flags-description {
                 type string;
               }
               leaf interface-flags {
                 type string;
               }
             }
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           list connection {
             container history {
             }
           }
           list mesh-group-connection {
             description
               "Information about all vc-connections of a specific 
               mesh-group";
             list connection {
               container history {
               }
             }
           }
         }
       }
       container vpls-rsvp-te-ingress-p2mp-lsp {
         leaf vpls-ingress-p2mp-lsp-name {
           type string;
           description
             "Name of ingress point-to-multipoint LSP";
         }
         leaf vpls-rsvp-te-p2mp-flood-nexthop-id {
           type int32;
           description
             "Identifier for VPLS RSVP traffic-engineering ingress flood 
             next hop";
         }
       }
       container multihome {
         leaf multihome.heading {
           type string;
         }
         list multihome-site {
           key "multihome-site-name";
           leaf multihome-site-name {
             type string;
             description
               "Name of site";
           }
           leaf multihome-site-id {
             type int32;
             description
               "Site Identifier";
           }
           leaf multihome-site-preference {
             type int32;
             description
               "Site Preference";
           }
           leaf multihome-site-state {
             type string;
             description
               "Site state";
           }
           leaf multihome-num-interfaces {
             type int32;
           }
           leaf multihome-num-interfaces-up {
             type int32;
           }
           list interface {
             key "interface-name";
             description
               "Interface name or address";
             leaf interface-name {
               type string;
               description
                 "Name of interface";
             }
             leaf interface-id {
               type int32;
             }
             leaf interface-description {
               type string;
             }
             leaf interface-flags-description {
               type string;
             }
             leaf interface-flags {
               type string;
             }
           }
           container remote-advertisements {
             leaf remote-advertisements.heading {
               type string;
             }
             list remote-adv {
               key "remote-adv-addr";
               leaf remote-adv-addr {
                 type string;
               }
               leaf remote-adv-preference {
                 type int32;
                 description
                   "Remote PE preference";
               }
               leaf remote-adv-ctrl-flag {
                 type string;
                 description
                   "Remote PE Control flags";
               }
               leaf remote-adv-ctrl-flag-description {
                 type string;
                 description
                   "Control flags description";
               }
             }
           }
         }
       }
       container history {
         leaf history.category-heading {
           type string;
         }
         leaf history.heading {
           type string;
         }
         list history-element {
           key "log-time-stamp log-event";
           leaf log-time-stamp {
             type string;
           }
           leaf log-event {
             type string;
           }
           leaf changed-entity {
             type string;
           }
         }
       }
     }
   }
 }
