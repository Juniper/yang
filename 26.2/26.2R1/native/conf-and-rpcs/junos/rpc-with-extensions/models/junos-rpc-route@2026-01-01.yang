/*
 * Copyright (c) 2026 Juniper Networks, Inc.
 * All rights reserved.
 */
 module junos-rpc-route {
   namespace "http://yang.juniper.net/junos/rpc/route";

   prefix route;

   import junos-common-ddl-extensions {
     prefix junos;
     revision-date 2026-01-01;
   }

   import junos-common-types {
     prefix jt;
     revision-date 2026-01-01;
   }

   organization "Juniper Networks, Inc.";

   contact "yang-support@juniper.net";

   description "Junos RPC YANG module for route command(s)";

   revision 2026-01-01 {
     description "Junos: 26.2R1.7";
   }

   rpc get-route-information {
     description "Show routing table information";
     junos:command "show route";
     input {
       leaf label {
         description "Label of entry in MPLS routing table";
         type union {
           type uint32;
           type string {
             pattern "<.*>|$.*";
           }
         }
       }
       leaf ccc {
         description "Name of entry in MPLS table with a circuit cross-connect interface";
         type string;
       }
       container evpn-esi-value {
         leaf esi {
           description "Filter evpn routes for a particular ESI, except evpn MAC routes";
           junos:cli-feature "nokeyword";
           type string;
         }
       }
       container evpn-mac-address {
         leaf mac_address {
           description "Filter evpn mac routes for a particular MAC";
           junos:cli-feature "nokeyword";
           type jt:mac-addr;
         }
       }
       container evpn-ethernet-tag-id {
         leaf ethernet-tag {
           description "Filter evpn routes for a particular Ethernet Tag ID";
           junos:cli-feature "nokeyword";
           type union {
             type uint32;
             type string {
               pattern "<.*>|$.*";
             }
           }
         }
       }
       leaf rd-prefix {
         description "Route distinguisher with ip prefix (rd:prefix)";
         type string;
       }
       leaf label-switched-path {
         description "Name of LSP tunnel associated with entries";
         type string {
           length "1 .. 64";
         }
       }
       leaf static-label-switched-path {
         description "Name of static LSP tunnel associated with entries";
         type string {
           length "1 .. 64";
         }
       }
       leaf te-link-local-node-ip {
         description "Local node's IPv4 address in the traffic-engineering link";
         type string;
       }
       leaf te-link-local-node-iso {
         description "Local node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-remote-node-ip {
         description "Remote node's IPv4 address in the traffic-engineering link";
         type string;
       }
       leaf te-link-remote-node-iso {
         description "Remote node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-local-ip {
         description "Local IPv4 address of the traffic-engineering link";
         type jt:ipaddr;
       }
       leaf te-link-remote-ip {
         description "Remote IPv4 address of the traffic-engineering link";
         type jt:ipaddr;
       }
       leaf te-mt-id {
         description "Multi-Topology ID of the traffic-engineering NLRI";
         type union {
           type uint32;
           type string {
             pattern "<.*>|$.*";
           }
         }
       }
       leaf te-node-ip {
         description "IPv4 address of the traffic-engineering node";
         type string;
       }
       leaf te-node-iso {
         description "ISO circuit ID of the traffic-engineering node";
         type string {
           junos:posix-pattern "^([[:xdigit:]]{1,4}[.]){3}[[:xdigit:]]{1,2}$";
           junos:pattern-message "Address must be of the form aaaa.bbbb.cccc.dd";
         }
       }
       leaf te-instance-id {
         description "Instance ID of the traffic-engineering NLRI";
         type union {
           type uint32;
           type string {
             pattern "<.*>|$.*";
           }
         }
       }
       leaf te-ipv4-prefix-node-ip {
         description "Originator node's IPv4 address in the traffic-engineering prefix";
         type string;
       }
       leaf te-ipv4-prefix-node-iso {
         description "Originator node's ISO circuit ID in the traffic-engineering prefix";
         type string {
           junos:posix-pattern "^([[:xdigit:]]{1,4}[.]){3}[[:xdigit:]]{1,2}$";
           junos:pattern-message "Address must be of the form aaaa.bbbb.cccc.dd";
         }
       }
       leaf te-ipv4-prefix-ip {
         description "IPv4 address of the traffic-engineering prefix";
         type jt:ipaddr;
       }
       leaf te-ipv6-prefix-node-iso {
         description "Originator node's ISO circuit ID in the traffic-engineering IPv6 prefix";
         type string {
           junos:posix-pattern "^([[:xdigit:]]{1,4}[.]){3}[[:xdigit:]]{1,2}$";
           junos:pattern-message "Address must be of the form aaaa.bbbb.cccc.dd";
         }
       }
       leaf te-ipv6-prefix-ipv6-addr {
         description "IPv6 address of the traffic-engineering IPv6 prefix";
         type jt:ipv6addr;
       }
       leaf te-srv6-sid-node-iso {
         description "Originator node's ISO circuit ID in the traffic-engineering SRv6 END SID";
         type string {
           junos:posix-pattern "^([[:xdigit:]]{1,4}[.]){3}[[:xdigit:]]{1,2}$";
           junos:pattern-message "Address must be of the form aaaa.bbbb.cccc.dd";
         }
       }
       leaf te-srv6-sid-ipv6-addr {
         description "IPv6 address of the traffic-engineering SRv6 END SID";
         type jt:ipv6addr;
       }
       leaf te-policy-spring-te-color {
         description "Show SPRING TE policies matching given color";
         type union {
           type uint32;
           type string {
             pattern "<.*>|$.*";
           }
         }
       }
       leaf te-policy-spring-te-origin {
         description "Show SPRING TE policies matching given origin";
         type union {
           type uint32;
           type string {
             pattern "<.*>|$.*";
           }
         }
       }
       leaf te-policy-spring-te-endpoint {
         description "Show SPRING TE policies matching given endpoint";
         type jt:ipaddr;
       }
       leaf te-policy-spring-te-src-addr {
         description "Show SPRING TE policies matching given source address";
         type jt:ipaddr;
       }
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf destination {
         description "IP address and optional prefix length of destination";
         junos:cli-feature "nokeyword";
         type jt:ipprefix-optional;
       }
       leaf all {
         description "Show all entries, including hidden entries";
         type empty;
       }
       leaf level {
         junos:cli-feature "nokeyword";
         type enumeration {
           enum "terse" {
             description "Display terse output";
           }
           enum "brief" {
             description "Display brief output";
           }
           enum "detail" {
             description "Display detailed output";
           }
           enum "extensive" {
             description "Display extensive output";
           }
         }
       }
       leaf match {
         junos:cli-feature "nokeyword";
         type enumeration {
           enum "best" {
             description "Show longest matching route";
           }
           enum "exact" {
             description "Show routes that match exactly";
           }
           enum "range" {
             description "Show all entries in prefix range";
           }
           enum "covering-subnets" {
             description "Show all matching subnets";
           }
         }
       }
       leaf table {
         description "Name of routing table";
         type string;
       }
       leaf inactive-prefix {
         description "Show inactive route destinations";
         type empty;
       }
       leaf inactive-path {
         description "Show inactive paths";
         type empty;
       }
       leaf active-path {
         description "Show active paths";
         type empty;
       }
       leaf private {
         description "Show private table routes";
         type empty;
       }
       leaf damping {
         description "Show entries subjected to particular kind of route damping";
         type enumeration {
           enum "suppressed" {
             description "Entries suppressed due to route damping";
           }
           enum "history" {
             description "Entries that are withdrawn but have history";
           }
           enum "decayed" {
             description "Entries that are decayed but not suppressed";
           }
         }
       }
       container output {
         leaf interface {
           description "Name of interface";
           type union {
             type jt:interface-unit;
             type string {
               pattern "<.*>|$.*";
             }
           }
         }
         leaf address {
           description "Address of interface";
           type string;
         }
       }
       leaf next-hop {
         description "IP address of next hop that is destination for entries";
         type jt:ipaddr;
       }
       leaf source-gateway {
         description "IP address of source router for entries";
         type jt:ipaddr;
       }
       leaf protocol {
         description "Name of protocol that is source for entries";
         type enumeration {
           enum "aggregate" {
             description "Locally generated aggregate route";
           }
           enum "bgp" {
             description "Border Gateway Protocol";
           }
           enum "bier" {
             description "BIER Protocol";
           }
           enum "direct" {
             description "Directly connected routes";
           }
           enum "dvmrp" {
             description "Distance Vector Multicast Routing Protocol";
           }
           enum "evpn" {
             description "EVPN";
           }
           enum "isis" {
             description "Intermediate System-to-Intermediate System";
           }
           enum "esis" {
             description "End System-to-Intermediate System";
           }
           enum "ldp" {
             description "Label Distribution Protocol";
           }
           enum "local" {
             description "Local system addresses";
           }
           enum "ospf" {
             description "Open Shortest Path First";
           }
           enum "ospf2" {
             description "Open Shortest Path First Version 2";
           }
           enum "ospf3" {
             description "Open Shortest Path First Version 3";
           }
           enum "pim" {
             description "Protocol Independent Multicast";
           }
           enum "mvpn" {
             description "BGP-MVPN Protocol";
           }
           enum "rift" {
             description "Routing in Fat Trees Protocol";
           }
           enum "gribi" {
             description "GRIBI Protocol";
           }
           enum "bfd" {
             description "BFD Protocol";
           }
           enum "rip" {
             description "Routing Information Protocol";
           }
           enum "ripng" {
             description "Routing Information Protocol for IPv6";
           }
           enum "rsvp" {
             description "Resource Reservation Protocol";
           }
           enum "static" {
             description "Statically defined prefixes";
           }
           enum "arp" {
             description "Prefixes learned via ARP";
           }
           enum "frr" {
             description "Prefixes created by Host (Direct route) Fast reroute";
           }
           enum "l2-learned-host-routing" {
             description "Layer-2-learned host routing";
           }
           enum "mpls" {
             description "Multiprotocol Label Switching";
           }
           enum "ccc" {
             description "Circuit cross-connect";
           }
           enum "express-segments" {
             description "Express segments";
           }
           enum "msdp" {
             description "Multicast Source Discovery Protocol";
           }
           enum "vpn" {
             description "Layer 3 virtual private network";
           }
           enum "l2vpn" {
             description "Layer 2 virtual private network";
           }
           enum "l2circuit" {
             description "Layer 2 circuit";
           }
           enum "rtarget" {
             description "Local route target VPN membership";
           }
           enum "spring-te" {
             description "SPRING Traffic-Engineered";
           }
           enum "tunnel" {
             description "Dynamic tunnel";
           }
           enum "flow" {
             description "Locally defined flow route";
           }
           enum "access" {
             description "Access route";
           }
           enum "access-internal" {
             description "Access-internal route";
           }
           enum "anchor" {
             description "Anchor route";
           }
           enum "bgp-static" {
             description "BGP static route";
           }
           enum "multipath" {
             description "Locally generated Multipath route";
           }
           enum "vpls" {
             description "Virtual Private LAN Service";
           }
           enum "bgp-ls-epe" {
             description "BGP egress peering using BGP-LS";
           }
           enum "srv6" {
             description "Segment Routing IPv6 local route";
           }
           enum "rib-export" {
             description "RIB export route";
           }
         }
       }
       leaf advertising-protocol-name {
         description "Name of dynamic routing protocol";
         junos:cli-feature "nokeyword";
         type enumeration {
           enum "bgp" {
             description "Border Gateway Protocol";
           }
           enum "dvmrp" {
             description "Distance Vector Multicast Routing Protocol";
           }
           enum "pim" {
             description "Protocol Independent Multicast";
           }
           enum "rip" {
             description "Routing Information Protocol";
           }
           enum "ripng" {
             description "Routing Information Protocol for IPv6";
           }
           enum "msdp" {
             description "Multicast Source Discovery Protocol";
           }
         }
       }
       leaf neighbor {
         description "IP address of neighbor (local for RIP and RIPng)";
         junos:cli-feature "nokeyword";
         type jt:ipaddr-scoped;
       }
       leaf receive-protocol-name {
         description "Name of dynamic routing protocol";
         junos:cli-feature "nokeyword";
         type enumeration {
           enum "bgp" {
             description "Border Gateway Protocol";
           }
           enum "rip" {
             description "Routing Information Protocol";
           }
           enum "ripng" {
             description "Routing Information Protocol for IPv6";
           }
           enum "dvmrp" {
             description "Distance Vector Multicast Routing Protocol";
           }
           enum "pim" {
             description "Protocol Independent Multicast";
           }
           enum "msdp" {
             description "Multicast Source Discovery Protocol";
           }
         }
       }
       leaf peer {
         description "IP address of neighbor";
         junos:cli-feature "nokeyword";
         type jt:ipaddr-scoped;
       }
       leaf match-prefix {
         description "Regular expression to match formatted prefix";
         type string;
       }
       leaf aspath-regex {
         description "BGP AS path regular expression for entries to match";
         type string;
       }
       leaf-list community {
         ordered-by user;
         description "Identifier for community (can include wildcards)";
         type string;
       }
       leaf no-community {
         description "Show entries with no associated community";
         type empty;
       }
       leaf community-name {
         description "Name of configured community policy to match";
         type string;
       }
       leaf hidden {
         description "Show hidden entries";
         type empty;
       }
       leaf validation-state {
         description "Show entries with a given validation state";
         type enumeration {
           enum "unverified" {
             description "Unverified route validation state";
           }
           enum "unknown" {
             description "Unknown route validation state";
           }
           enum "valid" {
             description "Valid route validation state";
           }
           enum "invalid" {
             description "Invalid route validation state";
           }
         }
       }
       leaf expanded-nh {
         description "Show nexthops in expanded format";
         type empty;
       }
       leaf nh-detail {
         description "Show nexthops in new version";
         type empty;
       }
       leaf fib-expanded-nh {
         description "Show fib nexthops in expanded format";
         type empty;
       }
       leaf output-queue {
         description "BGP output-queue for advertising protocol";
         type enumeration {
           enum "priority-1" {
             description "BGP output queue priority 1";
           }
           enum "priority-2" {
             description "BGP output queue priority 2";
           }
           enum "priority-3" {
             description "BGP output queue priority 3";
           }
           enum "priority-4" {
             description "BGP output queue priority 4";
           }
           enum "priority-5" {
             description "BGP output queue priority 5";
           }
           enum "priority-6" {
             description "BGP output queue priority 6";
           }
           enum "priority-7" {
             description "BGP output queue priority 7";
           }
           enum "priority-8" {
             description "BGP output queue priority 8";
           }
           enum "priority-9" {
             description "BGP output queue priority 9";
           }
           enum "priority-10" {
             description "BGP output queue priority 10";
           }
           enum "priority-11" {
             description "BGP output queue priority 11";
           }
           enum "priority-12" {
             description "BGP output queue priority 12";
           }
           enum "priority-13" {
             description "BGP output queue priority 13";
           }
           enum "priority-14" {
             description "BGP output queue priority 14";
           }
           enum "priority-15" {
             description "BGP output queue priority 15";
           }
           enum "priority-16" {
             description "BGP output queue priority 16";
           }
           enum "expedited" {
             description "BGP output queue expedited";
           }
         }
       }
       leaf display-client-data {
         description "Show client details";
         type empty;
       }
       leaf bmp-state {
         description "Show BMP state";
         type empty;
       }
       leaf bmp-rm-name {
         junos:cli-feature "nokeyword";
         type enumeration {
           enum "rib-in-pre-policy" {
             description "BMP RIB-IN pre-policy";
           }
           enum "rib-in-post-policy" {
             description "BMP RIB-IN post-policy";
           }
           enum "local-rib" {
             description "BMP local RIB";
           }
           enum "rib-out-pre-policy" {
             description "BMP RIB-OUT pre-policy";
           }
           enum "rib-out-post-policy" {
             description "BMP RIB-OUT post-policy";
           }
         }
       }
       leaf bmp-station-name {
         description "Show information for a particular BMP station";
         type string;
       }
       leaf programmed {
         description "Show API-programmed routes";
         type empty;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-forwarding-table-information {
     description "Show entries in all forwarding tables";
     junos:command "show route forwarding-table";
     input {
       uses command-forwarding;
       leaf level {
         junos:cli-feature "nokeyword";
         type enumeration {
           enum "detail" {
             description "Display all routes";
           }
           enum "extensive" {
             description "Display extensive information about routes";
           }
         }
       }
       leaf multicast {
         description "Display multicast routes";
         type empty;
       }
       leaf family {
         description "Name of family";
         type enumeration {
           enum "inet" {
             description "IP version 4 (IPv4)";
           }
           enum "inet6" {
             description "IP version 6 (IPv6)";
           }
           enum "unix" {
             description "UNIX";
           }
           enum "iso" {
             description "International Standards Organization protocol";
           }
           enum "tnp" {
             description "Trivial Network Protocol";
           }
           enum "mpls" {
             description "Multiprotocol Label Switching";
           }
           enum "vpls" {
             description "Virtual private LAN service";
           }
           enum "bridge" {
             description "Bridge (Layer 2 switching)";
           }
           enum "evpn" {
             description "Ethernet Virtual Private LAN services";
           }
           enum "vlan-classification" {
             description "VLAN classification table";
           }
           enum "ethernet-switching" {
             description "Switch forwarding table";
           }
           enum "fibre-channel" {
             description "Fibre channel forwarding table";
           }
           enum "fmembers" {
             description "Fibre channel membership table";
           }
           enum "fabric-multicast" {
             description "Fabric multicast routing table";
           }
           enum "fabric-replication" {
             description "Fabric replication routing table";
           }
           enum "mcsnoop-inet" {
             description "Multicast Snooping INET";
           }
           enum "mcsnoop-inet6" {
             description "Multicast Snooping INET6";
           }
           enum "satellite-vpls" {
             description "Satellite VPLS";
           }
           enum "satellite-inet" {
             description "Multicast Satellite INET";
           }
           enum "satellite-inet6" {
             description "Multicast Satellite INET6";
           }
           enum "evpn-mcsnoop" {
             description "Multicast Snooping EVPN";
           }
           enum "evpn-mcsnoop-v6" {
             description "Multicast Snooping EVPN INET6";
           }
           enum "bier" {
             description "BIER multicast";
           }
           enum "l2xc" {
             description "L2XC CCC";
           }
         }
       }
       leaf vpn {
         description "Name of VPN instance";
         type string;
       }
       leaf table {
         description "Name of routing table";
         type string;
       }
       leaf interface-name {
         description "Interface name";
         type string;
       }
       leaf vlan {
         description "VLAN name";
         type string;
       }
       leaf bridge-domain {
         description "Name of bridging domain";
         type string;
       }
       leaf summary {
         description "Display count of routes instead of details";
         type empty;
       }
       leaf matching {
         description "IP prefix and length for entries to match";
         type string;
       }
       leaf destination {
         description "Destination prefix";
         type string;
       }
       leaf learning-vlan-id {
         description "Learning VLAN";
         type string;
       }
       leaf label {
         description "Label for entries to match";
         type union {
           type uint32;
           type string {
             pattern "<.*>|$.*";
           }
         }
       }
       leaf ccc {
         description "Circuit cross-connect interface name for entries to match";
         type union {
           type jt:interface-name;
           type string {
             pattern "<.*>|$.*";
           }
         }
       }
       leaf bfr-id {
         description "BFR ID: BIER prefix to match";
         type union {
           type string {
             pattern "<.*>|$.*";
           }
           type uint32 {
             range "1 .. 65535";
           }
         }
       }
       leaf all {
         description "Display all routing forwarding-tables";
         type empty;
       }
     }
     output {
       choice output-tags {
         case actual-tag {
           container forwarding-table-information {
             uses forwarding-table-information-block;
           }
         }
         case multichassis-tag {
           container multi-routing-engine-results {
             list multi-routing-engine-item {
               leaf re-name {
                 type string;
               }
               choice output-tags {
                 case actual-tag {
                   container forwarding-table-information {
                     uses forwarding-table-information-block;
                   }
                 }
               }
             }
           }
         }
       }
     }
   }
   rpc get-fib-localization-information {
     description "Show route localization information";
     junos:command "show route localization";
     input {
       uses command-forwarding;
       leaf detail {
         description "Show detailed output";
         type empty;
       }
     }
     output {
       choice output-tags {
         case actual-tag {
           container fib-localization-information {
             uses fib-localization-information-block;
           }
         }
         case multichassis-tag {
           container multi-routing-engine-results {
             list multi-routing-engine-item {
               leaf re-name {
                 type string;
               }
               choice output-tags {
                 case actual-tag {
                   container fib-localization-information {
                     uses fib-localization-information-block;
                   }
                 }
               }
             }
           }
         }
       }
     }
   }
   rpc get-vpn-localization-information {
     description "Show vpn route localization information";
     junos:command "show route vpn-localization";
     input {
       leaf vpn-name {
         description "Name of the vpn instance";
         type string;
       }
       leaf family {
         description "Name of family";
         type enumeration {
           enum "inet" {
             description "IP version 4 (IPv4)";
           }
           enum "inet6" {
             description "IP version 6 (IPv6)";
           }
         }
       }
       leaf level {
         junos:cli-feature "nokeyword";
         type enumeration {
           enum "terse" {
             description "Display terse output";
           }
           enum "brief" {
             description "Display brief output";
           }
           enum "detail" {
             description "Display detailed output";
           }
         }
       }
     }
     output {
       choice output-tags {
         case actual-tag {
           container vpn-localization-information {
             uses vpn-localization-information-block;
           }
         }
         case multichassis-tag {
           container multi-routing-engine-results {
             list multi-routing-engine-item {
               leaf re-name {
                 type string;
               }
               choice output-tags {
                 case actual-tag {
                   container vpn-localization-information {
                     uses vpn-localization-information-block;
                   }
                 }
               }
             }
           }
         }
       }
     }
   }
   rpc get-route-tracking-information {
     description "Show RPM route tracking information";
     junos:command "show route rpm-tracking";
     input {
       leaf owner {
         description "Name of owner";
         type string {
           length "1 .. 32";
         }
       }
       leaf test {
         description "Name of test";
         type string {
           length "1 .. 32";
         }
       }
       leaf destination {
         description "IP address and optional prefix length of destination";
         type jt:ipprefix-optional;
       }
     }
     output {
       choice output-tags {
         case actual-tag {
           container route-tracking-information {
             uses route-tracking-information-block;
           }
         }
         case multichassis-tag {
           container multi-routing-engine-results {
             list multi-routing-engine-item {
               leaf re-name {
                 type string;
               }
               choice output-tags {
                 case actual-tag {
                   container route-tracking-information {
                     uses route-tracking-information-block;
                   }
                 }
               }
             }
           }
         }
       }
     }
   }
   rpc get-service-mapping-information {
     description "Show routing Transport Class information";
     junos:command "show route transport-class";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       choice trans-class-choice {
         case name {
           leaf get-routing-transport-class-by-name {
             description "Transport class Name";
             type string;
           }
         }
         case color {
           leaf color {
             description "Transport class Color";
             type union {
               type uint32;
               type string {
                 pattern "<.*>|$.*";
               }
             }
           }
         }
         case color-only {
           leaf color-only {
             description "Transport class Color-Only";
             type empty;
           }
         }
         case all {
           leaf all {
             description "Show all transport classes";
             type empty;
           }
         }
       }
     }
     output {
       choice output-tags {
         case actual-tag {
           container service-mapping-information {
             uses service-mapping-information-block;
           }
         }
         case multichassis-tag {
           container multi-routing-engine-results {
             list multi-routing-engine-item {
               leaf re-name {
                 type string;
               }
               choice output-tags {
                 case actual-tag {
                   container service-mapping-information {
                     uses service-mapping-information-block;
                   }
                 }
               }
             }
           }
         }
       }
     }
   }
   rpc get-instance-information {
     description "Show routing instances information";
     junos:command "show route instance";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "summary" {
             description "Display summary output";
           }
           enum "brief" {
             description "Display brief output (default)";
           }
           enum "detail" {
             description "Display detailed output";
           }
           enum "extensive" {
             description "Display extensive output";
           }
         }
       }
       leaf instance-name {
         description "Particular instance name";
         junos:cli-feature "nokeyword";
         type string;
       }
       leaf table {
         description "Table name";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container instance-information {
             uses instance-information-block;
           }
         }
         case multichassis-tag {
           container multi-routing-engine-results {
             list multi-routing-engine-item {
               leaf re-name {
                 type string;
               }
               choice output-tags {
                 case actual-tag {
                   container instance-information {
                     uses instance-information-block;
                   }
                 }
               }
             }
           }
         }
       }
     }
   }
   rpc get-operational-routing-instance-information {
     description "Show operational routing instances";
     junos:command "show route instance operational";
     output {
       choice output-tags {
         case actual-tag {
           container operational-routing-instance-information {
             uses operational-routing-instance-information-block;
           }
         }
         case multichassis-tag {
           container multi-routing-engine-results {
             list multi-routing-engine-item {
               leaf re-name {
                 type string;
               }
               choice output-tags {
                 case actual-tag {
                   container operational-routing-instance-information {
                     uses operational-routing-instance-information-block;
                   }
                 }
               }
             }
           }
         }
       }
     }
   }
   rpc get-localize-routing-instance-information {
     description "Show instances localization mapping";
     junos:command "show route instance localize";
     output {
       choice output-tags {
         case output-tag {
           leaf output {
             type string;
           }
         }
         case actual-tag {
           anyxml localize-routing-instance-information;
         }
         case multichassis-tag {
           anyxml multi-routing-engine-results;
         }
       }
     }
   }
   rpc get-route-snooping-information {
     description "Show routes for multicast snooping";
     junos:command "show route snooping";
     input {
       leaf destination {
         description "IP address and optional prefix length of destination";
         junos:cli-feature "nokeyword";
         type jt:ipprefix-optional;
       }
       leaf all {
         description "Show all entries, including hidden entries";
         type empty;
       }
       leaf level {
         junos:cli-feature "nokeyword";
         type enumeration {
           enum "terse" {
             description "Display terse output";
           }
           enum "brief" {
             description "Display brief output";
           }
           enum "detail" {
             description "Display detailed output";
           }
           enum "extensive" {
             description "Display extensive output";
           }
         }
       }
       leaf match {
         junos:cli-feature "nokeyword";
         type enumeration {
           enum "best" {
             description "Show longest matching route";
           }
           enum "exact" {
             description "Show routes that match exactly";
           }
           enum "range" {
             description "Show all entries in prefix range";
           }
           enum "covering-subnets" {
             description "Show all matching subnets";
           }
         }
       }
       leaf table {
         description "Name of routing table";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-snooping-instance-information {
     description "Show routing instances information";
     junos:command "show route snooping instance";
     input {
       leaf verbosity_level {
         junos:cli-feature "nokeyword";
         default "brief";
         type enumeration {
           enum "summary" {
             description "Display summary output";
           }
           enum "brief" {
             description "Display brief output (default)";
           }
           enum "detail" {
             description "Display detailed output";
           }
           enum "extensive" {
             description "Display extensive output";
           }
         }
       }
       leaf snooping-instance-name {
         description "Particular snooping instance name";
         junos:cli-feature "nokeyword";
         type string;
       }
     }
     output {
       choice output-tags {
         case actual-tag {
           container instance-information {
             uses instance-information-block;
           }
         }
         case multichassis-tag {
           container multi-routing-engine-results {
             list multi-routing-engine-item {
               leaf re-name {
                 type string;
               }
               choice output-tags {
                 case actual-tag {
                   container instance-information {
                     uses instance-information-block;
                   }
                 }
               }
             }
           }
         }
       }
     }
   }
   rpc get-route-snooping-summary {
     description "Show routing table statistics";
     junos:command "show route snooping summary";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-summary-information {
             uses route-summary-information-block;
           }
         }
         case multichassis-tag {
           container multi-routing-engine-results {
             list multi-routing-engine-item {
               leaf re-name {
                 type string;
               }
               choice output-tags {
                 case actual-tag {
                   container route-summary-information {
                     uses route-summary-information-block;
                   }
                 }
               }
             }
           }
         }
       }
     }
   }
   rpc get-rtflow-dep-information {
     description "Show flow route validation tables";
     junos:command "show route flow validation";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
         }
       }
       leaf table {
         description "Name of unicast routing table";
         type string;
       }
       leaf destination {
         description "IP address and optional prefix length of destination";
         junos:cli-feature "nokeyword";
         type jt:ipprefix-optional;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container rtflow-dep-information {
             uses rtflow-dep-information-block;
           }
         }
         case multichassis-tag {
           container multi-routing-engine-results {
             list multi-routing-engine-item {
               leaf re-name {
                 type string;
               }
               choice output-tags {
                 case actual-tag {
                   container rtflow-dep-information {
                     uses rtflow-dep-information-block;
                   }
                 }
               }
             }
           }
         }
       }
     }
   }
   rpc get-route-resolution-information {
     description "Show next-hop resolution database";
     junos:command "show route resolution";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf prefix {
         description "IP prefix/length of destination";
         junos:cli-feature "nokeyword";
         type string;
       }
       leaf table {
         description "Name of resolving table";
         type string;
       }
       leaf index {
         description "Index of resolution tree";
         type union {
           type uint32;
           type string {
             pattern "<.*>|$.*";
           }
         }
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-resolution-information {
             uses route-resolution-information-block;
           }
         }
         case multichassis-tag {
           container multi-routing-engine-results {
             list multi-routing-engine-item {
               leaf re-name {
                 type string;
               }
               choice output-tags {
                 case actual-tag {
                   container route-resolution-information {
                     uses route-resolution-information-block;
                   }
                 }
               }
             }
           }
         }
       }
     }
   }
   rpc get-route-resolution-summary {
     description "Show summary of tree";
     junos:command "show route resolution summary";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container route-resolution-information {
             uses route-resolution-information-block;
           }
         }
         case multichassis-tag {
           container multi-routing-engine-results {
             list multi-routing-engine-item {
               leaf re-name {
                 type string;
               }
               choice output-tags {
                 case actual-tag {
                   container route-resolution-information {
                     uses route-resolution-information-block;
                   }
                 }
               }
             }
           }
         }
       }
     }
   }
   rpc get-route-resolution-unresolved-information {
     description "Show routes that could not be resolved";
     junos:command "show route resolution unresolved";
     input {
       leaf verbosity_level {
         junos:cli-feature "nokeyword";
         default "brief";
         type enumeration {
           enum "brief" {
             description "Display brief output (default)";
           }
           enum "detail" {
             description "Display detailed output";
           }
         }
       }
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container route-resolution-unresolved-information {
             uses route-resolution-unresolved-information-block;
           }
         }
         case multichassis-tag {
           container multi-routing-engine-results {
             list multi-routing-engine-item {
               leaf re-name {
                 type string;
               }
               choice output-tags {
                 case actual-tag {
                   container route-resolution-unresolved-information {
                     uses route-resolution-unresolved-information-block;
                   }
                 }
               }
             }
           }
         }
       }
     }
   }
   rpc get-route-resolution-scheme {
     description "Show custom resolution schemes for route next-hop resolution";
     junos:command "show route resolution scheme";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       choice res-scheme-choice {
         case name {
           leaf get-resolution-scheme-by-name {
             description "Resolution scheme Name";
             type string;
           }
         }
         case community {
           leaf get-resolution-scheme-by-map-comm {
             description "The mapping-community of resolution scheme";
             type string;
           }
         }
         case color-only {
           leaf color-only {
             description "Show Color-Only Resolution schemes";
             type empty;
           }
         }
         case best-effort {
           leaf best-effort {
             description "Show Best-Effort Resolution schemes";
             type empty;
           }
         }
         case all {
           leaf all {
             description "Show all Resolution schemes";
             type empty;
             mandatory true;
           }
         }
       }
     }
     output {
       choice output-tags {
         case actual-tag {
           container route-resolution-scheme-information {
             uses route-resolution-scheme-information-block;
           }
         }
         case multichassis-tag {
           container multi-routing-engine-results {
             list multi-routing-engine-item {
               leaf re-name {
                 type string;
               }
               choice output-tags {
                 case actual-tag {
                   container route-resolution-scheme-information {
                     uses route-resolution-scheme-information-block;
                   }
                 }
               }
             }
           }
         }
       }
     }
   }
   rpc get-route-resolution-list-nh-information {
     description "Show list nexthop binding between indirect nexthop and hekper";
     junos:command "show route resolution list-nh";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf protocol-next-hop {
         description "Indirect protocol next hop address";
         type jt:ipaddr;
       }
     }
     output {
       choice output-tags {
         case actual-tag {
           container route-resolution-list-nh-information {
             uses route-resolution-list-nh-information-block;
           }
         }
         case multichassis-tag {
           container multi-routing-engine-results {
             list multi-routing-engine-item {
               leaf re-name {
                 type string;
               }
               choice output-tags {
                 case actual-tag {
                   container route-resolution-list-nh-information {
                     uses route-resolution-list-nh-information-block;
                   }
                 }
               }
             }
           }
         }
       }
     }
   }
   rpc get-route-resolution-active-helpers {
     description "Show only those helper nodes upon which paths are resolving";
     junos:command "show route resolution active-helpers";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
           enum "extensive" {
             description "Display extensive output";
           }
         }
       }
       leaf index {
         description "Index of resolution tree";
         type union {
           type uint32;
           type string {
             pattern "<.*>|$.*";
           }
         }
       }
     }
     output {
       choice output-tags {
         case actual-tag {
           container route-resolution-active-helpers-information {
             uses route-resolution-active-helpers-information-block;
           }
         }
         case multichassis-tag {
           container multi-routing-engine-results {
             list multi-routing-engine-item {
               leaf re-name {
                 type string;
               }
               choice output-tags {
                 case actual-tag {
                   container route-resolution-active-helpers-information {
                     uses route-resolution-active-helpers-information-block;
                   }
                 }
               }
             }
           }
         }
       }
     }
   }
   rpc get-route-resolution-active-helpers-statistics {
     description "Re-resolve statistics of the helper node";
     junos:command "show route resolution active-helpers statistics";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf prefix {
         description "IP prefix/length of destination";
         junos:cli-feature "nokeyword";
         type string;
       }
     }
     output {
       choice output-tags {
         case actual-tag {
           container route-resolution-active-helpers-statistics {
             uses route-resolution-active-helpers-statistics-block;
           }
         }
         case multichassis-tag {
           container multi-routing-engine-results {
             list multi-routing-engine-item {
               leaf re-name {
                 type string;
               }
               choice output-tags {
                 case actual-tag {
                   container route-resolution-active-helpers-statistics {
                     uses route-resolution-active-helpers-statistics-block;
                   }
                 }
               }
             }
           }
         }
       }
     }
   }
   rpc get-route-resolution-loop-history {
     description "Show the resolution loop events";
     junos:command "show route resolution loop-history";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf index {
         description "Index of resolution tree";
         type union {
           type uint32;
           type string {
             pattern "<.*>|$.*";
           }
         }
       }
     }
     output {
       choice output-tags {
         case actual-tag {
           container route-resolution-loop-information {
             uses route-resolution-loop-information-block;
           }
         }
         case multichassis-tag {
           container multi-routing-engine-results {
             list multi-routing-engine-item {
               leaf re-name {
                 type string;
               }
               choice output-tags {
                 case actual-tag {
                   container route-resolution-loop-information {
                     uses route-resolution-loop-information-block;
                   }
                 }
               }
             }
           }
         }
       }
     }
   }
   rpc get-route-reresolution-history {
     description "Show the resolution history";
     junos:command "show route resolution re-resolution-history";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf index {
         description "Index of resolution tree";
         type union {
           type uint32;
           type string {
             pattern "<.*>|$.*";
           }
         }
       }
     }
     output {
       choice output-tags {
         case actual-tag {
           container route-reresolution-history-information {
             uses route-reresolution-history-information-block;
           }
         }
         case multichassis-tag {
           container multi-routing-engine-results {
             list multi-routing-engine-item {
               leaf re-name {
                 type string;
               }
               choice output-tags {
                 case actual-tag {
                   container route-reresolution-history-information {
                     uses route-reresolution-history-information-block;
                   }
                 }
               }
             }
           }
         }
       }
     }
   }
   rpc get-route-summary-information {
     description "Show routing table statistics";
     junos:command "show route summary";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf table {
         description "Name of routing table";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-summary-information {
             uses route-summary-information-block;
           }
         }
         case multichassis-tag {
           container multi-routing-engine-results {
             list multi-routing-engine-item {
               leaf re-name {
                 type string;
               }
               choice output-tags {
                 case actual-tag {
                   container route-summary-information {
                     uses route-summary-information-block;
                   }
                 }
               }
             }
           }
         }
       }
     }
   }
   rpc get-route-prefix-length-distribution {
     description "Display the prefix length count for a routing table";
     junos:command "show route prefix-length-distribution";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf table {
         description "Name of routing table";
         type string;
       }
     }
     output {
       choice output-tags {
         case actual-tag {
           container route-prefix-length-distribution {
             uses route-prefix-length-distribution-block;
           }
         }
         case multichassis-tag {
           container multi-routing-engine-results {
             list multi-routing-engine-item {
               leaf re-name {
                 type string;
               }
               choice output-tags {
                 case actual-tag {
                   container route-prefix-length-distribution {
                     uses route-prefix-length-distribution-block;
                   }
                 }
               }
             }
           }
         }
       }
     }
   }
   rpc get-rt-pfe-install-errors {
     description "Routes with pfe installation errors";
     junos:command "show route pfe-install-error";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf level {
         junos:cli-feature "nokeyword";
         default "brief";
         type enumeration {
           enum "brief" {
             description "Display brief output (default)";
           }
           enum "detail" {
             description "Display nh details";
           }
         }
       }
     }
     output {
       choice output-tags {
         case actual-tag {
           container rt-pfe-install-errors {
             uses rt-pfe-install-errors-block;
           }
         }
         case multichassis-tag {
           container multi-routing-engine-results {
             list multi-routing-engine-item {
               leaf re-name {
                 type string;
               }
               choice output-tags {
                 case actual-tag {
                   container rt-pfe-install-errors {
                     uses rt-pfe-install-errors-block;
                   }
                 }
               }
             }
           }
         }
       }
     }
   }
   rpc get-rib-origin-validation-statistics {
     description "Show RIB table specific validation state statistics";
     junos:command "show route validation-statistics";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf table {
         description "Name of routing table";
         type string;
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-route-record-information {
     description "Show route record details";
     junos:command "show route record";
     input {
       leaf summary {
         description "Show route record statistics";
         type empty;
         mandatory true;
       }
     }
     output {
       choice output-tags {
         case actual-tag {
           container route-record-information {
             uses route-record-information-block;
           }
         }
         case multichassis-tag {
           container multi-routing-engine-results {
             list multi-routing-engine-item {
               leaf re-name {
                 type string;
               }
               choice output-tags {
                 case actual-tag {
                   container route-record-information {
                     uses route-record-information-block;
                   }
                 }
               }
             }
           }
         }
       }
     }
   }
   rpc get-route-martians {
     description "Show martian networks";
     junos:command "show route martians";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf table {
         description "Name of routing table";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-route-cumulative {
     description "Show the cumulative routes in VRF table";
     junos:command "show route cumulative";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf vpn-family {
         type enumeration {
           enum "inet.0" {
             description "Display the inet.0 vrf instance";
           }
           enum "inet6.0" {
             description "Display the inet6.0 vrf instance";
           }
         }
         mandatory true;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-route-rib-groups {
     description "Show group of routing tables";
     junos:command "show route rib-groups";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-route-rib-exports {
     description "Show group of routing tables";
     junos:command "show route rib-exports";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
     }
     output {
       choice output-tags {
         case actual-tag {
           container route-information {
             uses route-information-block;
           }
         }
         case multichassis-tag {
           container multi-routing-engine-results {
             list multi-routing-engine-item {
               leaf re-name {
                 type string;
               }
               choice output-tags {
                 case actual-tag {
                   container route-information {
                     uses route-information-block;
                   }
                 }
               }
             }
           }
         }
       }
     }
   }
   rpc get-rtexport-table-information {
     description "Show instance export information";
     junos:command "show route export";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
         }
       }
       leaf table-name {
         description "Name of table";
         junos:cli-feature "nokeyword";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case actual-tag {
           container rtexport-table-information {
             uses rtexport-table-information-block;
           }
         }
         case multichassis-tag {
           container multi-routing-engine-results {
             list multi-routing-engine-item {
               leaf re-name {
                 type string;
               }
               choice output-tags {
                 case actual-tag {
                   container rtexport-table-information {
                     uses rtexport-table-information-block;
                   }
                 }
               }
             }
           }
         }
       }
     }
   }
   rpc get-rtexport-target-information {
     description "Show VPN routing and forwarding route target export information";
     junos:command "show route export vrf-target";
     input {
       leaf verbosity_level {
         junos:cli-feature "nokeyword";
         default "brief";
         type enumeration {
           enum "brief" {
             description "Display brief output (default)";
           }
           enum "detail" {
             description "Display detailed output";
           }
         }
       }
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf-list community {
         ordered-by user;
         description "Community to match (can include wildcards)";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case output-tag {
           leaf output {
             type string;
           }
         }
         case actual-tag {
           anyxml rtexport-target-information;
         }
         case multichassis-tag {
           anyxml multi-routing-engine-results;
         }
       }
     }
   }
   rpc get-rtexport-instance-information {
     description "Show instance configuration and runtime information";
     junos:command "show route export instance";
     input {
       leaf verbosity_level {
         junos:cli-feature "nokeyword";
         default "brief";
         type enumeration {
           enum "brief" {
             description "Display brief output (default)";
           }
           enum "detail" {
             description "Display detailed output";
           }
         }
       }
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf instance-name {
         description "Name of instance";
         junos:cli-feature "nokeyword";
         type string;
       }
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output-tags {
         case output-tag {
           leaf output {
             type string;
           }
         }
         case actual-tag {
           anyxml rtexport-instance-information;
         }
         case multichassis-tag {
           anyxml multi-routing-engine-results;
         }
       }
     }
   }
   rpc get-rt-ribexport-table-information {
     description "Show instance export information";
     junos:command "show route rib-export-group";
     input {
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf verbosity_level {
         junos:cli-feature "nokeyword";
         default "brief";
         type enumeration {
           enum "brief" {
             description "Display brief output (default)";
           }
           enum "detail" {
             description "Display detailed output";
           }
         }
       }
       leaf table-name {
         description "Name of table";
         junos:cli-feature "nokeyword";
         type string;
       }
     }
     output {
       choice output-tags {
         case actual-tag {
           container rt-ribexport-table-information {
             uses rt-ribexport-table-information-block;
           }
         }
         case multichassis-tag {
           container multi-routing-engine-results {
             list multi-routing-engine-item {
               leaf re-name {
                 type string;
               }
               choice output-tags {
                 case actual-tag {
                   container rt-ribexport-table-information {
                     uses rt-ribexport-table-information-block;
                   }
                 }
               }
             }
           }
         }
       }
     }
   }
   rpc get-rt-ribexport-instance-information {
     description "Show instance configuration and runtime information";
     junos:command "show route rib-export-group instance";
     input {
       leaf verbosity_level {
         junos:cli-feature "nokeyword";
         default "brief";
         type enumeration {
           enum "brief" {
             description "Display brief output (default)";
           }
           enum "detail" {
             description "Display detailed output";
           }
         }
       }
       choice daemon-select {
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf instance-name {
         description "Name of instance";
         junos:cli-feature "nokeyword";
         type string;
       }
     }
     output {
       choice output-tags {
         case actual-tag {
           container rt-ribexport-instance-information {
             uses rt-ribexport-instance-information-block;
           }
         }
         case multichassis-tag {
           container multi-routing-engine-results {
             list multi-routing-engine-item {
               leaf re-name {
                 type string;
               }
               choice output-tags {
                 case actual-tag {
                   container rt-ribexport-instance-information {
                     uses rt-ribexport-instance-information-block;
                   }
                 }
               }
             }
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping route-information-block {
     container ipv4-route-list {
       description
         "State of IPv4 route table";
       leaf-list ipv4-route-entry {
         type string;
       }
     }
     container ipv6-route-list {
       description
         "State of IPv6 route table";
       leaf-list ipv6-route-entry {
         type string;
       }
     }
     leaf as-number {
       type int32;
     }
     leaf router-id {
       type jt:ipaddr;
     }
     leaf maximum-ecmp {
       type int32;
     }
     leaf note-network-services-mode {
       type string;
     }
     list route-table {
       key "table-name";
       leaf table-name {
         type string;
         description
           "Unicast routing table";
       }
       leaf destination-count {
         type int32;
         description
           "Number of destinations in this rib";
       }
       leaf total-route-count {
         type int32;
       }
       leaf active-route-count {
         type int32;
         description
           "Active routes";
       }
       leaf holddown-route-count {
         type int32;
       }
       leaf hidden-route-count {
         type int32;
       }
       leaf restart-state {
         type string;
       }
       leaf family-prefix-max {
         type int32;
       }
       leaf family-prefix-threshold {
         type int32;
       }
       leaf family-prefix-label {
         type string;
       }
       leaf family-route-max {
         type int32;
       }
       leaf family-route-threshold {
         type int32;
       }
       leaf family-route-limit-label {
         type string;
       }
       leaf global-prefix-max {
         type int32;
       }
       leaf global-prefix-threshold {
         type int32;
       }
       leaf global-prefix-label {
         type string;
       }
       leaf global-route-max {
         type int32;
       }
       leaf global-route-threshold {
         type int32;
       }
       leaf global-route-limit-label {
         type string;
       }
       leaf prefix-max {
         type int32;
       }
       leaf prefix-threshold {
         type int32;
       }
       leaf prefix-label {
         type string;
       }
       leaf route-max {
         type int32;
       }
       leaf route-threshold {
         type int32;
       }
       leaf route-limit-label {
         type string;
       }
       list protocols {
         key "protocol-name";
         leaf protocol-name {
           type string;
         }
         leaf protocol-route-count {
           type int32;
           description
             "Total protocol routes";
         }
         leaf active-route-count {
           type int32;
           description
             "Active routes";
         }
       }
       list rt-prefix-dist {
         key "rt-prefix-length";
         leaf rt-prefix-length {
           type string;
         }
         leaf rt-prefix-count {
           type int32;
         }
       }
       list rt {
         key "rt-destination";
         leaf rt-destination {
           type string;
           description
             "Route prefixes awaiting ACK";
         }
         leaf rt-prefix-length {
           type string;
         }
         list rt-entry {
           leaf active-tag {
             type string;
             description
               "Visual indication of active state of this route entry";
           }
           leaf validation-state {
             type string;
             description
               "Validation-state of a route";
           }
           leaf protocol-name {
             type string;
           }
           leaf preference {
             type int32;
             description
               "Preference for the route";
           }
           leaf metric {
             type int32;
           }
           leaf metric2 {
             type int32;
           }
           leaf nh-type {
             type string;
             description
               "Special next hop: Reject, Blackhole, Receive, Multicast, 
               Local, or Unused";
           }
           leaf as-path {
             type string;
             description
               "Name of AS path regular expression (BGP only)";
           }
           leaf last-active {
             type empty;
             description
               "This route entry was the last active route entry";
           }
           leaf current-active {
             type empty;
             description
               "This route entry is currently active";
           }
           leaf bgp-rt-mult-nh-idx {
             type uint32;
             description
               "BGP multipath nexthop index";
           }
           leaf deleted {
             type empty;
           }
           leaf nh-erc-btid-id {
             type string;
             description
               "ERC Backtrace ID";
           }
           leaf nh-erc-btid-op {
             type string;
             description
               "ERC BTID Operation";
           }
           leaf nh-erc-btid-nreference {
             type int32;
             description
               "ERC Number of BTID References";
           }
           leaf nh-erc-btid-bt {
             type string;
             description
               "ERC BTID Backtrace ";
           }
           container route-record {
             leaf rt-recorded {
               type string;
             }
             leaf nh-address {
               type string;
               description
                 "Address of next hop";
             }
             leaf as-index {
               type int32;
             }
             leaf as-recorded {
               type string;
             }
             leaf com-index {
               type int32;
             }
             leaf com-recorded {
               type string;
             }
           }
           list route-data-dcf {
             key "trunk-id snmp-idx";
             leaf trunk-id {
               type int32;
               description
                 "Trunk Identifier associated with the LAG port";
             }
             leaf snmp-idx {
               type int32;
               description
                 "IFD SNMP index";
             }
             leaf ts {
               type int32;
               description
                 "Timestamp associated with the route";
             }
             leaf class-id {
               type int32;
               description
                 "Class identifier associated with the route";
             }
             leaf rt-flags {
               type string;
               description
                 "Flags associated with the route";
             }
             leaf rt-type {
               type string;
               description
                 "Route type associated with the route";
             }
             leaf rt-proto {
               type string;
               description
                 "Protocol associated with the route";
             }
             leaf rt-l2domain {
               type int32;
               description
                 "L2domain associated with the route";
             }
             leaf rt-mac-addr {
               type jt:mac-addr;
               description
                 "Mac address associated with the route";
             }
             list snpa {
               key "snpa-type";
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
             }
             leaf snpa-count {
               type int32;
               description
                 "Number of SNPAs in this route";
             }
             leaf snpa-length {
               type int32;
               description
                 "Total length of the SNPAs, in bytes";
             }
             container multicast-member-map-data {
               description
                 "Multicast member map";
               leaf multicast-root-hash {
                 type int32;
               }
               leaf multicast-core-hash {
                 type int32;
               }
               leaf multicast-edge-hash {
                 type int32;
               }
               leaf multicast-member-map {
                 type string;
               }
             }
             container layer3-multicast-data {
               description
                 "Layer3 multicast core key";
               leaf layer3-multicast-corekey {
                 type int32;
               }
             }
             container multicast-vsg-corekey-data {
               description
                 "Vsg multicast core key";
               leaf multicast-vsg-corekey-key {
                 type int32;
               }
               leaf multicast-vsg-corekey-len {
                 type int32;
               }
             }
           }
           container rtd-flow-dep {
             leaf flow-dep-state {
               type string;
             }
             leaf flow-origin {
               type jt:ipaddr;
               description
                 "Originator of the flow information";
             }
             leaf flow-next-as {
               type uint32;
               description
                 "Neighbor AS of the flow information";
             }
             container flow-ucast-rt {
               description
                 "Unicast route used for resolution";
               leaf flow-rtn-dest {
                 type jt:ipaddr;
                 description
                   "Destination address";
               }
               leaf flow-rtn-plen {
                 type int32;
                 description
                   "Prefix length";
               }
               leaf flow-rtn-state {
                 type string;
                 description
                   "Validation entry state";
               }
             }
           }
           container bgp-path-attributes {
             container attr-as-path {
               description
                 "AS Path Attribute";
               leaf attr-length {
                 type string;
               }
               leaf flags {
                 type string;
                 description
                   "Enabled trace flags";
               }
               leaf path-length {
                 type string;
               }
               leaf attr-value {
                 type string;
               }
             }
             container attr-as4-path {
               description
                 "4-byte AS Path Attribute";
               leaf attr-length {
                 type string;
               }
               leaf path-length {
                 type string;
               }
               leaf flags {
                 type string;
                 description
                   "Enabled trace flags";
               }
               leaf attr-value {
                 type string;
               }
             }
             container attr-as-path-effective {
               description
                 "Effective AS-Path Attribute";
               leaf attr-length {
                 type string;
               }
               leaf aspath-effective-string {
                 type string;
               }
               leaf path-length {
                 type string;
               }
               leaf attr-value {
                 type string;
               }
               leaf flags {
                 type string;
                 description
                   "Enabled trace flags";
               }
             }
             container attr-aggregator {
               description
                 "Aggregator Attribute";
               leaf attr-length {
                 type string;
               }
               leaf flags {
                 type string;
                 description
                   "Enabled trace flags";
               }
               leaf aggr-as-number {
                 type string;
               }
               leaf aggr-router-id {
                 type string;
               }
             }
             container attr-aggregator4 {
               description
                 "Aggregator4 Attribute";
               leaf attr-length {
                 type string;
               }
               leaf flags {
                 type string;
                 description
                   "Enabled trace flags";
               }
               leaf aggr-as-number {
                 type string;
               }
               leaf aggr-router-id {
                 type string;
               }
             }
             container attr-cluster-list {
               description
                 "Cluster List Attribute";
               leaf attr-length {
                 type string;
               }
               leaf attr-value {
                 type string;
               }
             }
             container attr-originator-id {
               description
                 "Originator Attribute";
               leaf attr-length {
                 type string;
               }
               leaf attr-value {
                 type string;
               }
             }
             leaf domain-path {
               type string;
             }
             leaf attr-otc {
               type int32;
               description
                 "Only-to-customer attribute";
             }
             container attr-unrecognized {
               description
                 "Unrecognized attributes";
               leaf attr-length {
                 type string;
               }
               leaf attr-flags {
                 type string;
               }
               leaf attr-code {
                 type string;
               }
               leaf attr-value {
                 type string;
               }
             }
           }
           container communities {
             leaf-list community {
               type string;
               description
                 "Basic community";
             }
             leaf-list extended-community {
               type string;
               description
                 "Extended community";
             }
             leaf-list ipv6-extended-community {
               type string;
               description
                 "IPv6 extended community";
             }
           }
           list bgp-tunnel-attribute {
             key "tunnel-attribute-type";
             description
               "Tunne encap attribute information";
             leaf tunnel-attribute-type {
               type string;
             }
             leaf tunnel-attribute-rpf {
               type empty;
             }
             leaf tunnel-attribute-color {
               type uint32;
             }
             leaf tunnel-attribute-destination {
               type jt:ipaddr;
             }
           }
           container attrset {
             container bgp-prefix-sid-attr {
               description
                 "BGP Prefix SID Attribute";
               container bgp-prefix-sid-attr-label-idx-tlv {
                 leaf bgp-prefix-sid-label-idx-index {
                   type int32;
                 }
                 leaf bgp-prefix-sid-attr-status {
                   type string;
                 }
               }
               container bgp-prefix-sid-attr-srgb-tlv {
                 list bgp-prefix-sid-srgb-block {
                   key "bgp-prefix-sid-srgb-block-start-label";
                   leaf bgp-prefix-sid-srgb-block-start-label {
                     type int32;
                   }
                   leaf bgp-prefix-sid-srgb-block-range {
                     type int32;
                   }
                 }
               }
               container bgp-prefix-sid-attr-service-tlv {
                 leaf bgp-prefix-sid-srv6-sid-value {
                   type jt:ipaddr;
                 }
                 leaf bgp-prefix-sid-attr-service-tlv-type {
                   type uint32;
                 }
                 leaf bgp-prefix-sid-attr-tlv-type {
                   type uint32;
                 }
                 leaf bgp-prefix-sid-srv6-sid-bh {
                   type uint32;
                 }
                 leaf bgp-prefix-sid-srv6-sid-bl {
                   type uint32;
                 }
                 leaf bgp-prefix-sid-srv6-sid-nl {
                   type uint32;
                 }
                 leaf bgp-prefix-sid-srv6-sid-fl {
                   type uint32;
                 }
                 leaf bgp-prefix-sid-srv6-sid-al {
                   type uint32;
                 }
                 leaf bgp-prefix-sid-srv6-sid-tl {
                   type uint32;
                 }
                 leaf bgp-prefix-sid-srv6-sid-to {
                   type uint32;
                 }
               }
               container bgp-prefix-sid-attr-unknown-tlvs {
                 list bgp-prefix-sid-attr-unknown-tlv {
                   key "bgp-prefix-sid-unknown-tlv-type";
                   leaf bgp-prefix-sid-unknown-tlv-type {
                     type uint32;
                   }
                   leaf bgp-prefix-sid-unknown-tlv-len {
                     type uint32;
                   }
                 }
               }
             }
             leaf attrset-as {
               type int32;
               description
                 "Originator AS";
             }
             leaf med {
               type int32;
               description
                 "Multiple exit discriminator";
             }
             leaf local-preference {
               type int32;
             }
             leaf as-path {
               type string;
               description
                 "Name of AS path regular expression (BGP only)";
             }
             leaf pmsi {
               type string;
               description
                 "P-multicast service interface";
             }
             leaf cluster-id {
               type string;
             }
             leaf originator {
               type string;
             }
             leaf connector {
               type string;
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
           }
           container link-state-information {
             container link-state-link {
               leaf link-name {
                 type string;
               }
               leaf color {
                 type int32;
               }
               leaf metric {
                 type int32;
               }
               leaf te-metric {
                 type int32;
                 description
                   "LSP TE metric";
               }
               leaf link-avg-delay {
                 type uint32;
               }
               leaf link-min-delay {
                 type uint32;
               }
               leaf link-max-delay {
                 type uint32;
               }
               leaf link-avg-delay-var {
                 type uint32;
               }
               leaf ldp-support {
                 type string;
               }
               leaf rsvpte-support {
                 type string;
               }
               leaf maximum-bw {
                 type uint64;
               }
               leaf reservable-bw {
                 type uint64;
               }
               container protections {
                 leaf-list protection-type {
                   type string;
                   description
                     "LSP protection desired";
                 }
               }
               container link-srlgs {
                 leaf-list link-srlg {
                   type string;
                 }
               }
               container unreserved-bws {
                 list unreserved-bw {
                   key "unreserved-bw-priority";
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   key "link-lan-adj-sid-label";
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   key "link-p2p-adj-sid-label";
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
               container link-bgp-peer-sids {
                 list link-bgp-peer-sid {
                   key "link-bgp-peer-sid-label";
                   leaf link-bgp-peer-sid-label {
                     type uint32;
                   }
                   leaf link-bgp-peer-sid-flags {
                     type string;
                   }
                   leaf link-bgp-peer-sid-weight {
                     type uint32;
                   }
                 }
               }
               container link-srv6-end-x-sids {
                 list link-srv6-end-x-sid {
                   key "link-srv6-end-x-sid-val";
                   leaf link-srv6-end-x-sid-type {
                     type string;
                   }
                   leaf link-srv6-end-x-sid-val {
                     type jt:ipv6addr;
                   }
                   leaf link-srv6-end-x-sid-flags {
                     type string;
                   }
                   leaf link-srv6-end-x-sid-weight {
                     type int32;
                   }
                   leaf link-srv6-end-x-sid-algo {
                     type int32;
                   }
                   leaf link-srv6-end-x-sid-func {
                     type string;
                   }
                   leaf link-srv6-end-x-sid-lan-neighbor-id {
                     type string;
                   }
                   container link-srv6-end-x-sid-sstlv {
                     leaf link-srv6-end-x-sid-sstlv-header {
                       type empty;
                     }
                     leaf link-srv6-end-x-sid-sstlv-blen {
                       type uint32;
                     }
                     leaf link-srv6-end-x-sid-sstlv-nlen {
                       type uint32;
                     }
                     leaf link-srv6-end-x-sid-sstlv-flen {
                       type uint32;
                     }
                     leaf link-srv6-end-x-sid-sstlv-alen {
                       type uint32;
                     }
                   }
                 }
               }
               container link-msd-types {
                 list link-msd-entry {
                   key "link-msd-type";
                   leaf link-msd-type {
                     type uint32;
                   }
                   leaf link-msd-value {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf-list node-area {
                   type string;
                 }
               }
               container node-ipv4-router-ids {
                 leaf-list node-ipv4-router-id {
                   type jt:ipaddr;
                 }
               }
               container node-ipv6-router-ids {
                 leaf-list node-ipv6-router-id {
                   type jt:ipaddr;
                 }
               }
               container node-topologies {
                 list node-topology {
                   key "id";
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   key "node-spring-srgb-block-start node-spring-srgb-block-range";
                   leaf node-spring-srgb-block-start {
                     type uint32;
                   }
                   leaf node-spring-srgb-block-range {
                     type uint32;
                   }
                   leaf node-spring-srgb-block-flags {
                     type string;
                   }
                 }
               }
               container node-msd-types {
                 list node-msd-entry {
                   key "node-msd-type";
                   leaf node-msd-type {
                     type uint32;
                   }
                   leaf node-msd-value {
                     type uint32;
                   }
                 }
               }
               container node-srv6-capability {
                 leaf node-srv6-capability-flag {
                   type uint32;
                 }
               }
               container node-spring-algorithms {
                 list node-spring-algorithm {
                   key "node-spring-algorithm-type";
                   leaf node-spring-algorithm-type {
                     type uint32;
                   }
                 }
               }
               container node-spring-falgo-defs {
                 list node-spring-falgo-def {
                   key "node-spring-falgo-def-algo";
                   leaf node-spring-falgo-def-algo {
                     type uint32;
                   }
                   leaf node-spring-falgo-def-metric-type {
                     type uint32;
                   }
                   leaf node-spring-falgo-def-calculation-type {
                     type uint32;
                   }
                   leaf node-spring-falgo-def-priority {
                     type uint32;
                   }
                   leaf node-spring-falgo-def-flags {
                     type string;
                   }
                   leaf node-spring-falgo-def-include-any {
                     type string;
                   }
                   leaf node-spring-falgo-def-exclude {
                     type string;
                   }
                   leaf node-spring-falgo-def-include-all {
                     type string;
                   }
                 }
               }
             }
             list link-state-te-policy-cp-segment {
             }
             container link-state-te-policy-cp {
               leaf link-state-te-policy-cp-name {
                 type string;
               }
               leaf link-state-te-policy-cp-flags {
                 type string;
               }
               leaf link-state-te-policy-cp-preference {
                 type uint32;
               }
               leaf link-state-te-policy-cp-priority {
                 type uint32;
               }
               leaf link-state-te-policy-cp-constraint-header {
                 type empty;
               }
               leaf link-state-te-policy-cp-constraint-flags {
                 type string;
               }
               leaf link-state-te-policy-cp-mtid {
                 type uint32;
               }
               leaf link-state-te-policy-cp-algo {
                 type uint32;
               }
               leaf link-state-te-policy-cp-exclude-any {
                 type string;
               }
               leaf link-state-te-policy-cp-include-any {
                 type string;
               }
               leaf link-state-te-policy-cp-include-all {
                 type string;
               }
               leaf link-state-te-policy-cp-bandwidth {
                 type uint32;
               }
               leaf link-state-te-policy-cp-bsid-flags {
                 type string;
               }
               leaf link-state-te-policy-cp-mpls-bsid {
                 type uint32;
               }
               leaf link-state-te-policy-cp-mpls-spec-bsid {
                 type uint32;
               }
               leaf link-state-te-policy-cp-segment-list-count {
                 type int32;
               }
               container link-state-te-policy-cp-srv6-bsid-info {
                 leaf link-state-te-policy-cp-srv6-bsid-flags {
                   type string;
                   description
                     "SRv6 BSID flags";
                 }
                 leaf link-state-te-policy-cp-srv6-bsid {
                   type jt:ipv6addr;
                   description
                     "SRv6 BSID";
                 }
                 leaf link-state-te-policy-cp-srv6-spec-bsid {
                   type jt:ipv6addr;
                   description
                     "Specified SRv6 BSID";
                 }
                 leaf link-state-te-policy-cp-srv6-bsid-ep-bhv {
                   type uint32;
                   description
                     "SRv6 BSID endpoint behavior";
                 }
                 leaf link-state-te-policy-cp-srv6-bsid-ep-bhv-flags {
                   type string;
                   description
                     "SRv6 BSID endpoint behavior flags";
                 }
                 leaf link-state-te-policy-cp-srv6-bsid-ep-bhv-algo {
                   type uint32;
                   description
                     "SRv6 BSID endpoint behavior algo";
                 }
                 leaf link-state-te-policy-cp-srv6-bsid-sstlv {
                   type string;
                   description
                     "SRv6 BSID endpoint behavior SSTLV";
                 }
               }
               list link-state-te-policy-cp-segment-list {
                 key "link-state-te-policy-cp-segment-list-index";
                 leaf link-state-te-policy-cp-segment-list-index {
                   type int32;
                 }
                 leaf link-state-te-policy-cp-segment-list-flags {
                   type string;
                 }
                 leaf link-state-te-policy-cp-segment-list-mtid {
                   type uint32;
                 }
                 leaf link-state-te-policy-cp-segment-list-weight {
                   type uint32;
                 }
                 leaf link-state-te-policy-cp-segment-list-algo {
                   type uint32;
                 }
                 leaf link-state-te-policy-cp-segment-list-metric-type {
                   type string;
                 }
                 leaf link-state-te-policy-cp-segment-list-metric-value {
                   type uint32;
                 }
                 leaf link-state-te-policy-cp-segment-count {
                   type int32;
                 }
                 leaf link-state-te-policy-cp-segment-header {
                   type empty;
                 }
                 list link-state-te-policy-cp-segment {
                   leaf link-state-te-policy-cp-mpls-segment-id {
                     type uint32;
                   }
                   leaf link-state-te-policy-cp-srv6-segment-id {
                     type jt:ipv6addr;
                   }
                   leaf link-state-te-policy-cp-segment-descriptor {
                     type jt:ipaddr;
                   }
                   leaf link-state-te-policy-cp-segment-flags {
                     type string;
                   }
                   leaf link-state-te-policy-cp-segment-ep-bhv {
                     type string;
                   }
                   leaf link-state-te-policy-cp-segment-ep-bhv-flags {
                     type uint32;
                   }
                   leaf link-state-te-policy-cp-segment-ep-bhv-algo {
                     type uint32;
                   }
                   container link-state-te-policy-cp-segment-sstlv {
                     leaf link-state-te-policy-cp-segment-sstlv-header {
                       type empty;
                     }
                     leaf link-state-te-policy-cp-segment-sstlv-blen {
                       type uint32;
                     }
                     leaf link-state-te-policy-cp-segment-sstlv-nlen {
                       type uint32;
                     }
                     leaf link-state-te-policy-cp-segment-sstlv-flen {
                       type uint32;
                     }
                     leaf link-state-te-policy-cp-segment-sstlv-alen {
                       type uint32;
                     }
                   }
                 }
               }
             }
             container link-state-prefix {
               leaf link-state-prefix-attr-flags {
                 type string;
               }
               leaf link-state-prefix-metric {
                 type uint32;
               }
               list link-state-prefix-sid {
                 key "link-state-prefix-sid-index link-state-prefix-sid-flags link-state-prefix-sid-algo";
                 leaf link-state-prefix-sid-index {
                   type uint32;
                 }
                 leaf link-state-prefix-sid-flags {
                   type string;
                 }
                 leaf link-state-prefix-sid-algo {
                   type string;
                 }
               }
               container link-state-prefix-srv6-locator {
                 leaf link-state-prefix-srv6-locator-flags {
                   type string;
                 }
                 leaf link-state-prefix-srv6-locator-algo {
                   type string;
                 }
                 leaf link-state-prefix-srv6-locator-metric {
                   type string;
                 }
               }
               list link-state-prefix-fapm {
                 key "link-state-prefix-fapm-algo";
                 leaf link-state-prefix-fapm-algo {
                   type uint32;
                 }
                 leaf link-state-prefix-fapm-metric {
                   type uint32;
                 }
               }
             }
             container link-state-srv6-endsid {
               container link-state-srv6-endsid-info {
                 leaf link-state-srv6-endsid-epb {
                   type string;
                 }
                 leaf link-state-srv6-endsid-flags {
                   type string;
                 }
                 leaf link-state-srv6-endsid-algo {
                   type string;
                 }
                 container link-state-srv6-endsid-sstlv {
                   leaf link-state-srv6-endsid-sstlv-header {
                     type empty;
                   }
                   leaf link-state-srv6-endsid-sstlv-blen {
                     type uint32;
                   }
                   leaf link-state-srv6-endsid-sstlv-nlen {
                     type uint32;
                   }
                   leaf link-state-srv6-endsid-sstlv-flen {
                     type uint32;
                   }
                   leaf link-state-srv6-endsid-sstlv-alen {
                     type uint32;
                   }
                 }
               }
             }
             container link-state-unknown-tlvs {
               list link-state-unknown-tlv {
                 key "unknown-type";
                 leaf unknown-type {
                   type uint32;
                 }
                 leaf unknown-length {
                   type uint32;
                 }
                 leaf unknown-bytes {
                   type string;
                 }
               }
             }
           }
           container aggregate {
             leaf aggregate-truncate {
               type string;
             }
             container aggregate-as-path {
               container bgp-path-attributes {
                 container attr-as-path {
                   description
                     "AS Path Attribute";
                   leaf attr-length {
                     type string;
                   }
                   leaf flags {
                     type string;
                     description
                       "Enabled trace flags";
                   }
                 }
                 container attr-as4-path {
                   description
                     "4-byte AS Path Attribute";
                   leaf attr-length {
                     type string;
                   }
                 }
                 container attr-as-path-effective {
                   description
                     "Effective AS-Path Attribute";
                   leaf attr-length {
                     type string;
                   }
                 }
                 container attr-aggregator {
                   description
                     "Aggregator Attribute";
                   leaf attr-length {
                     type string;
                   }
                 }
                 container attr-aggregator4 {
                   description
                     "Aggregator4 Attribute";
                   leaf attr-length {
                     type string;
                   }
                 }
                 container attr-cluster-list {
                   description
                     "Cluster List Attribute";
                   leaf attr-length {
                     type string;
                   }
                 }
                 container attr-originator-id {
                   description
                     "Originator Attribute";
                   leaf attr-length {
                     type string;
                   }
                 }
               }
               leaf as-path {
                 type string;
                 description
                   "Name of AS path regular expression (BGP only)";
               }
               leaf reference-count {
                 type int32;
                 description
                   "Reference count";
               }
               leaf as-path-length {
                 type int32;
               }
               leaf aggregate-truncate {
                 type string;
               }
             }
             leaf aggregate-flags {
               type string;
               description
                 "Flags on this aggregate route entry";
             }
             leaf aggregate-depth {
               type int32;
               description
                 "Depth of this aggregate";
             }
             leaf aggregate-active {
               type empty;
               description
                 "Present if this aggregate is active";
             }
             leaf aggregate-algo {
               type uint32;
               description
                 "Algorithm number";
             }
             leaf contributing-route-count {
               type int32;
               description
                 "Number of contributing routes in this aggregate";
             }
             leaf aggregate-policy-name {
               type string;
             }
             list aggregated-route {
               key "destination-prefix";
               leaf destination-prefix {
                 type string;
                 description
                   "Destination prefix and mask";
               }
               leaf protocol-name {
                 type string;
               }
             }
           }
           list kern-nhexpand {
             description
               "Next-hop gateway information";
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
           }
           container kern-nh-platform-layer-input {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           container kern-nh-platform-layer-output {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           list nh {
             description
               "Next-hop gateway information";
             leaf selected-next-hop {
               type empty;
               description
                 "Present if this next hop is selected";
             }
             leaf to {
               type string;
               description
                 "Neighbor address to which to send (next-hop address)";
             }
             leaf nh-indirect-fnh-type {
               type string;
               description
                 "Indirect pointing to a well-known nexthop";
             }
             leaf via {
               type string;
               description
                 "Reachable via a local interface";
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
             leaf nh-string {
               type string;
             }
             leaf nh-table-receive {
               type string;
               description
                 "Destination is a local address";
             }
             leaf nh-table {
               type string;
               description
                 "Indirect pointing to another table";
             }
             leaf nh-table-localized {
               type string;
               description
                 "Indirect pointing to a localized table";
             }
             leaf nh-localized-ifl {
               type string;
               description
                 "Indirect pointing to a localized ifl";
             }
             leaf lsp-name {
               type string;
               description
                 "Tunneled into an RSVP LSP";
             }
             leaf mpls-label {
               type string;
               description
                 "Label of MPLS packet";
             }
             leaf nh-local-interface {
               type string;
               description
                 "Destination is a local interface";
             }
             leaf nh-service {
               type string;
               description
                 "Next-hop service";
             }
             leaf nh-private-comp {
               type string;
               description
                 "Private Composite Next-hop";
             }
             leaf srv6-prefix-sid {
               type jt:ipaddr;
               description
                 "SRv6 prefixe sid value";
             }
             leaf srv6-encap-brief {
               type string;
               description
                 "IPV6 SR-header encapsulation";
             }
             leaf elnh-address {
               type string;
               description
                 "Address of Element Next-hop";
             }
             leaf localized-table {
               type string;
               description
                 "Name of localized table";
             }
             leaf ae-member-interface {
               type string;
               description
                 "AE Member interface";
             }
             leaf weight {
               type int32;
               description
                 "Next-hop weight";
             }
             leaf balance {
               type int32;
               description
                 "Next-hop balance";
             }
             leaf uflags {
               type string;
               description
                 "Next-hop uflags";
             }
             leaf filter {
               type string;
               description
                 "Next-hop firewall filter";
             }
             leaf session {
               type string;
               description
                 "Session ID Associated with this NH";
             }
             leaf statistics-id-group-terse {
               type string;
               description
                 "Statistics ID Group Associated with this NH";
             }
             leaf app-specific-opaque {
               type string;
               description
                 "Application specific opaque data dump";
             }
             leaf gw-opaque {
               type string;
               description
                 "Nexthops gateway opaque data handle";
             }
             leaf statistics-pkts-count {
               type int32;
               description
                 "Statistics packet count Associated with this NH";
             }
             leaf statistics-bytes-count {
               type int32;
               description
                 "Statistics bytes count Associated with this NH";
             }
             leaf ext-int-type {
               type string;
               description
                 "Next-hop type of equal-external-internal multipath";
             }
             leaf fc {
               type int32;
               description
                 "Forwarding-class";
             }
             leaf label-ttl-action {
               type string;
               description
                 "TTL action associated with labels";
             }
             leaf load-balance-label {
               type string;
               description
                 "Load balance action associated with labels";
             }
             leaf label-element {
               type string;
               description
                 "Pointer to the tag label element";
             }
             leaf label-element-parent {
               type string;
               description
                 "Pointer to the tag label element parent";
             }
             leaf label-element-refcount {
               type string;
               description
                 "Number of references to the tag label element";
             }
             leaf label-element-childcount {
               type string;
               description
                 "Number of child references to the tag label element";
             }
             leaf label-element-lspid {
               type string;
               description
                 "LSP ID of the tag label element";
             }
             leaf nh-service-pkt-dist {
               type string;
               description
                 "Multi services packet distribution type";
             }
             leaf nh-service-app-data {
               type string;
               description
                 "Multi services application specific data";
             }
             leaf nh-index {
               type uint32;
               description
                 "Next-hop index";
             }
             leaf nh-address {
               type string;
               description
                 "Address of next hop";
             }
             leaf nh-reference-count {
               type int32;
               description
                 "Number of references to this next hop";
             }
             leaf tunnel-composite-attr-type {
               type string;
               description
                 "Tunnel-Type for tunnel-composite-nexthop";
             }
             leaf tunnel-composite-attr-subtype {
               type string;
               description
                 "Tunnel-Subtype for tunnel-composite-nexthop";
             }
             leaf tunnel-composite-attr-reference-count {
               type int32;
               description
                 "Tunnel-reference-count for tunnel-composite-nexthop";
             }
             leaf tunnel-composite-attr-nh-id {
               type int32;
               description
                 "Tunnel-NextHop-Id for tunnel-composite-nexthop";
             }
             leaf tunnel-composite-attr-dest {
               type jt:ipaddr;
               description
                 "Tunnel-Destination for tunnel-composite-nexthop";
             }
             leaf tunnel-composite-attr-src {
               type jt:ipaddr;
               description
                 "Tunnel-Source for tunnel-composite-nexthop";
             }
             leaf tunnel-composite-attr-tunnel-endpoint {
               type jt:ipaddr;
               description
                 "Tunnel-Endpoint for tunnel-composite-nexthop";
             }
             leaf tunnel-composite-anchor-pfe {
               type string;
               description
                 "Anchor PFE name, if tunnel nexthop is localized";
             }
             leaf tunnel-composite-encap-rtb-id {
               type int32;
               description
                 "Tunnel encap routing table index";
             }
             leaf tunnel-composite-decap-rtb-id {
               type int32;
               description
                 "Tunnel decap routing table index";
             }
             leaf tunnel-composite-attr-ttl {
               type int32;
               description
                 "Tunnel-TTL for tunnel-composite-nexthop";
             }
             leaf tunnel-composite-attr-udp-port {
               type int32;
               description
                 "Tunnel-UDP-Destination port for tunnel-composite-nexthop";
             }
             leaf tunnel-composite-attr-fc-id {
               type int32;
               description
                 "Tunnel-Forwarding-Class-ID for tunnel-composite-nexthop";
             }
             leaf tunnel-composite-attr-tid {
               type int32;
               description
                 "Tunnel-Id for tunnel-composite-nexthop";
             }
             leaf tunnel-composite-attr-label {
               type string;
               description
                 "Tunnel-VPN-Label for tunnel-composite-nexthop";
             }
             leaf tunnel-composite-attr-label-ttl {
               type string;
               description
                 "Tunnel-VPN-Label-TTL for tunnel-composite-nexthop";
             }
             leaf tunnel-composite-attr-gre-key {
               type int32;
               description
                 "GRE key for tunnel-composite-nexthop";
             }
             leaf-list tunnel-composite-attr-segment-addr {
               type jt:ipaddr;
               description
                 "IPv6 segment-address";
             }
             leaf-list tunnel-composite-attr-sid {
               type int32;
               description
                 "IPv6 segment-sid";
             }
             leaf tunnel-composite-attr-vni {
               type int32;
               description
                 "Tunnel-VNI for tunnel-composite-nexthop in VxLAN";
             }
             leaf tunnel-composite-attr-dest-mac {
               type string;
               description
                 "Tunnel-Dest-Mac for tunnel-composite-nexthop in VxLAN";
             }
             leaf translate-composite-attr-type {
               type string;
               description
                 "Translation type for translate-composite-nexthop";
             }
             leaf translate-composite-attr-flags {
               type string;
               description
                 "Flags for translate-composite-nexthop";
             }
             leaf translate-composite-attr-reference-count {
               type int32;
               description
                 "Reference count for translate-composite-nexthop";
             }
             leaf translate-composite-attr-nh-id {
               type int32;
               description
                 "NextHop id for translate-composite-nexthop";
             }
             leaf translate-composite-attr-dest {
               type jt:ipaddr;
               description
                 "Translation destination for translate-composite-nexthop";
             }
             leaf translate-composite-attr-dest-plen {
               type int32;
               description
                 "Translation destination prefix length for 
                 translate-composite-nexthop";
             }
             leaf translate-composite-attr-src {
               type jt:ipaddr;
               description
                 "Translation source for translate-composite-nexthop";
             }
             leaf translate-composite-attr-src-plen {
               type int32;
               description
                 "Translation source prefix length for 
                 translate-composite-nexthop";
             }
             leaf translate-composite-attr-dest-alg-type {
               type string;
               description
                 "Destination algorithm type for translate-composite-nexthop";
             }
             leaf translate-composite-attr-src-alg-type {
               type string;
               description
                 "Source algorithm type for translate-composite-nexthop";
             }
             leaf translate-composite-attr-dest-vrf-id {
               type int32;
               description
                 "Destination vrf id for translate-composite-nexthop";
             }
             leaf translate-composite-attr-src-vrf-id {
               type int32;
               description
                 "Source vrf id for translate-composite-nexthop";
             }
             leaf translate-composite-attr-hoplimit {
               type int32;
               description
                 "Hoplimit for translate-composite-nexthop";
             }
             leaf translate-composite-attr-traffic-class {
               type int32;
               description
                 "Traffic class for translate-composite-nexthop";
             }
             leaf translate-composite-attr-ttl {
               type int32;
               description
                 "Ttl for translate-composite-nexthop";
             }
             leaf translate-composite-attr-tos {
               type int32;
               description
                 "Tos for translate-composite-nexthop";
             }
           }
           container protocol-nh {
             description
               "Protocol next hop";
             list nh {
               description
                 "Next-hop gateway information";
               container vxlan-header-rewrite {
                 description
                   "VXLAN tunnel rewrite information";
                 leaf vxlan-header-rewrite-mtu {
                   type int32;
                   description
                     "VXLAN tunnel MTU";
                 }
                 leaf vxlan-header-rewrite-flags {
                   type int32;
                   description
                     "VXLAN tunnel flags";
                 }
                 leaf vxlan-header-rewrite-encap-rtb-id {
                   type int32;
                   description
                     "VXLAN tunnel encapsulation table ID";
                 }
                 leaf vxlan-header-rewrite-decap-rtb-id {
                   type int32;
                   description
                     "VXLAN tunnel decapsulation table ID";
                 }
                 leaf vxlan-header-rewrite-encap-vnid {
                   type int32;
                   description
                     "VXLAN tunnel encapsulation VNI";
                 }
                 leaf vxlan-header-rewrite-decap-vnid {
                   type int32;
                   description
                     "VXLAN tunnel decapsulation VNI";
                 }
                 leaf vxlan-header-rewrite-svtep {
                   type jt:ipaddr;
                   description
                     "Source VTEP address";
                 }
                 leaf vxlan-header-rewrite-dvtep {
                   type jt:ipaddr;
                   description
                     "Destination VTEP address";
                 }
                 leaf vxlan-header-rewrite-smac {
                   type string;
                   description
                     "Source MAC address";
                 }
                 leaf vxlan-header-rewrite-dmac {
                   type string;
                   description
                     "Destination MAC address";
                 }
               }
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf nh-string {
                 type string;
               }
               leaf elnh-address {
                 type string;
                 description
                   "Address of Element Next-hop";
               }
               leaf to {
                 type string;
                 description
                   "Neighbor address to which to send (next-hop address)";
               }
               leaf via {
                 type string;
                 description
                   "Reachable via a local interface";
               }
               leaf localized-table {
                 type string;
                 description
                   "Name of localized table";
               }
               leaf ae-member-interface {
                 type string;
                 description
                   "AE Member interface";
               }
               leaf weight {
                 type int32;
                 description
                   "Next-hop weight";
               }
               leaf balance {
                 type int32;
                 description
                   "Next-hop balance";
               }
               leaf uflags {
                 type string;
                 description
                   "Next-hop uflags";
               }
               leaf filter {
                 type string;
                 description
                   "Next-hop firewall filter";
               }
               leaf selected-next-hop {
                 type empty;
                 description
                   "Present if this next hop is selected";
               }
               leaf session {
                 type string;
                 description
                   "Session ID Associated with this NH";
               }
               leaf statistics-id-group-terse {
                 type string;
                 description
                   "Statistics ID Group Associated with this NH";
               }
               leaf app-specific-opaque {
                 type string;
                 description
                   "Application specific opaque data dump";
               }
               leaf gw-opaque {
                 type string;
                 description
                   "Nexthops gateway opaque data handle";
               }
               leaf statistics-pkts-count {
                 type int32;
                 description
                   "Statistics packet count Associated with this NH";
               }
               leaf statistics-bytes-count {
                 type int32;
                 description
                   "Statistics bytes count Associated with this NH";
               }
               leaf ext-int-type {
                 type string;
                 description
                   "Next-hop type of equal-external-internal multipath";
               }
               leaf fc {
                 type int32;
                 description
                   "Forwarding-class";
               }
               leaf lsp-name {
                 type string;
                 description
                   "Tunneled into an RSVP LSP";
               }
               leaf mpls-label {
                 type string;
                 description
                   "Label of MPLS packet";
               }
               leaf label-ttl-action {
                 type string;
                 description
                   "TTL action associated with labels";
               }
               leaf load-balance-label {
                 type string;
                 description
                   "Load balance action associated with labels";
               }
               leaf label-element {
                 type string;
                 description
                   "Pointer to the tag label element";
               }
               leaf label-element-parent {
                 type string;
                 description
                   "Pointer to the tag label element parent";
               }
               leaf label-element-refcount {
                 type string;
                 description
                   "Number of references to the tag label element";
               }
               leaf label-element-childcount {
                 type string;
                 description
                   "Number of child references to the tag label element";
               }
               leaf label-element-lspid {
                 type string;
                 description
                   "LSP ID of the tag label element";
               }
               leaf nh-table-receive {
                 type string;
                 description
                   "Destination is a local address";
               }
               leaf nh-table {
                 type string;
                 description
                   "Indirect pointing to another table";
               }
               leaf nh-localized-ifl {
                 type string;
                 description
                   "Indirect pointing to a localized ifl";
               }
               leaf nh-local-interface {
                 type string;
                 description
                   "Destination is a local interface";
               }
               leaf nh-service {
                 type string;
                 description
                   "Next-hop service";
               }
               leaf nh-service-pkt-dist {
                 type string;
                 description
                   "Multi services packet distribution type";
               }
               leaf nh-service-app-data {
                 type string;
                 description
                   "Multi services application specific data";
               }
               leaf nh-private-comp {
                 type string;
                 description
                   "Private Composite Next-hop";
               }
               leaf nh-index {
                 type uint32;
                 description
                   "Next-hop index";
               }
               leaf nh-address {
                 type string;
                 description
                   "Address of next hop";
               }
               leaf nh-reference-count {
                 type int32;
                 description
                   "Number of references to this next hop";
               }
               leaf tunnel-composite-attr-type {
                 type string;
                 description
                   "Tunnel-Type for tunnel-composite-nexthop";
               }
               leaf tunnel-composite-attr-subtype {
                 type string;
                 description
                   "Tunnel-Subtype for tunnel-composite-nexthop";
               }
               leaf tunnel-composite-attr-reference-count {
                 type int32;
                 description
                   "Tunnel-reference-count for tunnel-composite-nexthop";
               }
               leaf tunnel-composite-attr-nh-id {
                 type int32;
                 description
                   "Tunnel-NextHop-Id for tunnel-composite-nexthop";
               }
               leaf tunnel-composite-attr-dest {
                 type jt:ipaddr;
                 description
                   "Tunnel-Destination for tunnel-composite-nexthop";
               }
               leaf tunnel-composite-attr-src {
                 type jt:ipaddr;
                 description
                   "Tunnel-Source for tunnel-composite-nexthop";
               }
               leaf tunnel-composite-attr-tunnel-endpoint {
                 type jt:ipaddr;
                 description
                   "Tunnel-Endpoint for tunnel-composite-nexthop";
               }
               leaf tunnel-composite-anchor-pfe {
                 type string;
                 description
                   "Anchor PFE name, if tunnel nexthop is localized";
               }
               leaf tunnel-composite-encap-rtb-id {
                 type int32;
                 description
                   "Tunnel encap routing table index";
               }
               leaf tunnel-composite-decap-rtb-id {
                 type int32;
                 description
                   "Tunnel decap routing table index";
               }
               leaf tunnel-composite-attr-ttl {
                 type int32;
                 description
                   "Tunnel-TTL for tunnel-composite-nexthop";
               }
               leaf tunnel-composite-attr-udp-port {
                 type int32;
                 description
                   "Tunnel-UDP-Destination port for tunnel-composite-nexthop";
               }
               leaf tunnel-composite-attr-fc-id {
                 type int32;
                 description
                   "Tunnel-Forwarding-Class-ID for tunnel-composite-nexthop";
               }
               leaf tunnel-composite-attr-tid {
                 type int32;
                 description
                   "Tunnel-Id for tunnel-composite-nexthop";
               }
               leaf tunnel-composite-attr-label {
                 type string;
                 description
                   "Tunnel-VPN-Label for tunnel-composite-nexthop";
               }
               leaf tunnel-composite-attr-label-ttl {
                 type string;
                 description
                   "Tunnel-VPN-Label-TTL for tunnel-composite-nexthop";
               }
               leaf tunnel-composite-attr-gre-key {
                 type int32;
                 description
                   "GRE key for tunnel-composite-nexthop";
               }
               leaf-list tunnel-composite-attr-segment-addr {
                 type jt:ipaddr;
                 description
                   "IPv6 segment-address";
               }
               leaf-list tunnel-composite-attr-sid {
                 type int32;
                 description
                   "IPv6 segment-sid";
               }
               leaf tunnel-composite-attr-vni {
                 type int32;
                 description
                   "Tunnel-VNI for tunnel-composite-nexthop in VxLAN";
               }
               leaf tunnel-composite-attr-dest-mac {
                 type string;
                 description
                   "Tunnel-Dest-Mac for tunnel-composite-nexthop in VxLAN";
               }
               leaf translate-composite-attr-type {
                 type string;
                 description
                   "Translation type for translate-composite-nexthop";
               }
               leaf translate-composite-attr-flags {
                 type string;
                 description
                   "Flags for translate-composite-nexthop";
               }
               leaf translate-composite-attr-reference-count {
                 type int32;
                 description
                   "Reference count for translate-composite-nexthop";
               }
               leaf translate-composite-attr-nh-id {
                 type int32;
                 description
                   "NextHop id for translate-composite-nexthop";
               }
               leaf translate-composite-attr-dest {
                 type jt:ipaddr;
                 description
                   "Translation destination for translate-composite-nexthop";
               }
               leaf translate-composite-attr-dest-plen {
                 type int32;
                 description
                   "Translation destination prefix length for 
                   translate-composite-nexthop";
               }
               leaf translate-composite-attr-src {
                 type jt:ipaddr;
                 description
                   "Translation source for translate-composite-nexthop";
               }
               leaf translate-composite-attr-src-plen {
                 type int32;
                 description
                   "Translation source prefix length for 
                   translate-composite-nexthop";
               }
               leaf translate-composite-attr-dest-alg-type {
                 type string;
                 description
                   "Destination algorithm type for 
                   translate-composite-nexthop";
               }
               leaf translate-composite-attr-src-alg-type {
                 type string;
                 description
                   "Source algorithm type for translate-composite-nexthop";
               }
               leaf translate-composite-attr-dest-vrf-id {
                 type int32;
                 description
                   "Destination vrf id for translate-composite-nexthop";
               }
               leaf translate-composite-attr-src-vrf-id {
                 type int32;
                 description
                   "Source vrf id for translate-composite-nexthop";
               }
               leaf translate-composite-attr-hoplimit {
                 type int32;
                 description
                   "Hoplimit for translate-composite-nexthop";
               }
               leaf translate-composite-attr-traffic-class {
                 type int32;
                 description
                   "Traffic class for translate-composite-nexthop";
               }
               leaf translate-composite-attr-ttl {
                 type int32;
                 description
                   "Ttl for translate-composite-nexthop";
               }
               leaf translate-composite-attr-tos {
                 type int32;
                 description
                   "Tos for translate-composite-nexthop";
               }
             }
             leaf to {
               type string;
               description
                 "Neighbor address to which to send (next-hop address)";
             }
             leaf metric {
               type int32;
             }
             leaf aigp {
               type string;
               description
                 "AIGP";
             }
             leaf balance {
               type int32;
               description
                 "Next-hop balance";
             }
             leaf flags {
               type string;
               description
                 "Enabled trace flags";
             }
             leaf res-state {
               type string;
               description
                 "Status of route resolution";
             }
             leaf res-tsp-idx {
               type int32;
               description
                 "TSP index of the path";
             }
             leaf-list res-path-aux {
               type string;
             }
             leaf-list res-path-aux-type {
               type string;
             }
             leaf-list res-path-aux-flags {
               type string;
             }
             leaf-list res-path-aux-rs-name {
               type string;
             }
             leaf-list res-path-aux-rs-ribs {
               type string;
             }
             leaf-list res-path-inode-flags {
               type string;
             }
             leaf-list res-path-flags {
               type string;
             }
             leaf-list res-path-fnh-link {
               type string;
             }
             leaf-list res-path-inh-link {
               type string;
             }
             leaf mpls-label {
               type string;
               description
                 "Label of MPLS packet";
             }
             leaf label-ttl-action {
               type string;
               description
                 "TTL action associated with labels";
             }
             leaf load-balance-label {
               type string;
               description
                 "Load balance action associated with labels";
             }
             leaf-list composite-nh {
               type string;
             }
             leaf-list pnh-statistics-id-group {
               type string;
               description
                 "Statistics ID Group Associated with this protocol NH";
             }
             leaf-list vpnlabel-nh {
               type string;
             }
             leaf-list indirect-nh {
               type string;
             }
             leaf ext-int-type {
               type string;
               description
                 "Next-hop type of equal-external-internal multipath";
             }
             leaf gw-opaque {
               type string;
               description
                 "Nexthops gateway opaque data handle";
             }
             leaf-list forwarding-nh-count {
               type int32;
               description
                 "Number of indirect path forwarding next hops";
             }
             leaf-list merged-forwarding-nh-count {
               type int32;
               description
                 "Number of indirect path forwarding next hops (Merged)";
             }
             leaf nh-type {
               type string;
               description
                 "Special next hop: Reject, Blackhole, Receive, Multicast, 
                 Local, or Unused";
             }
             leaf-list node-prefix {
               type string;
             }
             leaf-list node-prefix-length {
               type int32;
             }
             leaf-list originating-rib {
               type string;
               description
                 "Routing table from which this route was learned";
             }
             leaf-list node-metric {
               type int32;
             }
             leaf-list node-path-count {
               type int32;
               description
                 "Number of paths for this node";
             }
             leaf node-flags {
               type int32;
               description
                 "Flags for this node";
             }
             leaf-list node-address {
               type string;
             }
             leaf-list node-forwarding-nh-count {
               type int32;
             }
             leaf-list nh-subtype {
               type string;
               description
                 "Specified nexthop subtype";
             }
             leaf indirect-nh-count {
               type int32;
               description
                 "Number of indirect next hops";
             }
             leaf composite-nh-count {
               type int32;
               description
                 "Number of composite next hops";
             }
             container eth-header-rewrite {
               description
                 "Ethernet header rewrite information";
               leaf eth-header-rewrite-smac {
                 type string;
                 description
                   "Source MAC address";
               }
               leaf eth-header-rewrite-dmac {
                 type string;
                 description
                   "Destination MAC address";
               }
               leaf eth-header-rewrite-tpid {
                 type int32;
                 description
                   "Ethernet header TPID";
               }
               leaf eth-header-rewrite-tci {
                 type int32;
                 description
                   "Ethernet header TCI";
               }
               leaf eth-header-rewrite-vlan-id {
                 type int32;
                 description
                   "Ethernet header VLAN ID";
               }
               leaf eth-header-rewrite-ethertype {
                 type int32;
                 description
                   "Ethernet header ethertype";
               }
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container fully-resolved-tunnel {
               description
                 "GRE or UDP tunnel rewrite information";
               leaf fully-resolved-tunnel-type {
                 type string;
                 description
                   "Tunnel type";
               }
               leaf fully-resolved-tunnel-dest {
                 type jt:ipaddr;
                 description
                   "Tunnel Destination";
               }
               leaf fully-resolved-tunnel-src {
                 type jt:ipaddr;
                 description
                   "Tunnel Source";
               }
               leaf fully-resolved-tunnel-ep-addr {
                 type jt:ipaddr;
                 description
                   "Tunnel endpoint address";
               }
               leaf fully-resolved-tunnel-encap-rtb-id {
                 type int32;
                 description
                   "Tunnel encap routing table id";
               }
               leaf fully-resolved-tunnel-decap-rtb-id {
                 type int32;
                 description
                   "Tunnel decap routing table id";
               }
             }
           }
           container srte-policy-state {
             leaf sr-source {
               type string;
             }
             leaf sr-origin {
               type string;
             }
             leaf sr-preference {
               type uint32;
             }
             leaf sr-preference-override {
               type uint32;
             }
             leaf sr-route-distinguisher {
               type uint32;
             }
           }
           container srte-policy-information {
             container srte-policy {
               leaf srte-path-preference {
                 type uint32;
               }
               leaf srte-binding-sid {
                 type string;
               }
               leaf srte-adv-policy-name {
                 type string;
               }
               leaf srte-priority {
                 type uint32;
               }
               leaf srte-enlp {
                 type uint32;
               }
               leaf srte-tlv-recv-flags {
                 type string;
               }
               leaf srte-binding-sid-label-encoding {
                 type string;
               }
               list srte-segment-list {
                 leaf srte-segment-list-weight {
                   type uint32;
                 }
                 list srte-segment {
                   leaf srte-segment-label {
                     type uint32;
                   }
                   leaf srte-segment-label-ttl {
                     type string;
                     description
                       "SR Policy segment label ttl";
                   }
                   leaf srte-segment-type {
                     type string;
                     description
                       "SR Policy segment type";
                   }
                   leaf srte-segment-label-class {
                     type uint32;
                     description
                       "SR Policy segment label traffic-class";
                   }
                 }
               }
             }
           }
           container bgp-prefix-sid-attr {
             description
               "BGP Prefix SID Attribute";
             container bgp-prefix-sid-attr-label-idx-tlv {
               leaf bgp-prefix-sid-label-idx-index {
                 type int32;
               }
               leaf bgp-prefix-sid-attr-status {
                 type string;
               }
             }
             container bgp-prefix-sid-attr-srgb-tlv {
               list bgp-prefix-sid-srgb-block {
                 key "bgp-prefix-sid-srgb-block-start-label";
                 leaf bgp-prefix-sid-srgb-block-start-label {
                   type int32;
                 }
                 leaf bgp-prefix-sid-srgb-block-range {
                   type int32;
                 }
               }
             }
             container bgp-prefix-sid-attr-service-tlv {
               leaf bgp-prefix-sid-srv6-sid-value {
                 type jt:ipaddr;
               }
               leaf bgp-prefix-sid-attr-service-tlv-type {
                 type uint32;
               }
               leaf bgp-prefix-sid-attr-tlv-type {
                 type uint32;
               }
               leaf bgp-prefix-sid-srv6-sid-bh {
                 type uint32;
               }
               leaf bgp-prefix-sid-srv6-sid-bl {
                 type uint32;
               }
               leaf bgp-prefix-sid-srv6-sid-nl {
                 type uint32;
               }
               leaf bgp-prefix-sid-srv6-sid-fl {
                 type uint32;
               }
               leaf bgp-prefix-sid-srv6-sid-al {
                 type uint32;
               }
               leaf bgp-prefix-sid-srv6-sid-tl {
                 type uint32;
               }
               leaf bgp-prefix-sid-srv6-sid-to {
                 type uint32;
               }
             }
             container bgp-prefix-sid-attr-unknown-tlvs {
               list bgp-prefix-sid-attr-unknown-tlv {
                 key "bgp-prefix-sid-unknown-tlv-type";
                 leaf bgp-prefix-sid-unknown-tlv-type {
                   type uint32;
                 }
                 leaf bgp-prefix-sid-unknown-tlv-len {
                   type uint32;
                 }
               }
             }
           }
           container srte-policy-telemetry-statistics-state {
             leaf srte-policy-telemetry-statistics-state.heading {
               type string;
             }
             container srte-policy-telemetry-statistics-config {
               leaf ingress {
                 type empty;
                 description
                   "Flag indicating ingress statistics is configured";
               }
               leaf transit {
                 type empty;
                 description
                   "Flag indicating transit statistics is configured";
               }
             }
             list srte-policy-telemetry-statistics-sensor-information {
               leaf sensor-type {
                 type string;
               }
               leaf sensor-status {
                 type string;
               }
               leaf sensor-id {
                 type int32;
                 description
                   "Unique identifier for the sensor";
               }
             }
           }
           list flex-tunnel-profile {
             description
               "Flex V4/V6 route tunnel attribute information";
             container flex-tunnel-profile-info {
               description
                 "The tunnel profile information";
               leaf flex-tunnel-profile-num {
                 type int32;
                 description
                   "The tunnel profile number";
               }
               leaf flex-tunnel-profile-action {
                 type string;
                 description
                   "The action that this profile will be used for";
               }
               leaf flex-tunnel-profile-vni {
                 type int32;
                 description
                   "VXLAN Network Identifier (VNI)";
               }
               leaf flex-tunnel-profile-src-pfx {
                 type string;
                 description
                   "Source address and prefix length";
               }
               leaf flex-tunnel-profile-src-udp-port-range {
                 type string;
                 description
                   "Outer source UDP port range";
               }
               leaf flex-tunnel-profile-src-mac {
                 type string;
                 description
                   "Source MAC address, a 48-bit MAC value";
               }
               leaf flex-tunnel-profile-dest-pfx {
                 type string;
                 description
                   "Destination address";
               }
               leaf flex-tunnel-profile-dest-udp-port {
                 type int32;
                 description
                   "Outer destination UDP port";
               }
               leaf flex-tunnel-profile-dest-mac {
                 type string;
                 description
                   "Destination MAC address, a 48-bit MAC value";
               }
               leaf flex-tunnel-profile-flex-vxlan-flags {
                 type int32;
                 description
                   "Flex VxLAN flags";
               }
               leaf flex-tunnel-profile-reserved-24-bit-field {
                 type int32;
                 description
                   "VXLAN 24-bit reserved field as specified in RFC7348";
               }
               leaf flex-tunnel-profile-reserved-8-bit-field {
                 type int32;
                 description
                   "VXLAN 8-bit reserved field as specified in RFC7348";
               }
               container flex-tunnel-profile-stats {
                 description
                   "Statistics associated with tunnel";
                 leaf flex-tunnel-stats-pkts-count {
                   type int32;
                   description
                     "Packet count";
                 }
                 leaf flex-tunnel-stats-pps {
                   type int32;
                   description
                     "Packets per second";
                 }
                 leaf flex-tunnel-stats-bytes-count {
                   type int32;
                   description
                     "Byte count";
                 }
                 leaf flex-tunnel-stats-bps {
                   type int32;
                   description
                     "Bytes per second";
                 }
               }
             }
             leaf flex-tunnel-profile-string {
               type string;
               description
                 "The tunnel profile string";
             }
           }
           leaf preference2 {
             type int32;
           }
           leaf age {
             type string;
           }
           leaf med {
             type int32;
             description
               "Multiple exit discriminator";
           }
           leaf local-preference {
             type int32;
           }
           leaf rt-tag {
             type int32;
           }
           leaf rt-tag2 {
             type int32;
           }
           leaf learned-from {
             type jt:ipaddr;
             description
               "Peer address from which this route was learned";
           }
           leaf peer-as {
             type int32;
             description
               "Peer AS number";
           }
           leaf evpn-remote-mes {
             type jt:ipaddr;
             description
               "Remote PE";
           }
           leaf evpn-routing-instance-name {
             type string;
             description
               "Routing Instance";
           }
           leaf evpn-tag-rt-type {
             type string;
             description
               "Route Type";
           }
           leaf evpn-vlan-id {
             type int32;
             description
               "VLAN-ID";
           }
           leaf evpn-vpws-service-id {
             type int32;
             description
               "VPWS Service-Id";
           }
           leaf rt-evpn-esi {
             type string;
             description
               "ESI";
           }
           leaf evpn-isid {
             type int32;
             description
               "ISID";
           }
           leaf rt-evpn-bmac {
             type string;
             description
               "BMAC";
           }
           leaf bgp-rtarget-type {
             type string;
             description
               "BGP RT-Constrain route type";
           }
           leaf bgp-rtarget-generation {
             type uint32;
             description
               "BGP RT-Constrain generation";
           }
           leaf bgp-rtarget-for {
             type string;
             description
               "BGP RT-Constrain member";
           }
           leaf nh-index {
             type uint32;
             description
               "Next-hop index";
           }
           leaf transport-class {
             type string;
             description
               "Transport class name";
           }
           leaf nh-address {
             type string;
             description
               "Address of next hop";
           }
           leaf nh-reference-count {
             type int32;
             description
               "Number of references to this next hop";
           }
           leaf ext-int-intf-index {
             type int32;
             description
               "Interface index of equal-external-internal multipath";
           }
           leaf nh-session-id {
             type uint32;
             description
               "Nexthop session id";
           }
           leaf nh-key-opaque {
             type string;
             description
               "Nexthop key opaque handle";
           }
           leaf nh-non-key-opaque {
             type string;
             description
               "Nexthop non-key opaque handle";
           }
           leaf nh-key-opaque-dump {
             type string;
             description
               "Nexthop key opaque app dump";
           }
           leaf nh-non-key-opaque-dump {
             type string;
             description
               "Nexthop non-key opaque app dump";
           }
           leaf nh-flood-overflow {
             type empty;
             description
               "Flood nexthop exceeds maximum branches";
           }
           leaf nh-kernel-id {
             type int32;
             description
               "Table Id for this next hop";
           }
           leaf client-data {
             type string;
             description
               "Route server client details";
           }
           leaf route-distinguisher {
             type string;
             description
               "Name of the route-distinguisher";
           }
           leaf reason-for-invalid {
             type string;
           }
           leaf thread-name {
             type string;
           }
           leaf pmsi {
             type string;
             description
               "P-multicast service interface";
           }
           leaf connector {
             type string;
           }
           leaf color {
             type int32;
           }
           leaf color2 {
             type int32;
           }
           leaf prefix-segment-index {
             type int32;
           }
           leaf rt-isis-level {
             type int32;
           }
           leaf rt-isis-downbit {
             type int32;
           }
           leaf rt-entry-state {
             type string;
             description
               "State of this route entry";
           }
           leaf rt-fib-install-priority {
             type string;
             description
               "Route FIB installation priority";
           }
           leaf rt-ack-state {
             type string;
             description
               "Route acknowledgement state";
           }
           leaf rt-ack-ll-flag {
             type string;
             description
               "Status of route ACK flags";
           }
           leaf rt-ack-req-ts {
             type string;
             description
               "Time when ack request is sent";
           }
           leaf rt-ack-res-time {
             type uint32;
             description
               "Ack route response time";
           }
           leaf rt-ack-re-flash-time {
             type string;
             description
               "Time when ack is re flashed to protocols";
           }
           leaf rt-ack-re-flash-status {
             type string;
             description
               "Status of ACK re-flash to protocols";
           }
           leaf rt-ack-guid {
             type uint64;
             description
               "Ack route global identifier";
           }
           leaf rt-ack-olc {
             type uint64;
             description
               "Ack route global version";
           }
           leaf rt-ack-local-ver {
             type uint32;
             description
               "Ack route global version";
           }
           leaf rt-ack-and-err-flag {
             type uint32;
             description
               "Route ack and error flag";
           }
           leaf rt-ack-history {
             type uint32;
             description
               "Route ack history";
           }
           leaf pfe-err-state {
             type string;
             description
               "Route error state from PFE";
           }
           leaf pfe-err-time {
             type uint32;
             description
               "Route error receive time";
           }
           leaf rt-ver-id {
             type uint32;
             description
               "Route version ID";
           }
           leaf rt-entry-pim-state {
             type string;
             description
               "PIM state of this route entry";
           }
           leaf inactive-reason {
             type string;
             description
               "HFRR profile Inactive reason (if any)";
           }
           leaf local-as {
             type int32;
             description
               "Local AS number";
           }
           leaf med-plus-igp {
             type int32;
           }
           leaf rt-aigp {
             type uint64;
           }
           leaf rt-effective-aigp {
             type uint64;
             description
               "Effective AIGP value used by route selection";
           }
           leaf rt-effective-aigp-reason {
             type string;
             description
               "Reason why the effective AIGP value was selected";
           }
           leaf rt-resolving-aigp {
             type uint64;
           }
           leaf rt-effective-metric {
             type uint64;
             description
               "Effective metric value used by route selection";
           }
           leaf rt-effective-metric-reason {
             type string;
             description
               "Reason why the effective metric value was selected";
           }
           leaf rt-orr {
             type uint32;
           }
           leaf rt-actual-igp-metric {
             type uint32;
           }
           leaf rt-ospf-area {
             type string;
           }
           leaf task-name {
             type string;
             description
               "Name of this task";
           }
           leaf announce-bits {
             type int32;
           }
           leaf announce-tasks {
             type string;
           }
           leaf flow-id {
             type int32;
           }
           leaf bgp-rt-flag {
             type string;
             description
               "BGP route flag";
           }
           leaf label-base {
             type int32;
             description
               "Label base for l2vpn";
           }
           leaf label-range {
             type int32;
             description
               "Label range for l2vpn";
           }
           leaf l2vpn-status-vector {
             type string;
           }
           leaf label-offset {
             type int32;
             description
               "Label offset for l2vpn";
           }
           leaf remote-site {
             type int32;
             description
               "Remote site id";
           }
           leaf l2vpn-mesh-group {
             type string;
           }
           leaf vc-label {
             type int32;
             description
               "VC label";
           }
           leaf context-id {
             type jt:ipaddr;
             description
               "Context Identifier";
           }
           leaf route-control-word {
             type string;
             description
               "Control Word";
           }
           leaf mtu {
             type int32;
             description
               "MTU along an interface";
           }
           leaf cell-bundle-size {
             type int32;
             description
               "Cell bundle size";
           }
           leaf vlan-id {
             type int32;
           }
           leaf flow-label-transmit {
             type int32;
           }
           leaf flow-label-receive {
             type int32;
           }
           leaf tdm-payload-size {
             type int32;
           }
           leaf tdm-bitrate {
             type int32;
           }
           leaf pw-status-code {
             type int32;
           }
           leaf cac-bandwidth-failure {
             type empty;
             description
               "Call admission control failure due to insufficient bandwidth";
           }
           leaf vpn-label {
             type int32;
             description
               "VPN label";
           }
           leaf route-label {
             type int32;
             description
               "Route label";
           }
           leaf route-labels {
             type string;
             description
               "Route label";
           }
           leaf mac-route-esi {
             type string;
             description
               "ESI";
           }
           leaf evpn-igmp-flags {
             type int32;
             description
               "IGMP flags";
           }
           leaf evpn-mld-flags {
             type int32;
             description
               "MLD flags";
           }
           leaf evpn-leave-reserved {
             type int32;
             description
               "IGMP Leave Reserved Field";
           }
           leaf evpn-leave-mrt {
             type int32;
             description
               "IGMP Leave Max Response Time";
           }
           leaf overlay-gateway-address {
             type jt:ipaddr;
             description
               "Overlay gateway address";
           }
           leaf reroute-address {
             type jt:ipaddr;
             description
               "Reroute address";
           }
           leaf bgp-otc {
             type int32;
           }
           leaf peer-id {
             type jt:ipaddr;
           }
           leaf rt-entry-ext-pfx-attr-flags {
             type string;
             description
               "Route entry extended prefix attribute flags";
           }
           leaf rt-entry-ext-pfx-source-rtrid {
             type string;
             description
               "Route entry extended prefix source rtr id";
           }
           leaf path-id {
             type string;
           }
           leaf gateway {
             type string;
             description
               "Sourcing gateway";
           }
           leaf rtrib-primary {
             type string;
             description
               "Primary routing table";
           }
           leaf rib-export-rtrib-primary {
             type string;
             description
               "RIB export primary routing table";
           }
           leaf rtrib-secondary {
             type string;
             description
               "Secondary routing table";
           }
           leaf indirect-nh-count {
             type int32;
             description
               "Number of indirect next hops";
           }
           leaf composite-nh-count {
             type int32;
             description
               "Number of composite next hops";
           }
           leaf helper-nhid {
             type uint32;
             description
               "Helper nexthop index";
           }
           leaf helper-refcount {
             type int32;
             description
               "Reference count of those needing helper route";
           }
           leaf backup-pe-group-name {
             type string;
             description
               "Name of the backup PE group";
           }
           leaf designated-forwarder {
             type string;
             description
               "Indicates if we are the designated forwarder for this route";
           }
           leaf rt-entry-opaque-data {
             type string;
             description
               "Opaque data associated with the route entry";
           }
           leaf rt-stats-id-grp-single-line {
             type string;
             description
               "Stats-id-group associated with the route entry";
           }
           leaf rt-entry-ext-pfx-sid-data {
             type string;
             description
               "Route entry extended prefix sid data";
           }
           leaf hidden-reason {
             type string;
             description
               "Protocol's reason for hiding the route";
           }
           leaf bgp-bmp-send-flag-start {
             type string;
           }
           leaf bgp-bmp-send-flag-pre {
             type string;
           }
           leaf bgp-bmp-send-flag-post {
             type string;
           }
           leaf bgp-bmp-send-flag-ribout-prepolicy {
             type string;
           }
           leaf bgp-bmp-send-flag-ribout-postpolicy {
             type string;
           }
           leaf bgp-bmp-send-flag-station {
             type string;
           }
           leaf bgp-nnh-nodes {
             type string;
             description
               "Next-next-hop nodes";
           }
           leaf bgp-nh-nnh-map {
             type string;
             description
               "Next-hop to next-next-hop map";
           }
           leaf bgp-profile-creation-failure-reason {
             type string;
             description
               "Reason for failing to create profile for next-next-hop map";
           }
           leaf bgp-nh-nnh-entry {
             type string;
             description
               "Next-hop to next-next-hop entry";
           }
           leaf glb-profile {
             type string;
             description
               "GLB Profile";
           }
           leaf glb-profile-id {
             type uint32;
             description
               "GLB Profile ID";
           }
           leaf rt-entry-stats {
             type string;
             description
               "Route entry statistics data";
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container route-flap-damping {
             leaf last-merit {
               type int32;
               description
                 "Last merit value";
             }
             leaf merit {
               type int32;
               description
                 "Current merit value";
             }
             leaf damping-parameters {
               type string;
             }
             leaf default-damping-parameters {
               type empty;
               description
                 "Default damping parameters used";
             }
             leaf last-update {
               type string;
             }
             leaf first-update {
               type string;
             }
             leaf route-flap-count {
               type int32;
               description
                 "Number of times this route has flapped";
             }
             leaf suppressed {
               type empty;
               description
                 "This route is suppressed";
             }
             leaf reuse-time {
               type string;
               description
                 "Time until this route is reusable";
             }
             leaf reuse-preference {
               type int32;
               description
                 "Preference to use when this route is reused";
             }
             leaf expire-time {
               type string;
               description
                 "Time when this damping entry expires";
             }
           }
           container nhh {
             leaf nh-type {
               type string;
               description
                 "Special next hop: Reject, Blackhole, Receive, Multicast, 
                 Local, or Unused";
             }
             leaf nh-index {
               type uint32;
               description
                 "Next-hop index";
             }
             leaf transport-class {
               type string;
               description
                 "Transport class name";
             }
             leaf nh-address {
               type string;
               description
                 "Address of next hop";
             }
             leaf nh-reference-count {
               type int32;
               description
                 "Number of references to this next hop";
             }
             leaf ext-int-intf-index {
               type int32;
               description
                 "Interface index of equal-external-internal multipath";
             }
             leaf nh-session-id {
               type uint32;
               description
                 "Nexthop session id";
             }
             leaf nh-key-opaque {
               type string;
               description
                 "Nexthop key opaque handle";
             }
             leaf nh-non-key-opaque {
               type string;
               description
                 "Nexthop non-key opaque handle";
             }
             leaf nh-key-opaque-dump {
               type string;
               description
                 "Nexthop key opaque app dump";
             }
             leaf nh-non-key-opaque-dump {
               type string;
               description
                 "Nexthop non-key opaque app dump";
             }
             leaf nh-flood-overflow {
               type empty;
               description
                 "Flood nexthop exceeds maximum branches";
             }
             leaf nh-kernel-id {
               type int32;
               description
                 "Table Id for this next hop";
             }
           }
           list nh-expand {
             key "nhe-name nhe-handle";
             description
               "Next-hop gateway information";
             leaf nhe-name {
               type string;
               description
                 "Name of next-hop";
             }
             leaf nhe-handle {
               type string;
               description
                 "Nexthop pointer";
             }
             leaf nhe-index {
               type int32;
               description
                 "Next-hop index";
             }
             leaf nhe-to {
               type string;
               description
                 "Nexthop address";
             }
             leaf nhe-mbr-count {
               type int32;
               description
                 "Number of child nexhops";
             }
             leaf nhe-mpls-label {
               type string;
               description
                 "Label of MPLS packet";
             }
           }
           list rt-session-id {
             key "rt-session-id-value";
             description
               "Session-IDs associated with route";
             leaf rt-session-id-value {
               type int32;
               description
                 "Value of session-id";
             }
             leaf rt-session-id-version {
               type int32;
               description
                 "Version of session-id";
             }
           }
           container flex-rt-statistics {
             description
               "Statistics associated with route";
             leaf flex-rt-statistics-pkts-count {
               type int32;
               description
                 "Packet count";
             }
             leaf flex-rt-statistics-pps {
               type int32;
               description
                 "Pps";
             }
             leaf flex-rt-statistics-bytes-count {
               type int32;
               description
                 "Byte count";
             }
             leaf flex-rt-statistics-bps {
               type int32;
               description
                 "Bps";
             }
           }
           leaf bgp-group-name {
             type string;
           }
           leaf bgp-no-label-reason {
             type string;
           }
           leaf sr-policy-distinguisher {
             type uint32;
           }
           leaf sr-policy-color {
             type uint32;
           }
           leaf sr-policy-endpoint {
             type jt:ipaddr;
           }
           leaf bgp-metric-flags {
             type string;
             description
               "BGP metrics flags";
           }
           leaf bgp-output-queue-class {
             type string;
             description
               "BGP output queue class";
           }
           leaf cluster-id {
             type string;
           }
           leaf originator {
             type string;
           }
           leaf bgp-aigp {
             type string;
             description
               "Accumulated IGP Metric";
           }
           leaf bgp-elc {
             type empty;
             description
               "Entropy label capable";
           }
           leaf bgp-elc-v2 {
             type empty;
             description
               "Entropy label capable version 2";
           }
           leaf bgp-elc-v3 {
             type empty;
             description
               "Entropy label capable version 3";
           }
           leaf bgp-nhc-unknown-characteristics-len {
             type uint32;
             description
               "Total length of NHC unknown characteristics";
           }
           leaf bgp-nhc-nh-valid {
             type string;
             description
               "Whether next hop field matches route next hop";
           }
           leaf bgp-nhc-characteristic-code {
             type uint32;
             description
               "NHC characteristic code";
           }
           leaf bgp-nhc-characteristic-len {
             type uint32;
             description
               "NHC characteristic length";
           }
           leaf bgp-nhc-characteristic-val {
             type string;
             description
               "NHC characteristic value";
           }
         }
         list kern-nhexpand {
           key "kern-nhe-name kern-nhe-handle";
           description
             "Next-hop gateway information";
           container srv6-info {
             leaf srv6-info-srh-sid-mode {
               type string;
               description
                 "Reduced/non-reduced mode for SRH";
             }
             leaf srv6-info-packet-mode {
               type string;
               description
                 "Packet mode for SRV6-Tunnel";
             }
             leaf srv6-info-srh-last-sid {
               type string;
               description
                 "Remove last sid for ACX";
             }
             leaf srv6-info-dyn-tunnel {
               type string;
               description
                 "SRv6 tunnel created dynamically";
             }
             leaf srv6-cos-propagation {
               type string;
               description
                 "SRv6 CoS propagation";
             }
             leaf srv6-ttl-propagation {
               type string;
               description
                 "SRv6 TTL propagation";
             }
             leaf srv6-source {
               type jt:ipaddr;
               description
                 "Source IPv6 address";
             }
             leaf srv6-destination {
               type jt:ipaddr;
               description
                 "Destination IPv6 address";
             }
             list srv6-segment-list {
               key "srv6-segment-list-index";
               description
                 "SRH Segment list";
               leaf srv6-segment-list-index {
                 type uint32;
                 description
                   "SRH segment list index";
               }
               leaf srv6-segment-list-addr {
                 type jt:ipaddr;
                 description
                   "SRH segment address";
               }
             }
           }
           leaf kern-nhe-platform-layer-input {
             type empty;
             description
               "Platform layer input nexthop";
           }
           leaf kern-nhe-platform-layer-output {
             type empty;
             description
               "Platform layer output nexthop";
           }
           leaf kern-nhe-in-kernel {
             type empty;
             description
               "Nexthop install in kernel";
           }
           leaf kern-nhe-fib-channel {
             type string;
             description
               "Fib channel in which route is installed";
           }
           leaf kern-nhe-name {
             type string;
             description
               "Name of next-hop";
           }
           leaf kern-nhe-subtype {
             type string;
             description
               "Nexthop Subtype";
           }
           leaf kern-nhe-handle {
             type string;
             description
               "Nexthop pointer";
           }
           leaf kern-nhe-index {
             type int32;
             description
               "Next-hop index";
           }
           leaf kern-gw-flags {
             type string;
             description
               "Nexthop gateway flags";
           }
           leaf kern-gw-opaque {
             type string;
             description
               "Nexthop gateway opaque data handle";
           }
           leaf kern-key-opaque {
             type string;
             description
               "Nexthop key opaque data handle";
           }
           leaf kern-nhe-to {
             type string;
             description
               "Nexthop address";
           }
           leaf kern-nhe-mbr-count {
             type int32;
             description
               "Number of child nexhops";
           }
           leaf kern-nhe-mpls-label {
             type string;
             description
               "Label of MPLS packet";
           }
           leaf kern-nhe-pnh {
             type string;
             description
               "Protocol Nexthop address";
           }
           leaf kern-nhe-fib-nh-str {
             type string;
             description
               "FIB inh or cnh identifier";
           }
           leaf kern-nhe-sessionid {
             type int32;
             description
               "Session ID";
           }
           leaf kern-nhe-tunnel-type {
             type string;
             description
               "Tunnel type";
           }
           leaf kern-nhe-tunnel-src {
             type string;
             description
               "Tunnel Source address";
           }
           leaf kern-nhe-tunnel-dest {
             type string;
             description
               "Tunnel Destination address";
           }
           leaf kern-nhe-tunnel-ep {
             type string;
             description
               "Tunnel Endpoint address";
           }
           leaf kern-nhe-tunnel-vxlan-encap-vni {
             type int32;
             description
               "VxLAN tunnel encap vni";
           }
           leaf kern-nhe-tunnel-vxlan-decap-vni {
             type int32;
             description
               "VxLAN tunnel decap vni";
           }
           leaf kern-nhe-translate-type {
             type string;
             description
               "Translation type";
           }
           leaf kern-nhe-translate-src {
             type string;
             description
               "Translation Source address";
           }
           leaf kern-nhe-translate-src-plen {
             type int32;
             description
               "Translation Source address prefix length";
           }
           leaf kern-nhe-translate-dest {
             type string;
             description
               "Translation Destination address";
           }
           leaf kern-nhe-translate-dest-plen {
             type int32;
             description
               "Translation Destination address prefix length";
           }
           leaf kern-nhe-tunnel-encap-rtb-id {
             type int32;
             description
               "Tunnel encap routing table id";
           }
           leaf kern-nhe-tunnel-decap-rtb-id {
             type int32;
             description
               "Tunnel decap routing table id";
           }
           leaf kern-nhe-interface {
             type string;
             description
               "Interface";
           }
           leaf kern-nhe-slice-gencfg-id {
             type int32;
             description
               "Slice-Gencfg ID";
           }
           leaf kern-nhe-sliceid {
             type int32;
             description
               "Slice ID";
           }
           leaf kern-nhe-fwf {
             type string;
             description
               "Filter Name";
           }
           leaf kern-nhe-flex-tunnel-info {
             type string;
             description
               "Flex-tunnel information of nexthop";
           }
           leaf kern-nhe-flags {
             type string;
             description
               "Nexthop flags";
           }
           leaf kern-nhe-stats-id-group {
             type string;
             description
               "Statistics ID Group associated with nexthop";
           }
           leaf kern-nhe-reference-count {
             type int32;
             description
               "Nexthop reference count";
           }
           leaf kern-elnh-address {
             type string;
             description
               "Address of Element Next-hop";
           }
         }
         leaf rt-entry-count {
           type int32;
           description
             "Number of route entries in this route";
         }
         leaf rt-announced-count {
           type int32;
           description
             "Number of announced route entries";
         }
         leaf rt-state {
           type string;
           description
             "State of this route";
         }
         leaf-list tsi {
           type string;
           description
             "Task-specific information";
         }
         container communities {
           leaf-list community {
             type string;
             description
               "Basic community";
           }
           leaf-list extended-community {
             type string;
             description
               "Extended community";
           }
           leaf-list ipv6-extended-community {
             type string;
             description
               "IPv6 extended community";
           }
         }
         list bgp-tunnel-attribute {
           key "tunnel-attribute-type";
           description
             "Tunne encap attribute information";
           leaf tunnel-attribute-type {
             type string;
           }
           leaf tunnel-attribute-rpf {
             type empty;
           }
           leaf tunnel-attribute-color {
             type uint32;
           }
           leaf tunnel-attribute-destination {
             type jt:ipaddr;
           }
         }
       }
       container route-state-history {
         list route-state-history-elements {
           key "rt-history-time";
           leaf rt-history-time {
             type string;
           }
           leaf rt-history-event {
             type string;
           }
         }
       }
     }
     list rt-martians {
       key "rt-martian-table-name";
       leaf rt-martian-table-name {
         type string;
         description
           "Name of the martian table, for example, inet.0";
       }
       list route-filter {
         key "address";
         description
           "Entries in martian table";
         leaf address {
           type jt:ipaddr;
         }
         leaf flags {
           type string;
           description
             "Enabled trace flags";
         }
         leaf extended-information {
           type string;
         }
         leaf match-count {
           type uint64;
         }
         container policy-extended-information {
           leaf account {
             type empty;
             description
               "Account";
           }
           leaf accept {
             type empty;
             description
               "Accept a route";
           }
           leaf advertise-locator {
             type empty;
             description
               "Advertise SRv6 locator";
           }
           leaf advertise-locator-internal {
             type empty;
             description
               "Advertise SRv6 locator internal";
           }
           leaf aggregate-bandwidth {
             type int32;
             description
               "Aggregate bandwidth";
           }
           leaf auto-link-bandwidth {
             type empty;
             description
               "Auto link bandwidth";
           }
           leaf push-label {
             type empty;
             description
               "Push label";
           }
           leaf analyze {
             type empty;
             description
               "Send to registered controllers for analysis";
           }
           leaf as-path-prepend {
             type uint32;
             description
               "Prepend AS numbers to an AS path (BGP only)";
           }
           leaf as-path-replace {
             type string;
             description
               "Replace AS numbers, or 'private' for an AS path (BGP only)";
           }
           leaf cos-next-hop-map {
             type string;
             description
               "The CoS-based next-hop map in forwarding table";
           }
           leaf damping {
             type string;
             description
               "Define BGP route flap damping parameters";
           }
           leaf default-action {
             type string;
             description
               "The default policy action";
           }
           leaf destination-class {
             type string;
             description
               "The destination class in forwarding table";
           }
           leaf dynamic-tunnel-attributes {
             type string;
             description
               "The dynamic tunnel attributes used for forwarding";
           }
           leaf fib-install-priority {
             type string;
             description
               "FIB install priority";
           }
           leaf filter {
             type string;
             description
               "Next-hop firewall filter";
           }
           leaf get-route-range {
             type empty;
             description
               "Get route range";
           }
           leaf ignore-service-label {
             type string;
             description
               "Ignore service labels";
           }
           leaf install-to-fib {
             type string;
             description
               "Install to FIB";
           }
           leaf ipv4-source-router-id {
             type empty;
           }
           leaf ipv4-source-router-id-address {
             type string;
             description
               "IPV4 source router id address";
           }
           leaf ipv6-source-router-id {
             type empty;
           }
           leaf ipv6-source-router-id-address {
             type string;
             description
               "IPV6 source router id address";
           }
           leaf label-allocation {
             type string;
             description
               "Label allocation mode";
           }
           leaf label-allocation-fallback-reject {
             type string;
             description
               "Suppress prefix export when label allocation fails";
           }
           leaf limit-bandwidth {
             type uint64;
             description
               "Limit advertised aggregate outbound link bandwidth";
           }
           leaf load-balance {
             type string;
             description
               "Load-balancing algorithm chosen";
           }
           leaf mhop-bfd-port {
             type uint32;
             description
               "Use port number 4784 for MPLS-BFD as per RFC5884";
           }
           leaf multipath-resolve {
             type string;
             description
               "Use all paths for resolution over this prefix";
           }
           leaf next {
             type string;
             description
               "Skip to next policy or term";
           }
           leaf no-backup {
             type empty;
             description
               "This prefix should not have backup";
           }
           leaf no-entropy-label-capability {
             type empty;
             description
               "Don't advertise entropy label capability";
           }
           leaf no-route-localize {
             type empty;
             description
               "No route localize";
           }
           leaf origin {
             type string;
             description
               "BGP origin attribute";
           }
           leaf p2mp-lsp-root {
             type jt:ipaddr;
             description
               "P2mp lsp root address";
           }
           leaf policy-priority {
             type string;
           }
           leaf reject {
             type empty;
             description
               "Reject a route";
           }
           leaf request-long-lived-ack {
             type empty;
             description
               "Advertise route after forwarding is programmed";
           }
           leaf resolution-map {
             type string;
             description
               "Resolution map";
           }
           leaf resolution-map-mode {
             type string;
             description
               "Resolution map modes";
           }
           leaf selected-mldp-egress {
             type string;
             description
               "This node should act as egress node for MLDP inband 
               signalling";
           }
           leaf send-withdrawal-on-route-change {
             type empty;
             description
               "Withdrawn route as change is not ack'd from forwarding";
           }
           leaf set-down-bit {
             type empty;
             description
               "Set down bit";
           }
           leaf slice {
             type string;
             description
               "Slice name";
           }
           leaf source-class {
             type string;
             description
               "The source class in forwarding table";
           }
           leaf sr-te-template {
             type string;
             description
               "SR TE template to apply";
           }
           leaf ssm-source {
             type jt:ipaddr;
             description
               "List of Sources for SSM mapping";
           }
           leaf trace {
             type empty;
             description
               "Log matches to a trace file";
           }
           leaf tunnel-end-point-address {
             type string;
             description
               "Set tunnel end-point address of tunnel";
           }
           leaf tunnel-termination-profile {
             type string;
             description
               "Tunnel termination profile name";
           }
           leaf validation-state {
             type string;
             description
               "Validation-state of a route";
           }
           container install-nexthop {
             description
               "The next hop to be used for forwarding";
             container except {
               leaf lsp {
                 type string;
                 description
                   "Label switched path name";
               }
               leaf lsp-regex {
                 type string;
                 description
                   "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
               leaf macsec-interfaces {
                 type empty;
               }
             }
             container fallback {
               leaf lsp {
                 type string;
                 description
                   "Label switched path name";
               }
               leaf lsp-regex {
                 type string;
                 description
                   "Label switched path name regular expression";
               }
               leaf non-labelled-nexthop {
                 type empty;
               }
               leaf non-lsp-nexthop {
                 type empty;
               }
               leaf static-lsp {
                 type string;
               }
               leaf static-lsp-regex {
                 type string;
               }
               leaf overlay-vxlan-interfaces {
                 type empty;
               }
               leaf macsec-interfaces {
                 type empty;
               }
             }
           }
           container map-to-interface {
             description
               "Set output logical interface";
             list interface {
               key "interface-name";
               description
                 "Interface name or address";
               leaf interface-name {
                 type string;
                 description
                   "Name of interface";
               }
               leaf interface-flags {
                 type string;
               }
             }
           }
           container then-metric {
           }
           container prefix-segment {
             description
               "The prefix segment attributes";
             container algorithm {
               leaf prefix-segment-index-value {
                 type uint32;
               }
               leaf algorithm-name {
                 type uint32;
               }
               leaf node-segment {
                 type empty;
               }
             }
           }
           list tunnel-attribute {
             description
               "Tunnel attribute information";
             leaf tunnel-type {
               type string;
               description
                 "Tunnel type";
             }
             leaf reference-count {
               type int32;
               description
                 "Reference count";
             }
             leaf tunnel-data {
               type string;
               description
                 "Tunnel Data";
             }
           }
           container source-based-forwarding {
             container sbf-attributes {
               leaf sbf-next-table {
                 type string;
               }
             }
           }
           container policy-label {
           }
         }
       }
     }
     list rt-ribexport {
       key "rt-ribexport-name";
       leaf rt-ribexport-name {
         type string;
         description
           "RIB export name";
       }
       leaf rt-ribexport-address {
         type string;
         description
           "RIB export address";
       }
       leaf rt-ribexport-flags {
         type string;
         description
           "RIB export flags";
       }
       leaf rt-ribexport-refcount {
         type uint32;
         description
           "RIB export refcount";
       }
       leaf rt-ribexport-address-family {
         type string;
         description
           "RIB export group address family";
       }
       leaf rt-ribexport-policy-name {
         type string;
         description
           "Policy name";
       }
       leaf-list rt-ribexport-import-name {
         type string;
         description
           "Import RIB name";
       }
       leaf rt-ribexport-trace-address {
         type string;
         description
           "RIB export group trace pointer";
       }
       leaf rt-ribexport-deleted {
         type empty;
         description
           "Ribexport deleted. Display of ribexport will end here.";
       }
     }
     list rt-ribgroup {
       key "rt-ribgroup-name rt-ribgroup-address";
       leaf rt-ribgroup-name {
         type string;
         description
           "Rib-group name";
       }
       leaf rt-ribgroup-address {
         type string;
         description
           "Rib-group address";
       }
       leaf rt-ribgroup-address-family {
         type string;
         description
           "Rib-group address family";
       }
       leaf rt-ribgroup-flags {
         type string;
         description
           "Rib-group flags";
       }
       leaf rt-ribgroup-refcount {
         type uint32;
         description
           "Rib-group refcount";
       }
       leaf rt-ribgroup-export-name {
         type string;
         description
           "Export RIB name";
       }
       leaf rt-ribgroup-import-name {
         type string;
         description
           "Import RIB name";
       }
       leaf rt-ribgroup-import-policy-name {
         type string;
         description
           "Import policy name";
       }
       leaf-list rt-ribgroup-import-secondary-name {
         type string;
         description
           "Import secondary RIB name";
       }
       leaf rt-ribgroup-union-head-name {
         type string;
         description
           "Rib-group union head name";
       }
       leaf rt-ribgroup-union-child-name {
         type string;
         description
           "Rib-group union child name";
       }
       leaf rt-ribgroup-deleted {
         type empty;
         description
           "Ribgroup deleted. Display of ribgroups will end here.";
       }
     }
     container rt-test-policy-prefix {
       leaf rt-policy-name {
         type string;
       }
       leaf rt-destination {
         type string;
         description
           "Route prefixes awaiting ACK";
       }
       leaf rt-prefix-length {
         type string;
       }
       container rt-test-policy-term {
         leaf rt-policy-term-name {
           type string;
         }
         leaf rt-policy-term-result {
           type string;
         }
         leaf rt-policy-term-action {
           type string;
         }
       }
     }
     container rt-test-policy {
       leaf rt-policy-name {
         type string;
       }
       leaf rt-route-accepted {
         type int32;
       }
       leaf rt-route-rejected {
         type int32;
       }
     }
     container rt-test-rib-sharding {
       leaf rt-destination {
         type string;
         description
           "Route prefixes awaiting ACK";
       }
       leaf rt-hash-prefix-to-shard {
         type string;
       }
     }
     list route-entry {
       leaf destination-address {
         type string;
       }
       leaf route-flags {
         type string;
       }
       leaf route-state {
         type string;
       }
       list nh-entry {
         leaf nexthop-address {
           type string;
         }
         leaf nexthop-type {
           type string;
         }
         leaf nexthop-index {
           type int32;
         }
         leaf nexthop-interface {
           type string;
         }
         leaf nexthop-local-address {
           type string;
         }
         list event-history {
           leaf event-timestamp {
             type string;
           }
           leaf event-id {
             type string;
           }
           leaf event-action {
             type string;
           }
           leaf event-information {
             type string;
           }
         }
       }
     }
   }
   grouping forwarding-table-information-block {
     list route-table {
       description
         "Denotes a routing table";
       leaf logical-system-name {
         type string;
         description
           "Name of this logical system";
       }
       leaf table-name {
         type string;
         description
           "Name of this routing table";
       }
       leaf route-table-deleted {
         type empty;
         description
           "Whether this routing table has been deleted";
       }
       leaf pbbn-table-name {
         type string;
         description
           "Name of corresponding PBBN routing table";
       }
       leaf pbbn-route-table-deleted {
         type empty;
         description
           "Whether corresponding PBBN routing table has been deleted";
       }
       leaf mac-vrf-fwd-inst-name {
         type string;
         description
           "Forwarding instance name for a macvrf instance";
       }
       leaf mac-vrf-fwd-inst-flag {
         type empty;
         description
           "Instance is internal macvrf forwarding instance";
       }
       leaf bd-name {
         type string;
         description
           "Name of this bridging domain";
       }
       leaf bridge-table-deleted {
         type empty;
         description
           "Whether this bridge table has been deleted";
       }
       leaf address-family {
         type string;
         description
           "Address family for this routing table";
       }
       leaf address-family-number {
         type string;
         description
           "If the address family name is unknown, print the number";
       }
       leaf enabled-protocols {
         type string;
         description
           "Protocols enabled for this routing table";
       }
       leaf bier-subdomain-id {
         type int32;
         description
           "BIER table subdomain id";
       }
       leaf bier-bsl {
         type int32;
         description
           "BIER table bit string length";
       }
       leaf bier-set-id {
         type int32;
         description
           "BIER table set identifier";
       }
       list rt-entry {
         description
           "Routing table entry for a destination";
         leaf rt-destination {
           type string;
           description
             "Destination address";
         }
         leaf destination-type {
           type string;
           description
             "Destination type for this entry";
         }
         leaf route-reference-count {
           type int32;
           description
             "Reference count for this destination entry";
         }
         list nh {
           description
             "Next hop for this routing table entry";
           leaf to {
             type string;
             description
               "Next-hop address for this entry";
           }
           leaf nh-type {
             type string;
             description
               "Next-hop type";
           }
           leaf nh-index {
             type int32;
             description
               "Index in next-hop table";
           }
           leaf nh-reference-count {
             type int32;
             description
               "Next-hop reference count";
           }
           leaf via {
             type string;
             description
               "Network interface name";
           }
           leaf nh-composite-num-nhs {
             type int32;
             description
               "Number of next hops in a composite next hop";
           }
           leaf nh-composite-nh-index {
             type int32;
             description
               "Index of next hops in a composite next hop";
           }
           leaf nh-composite-function {
             type string;
             description
               "Composition function for next hops in a composite next hop";
           }
           leaf nh-composite-num-derived-nhs {
             type int32;
             description
               "Number of derived next hops for a composite next hop";
           }
           leaf nh-composite-derived-nh-index {
             type int32;
             description
               "Index of derived next hops in a composite next hop";
           }
           leaf nh-label {
             type string;
             description
               "Next-hop tag label";
           }
           leaf nh-cfi-index {
             type int32;
             description
               "Next-hop core-facing-interface index";
           }
           leaf nh-key-flags {
             type int32;
             description
               "Next-hop key flags";
           }
           leaf subnh-index {
             type int32;
             description
               "Index of subnh in a nexthop";
           }
           leaf nh-weight {
             type int32;
             description
               "Next-hop weight";
           }
           leaf nh-balance {
             type int32;
             description
               "Next-hop balance";
           }
           leaf nh-uflags {
             type int32;
             description
               "Next-hop uflags";
           }
           leaf nh-le-beb-mac {
             type jt:mac-addr;
             description
               "The remote BEB MAC learned on bridge-domain of type PBN";
           }
           leaf alt-fwdnh-index {
             type int32;
             description
               "Alternate forward Index in next-hop table";
           }
           leaf nh-l3-interface {
             type string;
             description
               "Next-hop L3 interface";
           }
           list nh-l2-interface {
             leaf nh-l2-interface-name {
               type string;
               description
                 "Next-hop L2 interface";
             }
           }
         }
         leaf learn-vlan {
           type uint32;
           description
             "VLAN ID in the routing instance in which the MAC address was 
             learned";
         }
         leaf route-interface-index {
           type int32;
           description
             "Interface referenced by this route";
         }
         leaf rt-feature-id {
           type int32;
           description
             "Route feature ID";
         }
         leaf multicast-rpf-nh-index {
           type int32;
           description
             "Multicast rpf nh index for this route";
         }
         leaf route-p2mp-index {
           type int32;
           description
             "P2mp nexthop index";
         }
         leaf ifl-generation {
           type uint32;
           description
             "Creation time of the IFL when this MAC was learned";
         }
         leaf epoch {
           type uint32;
           description
             "Time when this MAC was learned";
         }
         leaf flood-token {
           type uint32;
           description
             "Layer2 flood token associated with this route entry";
         }
         leaf mac-sequence-number {
           type uint32;
           description
             "Sequence number assigned to this MAC";
         }
         leaf learn-mask {
           type uint32;
           description
             "Mask of PFEs where this MAC was learned";
         }
         leaf l2al-rtflags {
           type string;
           description
             "Route flags associated with MAC routes";
         }
         leaf route-flags {
           type string;
           description
             "Flags associated with this route entry";
         }
         leaf vlan-index {
           type uint32;
           description
             "VLAN index";
         }
         leaf vlan-flags {
           type uint32;
           description
             "VLAN flags";
         }
         leaf statistics-group-id {
           type uint32;
           description
             "Stats ID Group ID";
         }
         container rpf-information {
           description
             "Reverse-path forwarding check for this route";
           leaf via {
             type string;
             description
               "Network interface name";
           }
         }
         container vpls-mac-source-address-statistics {
           description
             "MAC source address statistics";
           leaf packet-count {
             type uint64;
             description
               "Packet count";
           }
           leaf byte-count {
             type uint64;
             description
               "Byte count";
           }
         }
         container vpls-mac-destination-address-statistics {
           description
             "MAC destination address statistics";
           leaf packet-count {
             type uint64;
             description
               "Packet count";
           }
           leaf byte-count {
             type uint64;
             description
               "Byte count";
           }
         }
         container bridge-mac-source-address-statistics {
           description
             "MAC source address statistics";
           leaf packet-count {
             type uint64;
             description
               "Packet count";
           }
           leaf byte-count {
             type uint64;
             description
               "Byte count";
           }
         }
         container bridge-mac-destination-address-statistics {
           description
             "MAC destination address statistics";
           leaf packet-count {
             type uint64;
             description
               "Packet count";
           }
           leaf byte-count {
             type uint64;
             description
               "Byte count";
           }
         }
         leaf snmp-idx {
           type uint32;
           description
             "KRT: IFD SNMP index";
         }
       }
       list route-table-summary {
         description
           "Routing table summary";
         leaf route-table-type {
           type string;
           description
             "Type for this routing table";
         }
         leaf route-count {
           type int32;
           description
             "Number of routes in this routing table";
         }
       }
       list rt-entry-with-guid {
         description
           "Routing entry with guid for a destination";
         leaf rt-destination {
           type string;
           description
             "Destination address";
         }
         leaf destination-type {
           type string;
           description
             "Destination type for this entry";
         }
         leaf route-reference-count {
           type int32;
           description
             "Reference count for this destination entry";
         }
         leaf to {
           type string;
           description
             "Next-hop address for this entry";
         }
         leaf nh-type {
           type string;
           description
             "Next-hop type";
         }
         leaf nh-index {
           type int32;
           description
             "Index in next-hop table";
         }
         leaf nh-reference-count {
           type int32;
           description
             "Next-hop reference count";
         }
         leaf via {
           type string;
           description
             "Network interface name";
         }
         leaf obj-guid {
           type uint64;
         }
         leaf rt-feature-id {
           type int32;
           description
             "Route feature ID";
         }
       }
     }
   }
   grouping fib-localization-information-block {
     container fib-localization-state {
       description
         "FIB localization state";
       leaf ready-fib-local {
         type string;
         description
           "Ready FIB-local FPCs";
       }
       leaf ready-fib-remote {
         type string;
         description
           "Ready FIB-remote FPCs";
       }
       leaf ready-normal {
         type string;
         description
           "Ready normal FPCs";
       }
       leaf state-read-failed-on-backup {
         type empty;
       }
       leaf state-read-error {
         type empty;
       }
     }
     container fib-localization-configuration {
       description
         "FIB localization configuration";
       leaf configured-protocols {
         type string;
         description
           "Configured FIB-local protocols";
       }
       leaf configured-fib-local {
         type string;
         description
           "Configured FIB-local FPCs";
       }
       leaf configured-fib-remote {
         type string;
         description
           "Configured FIB-remote FPCs";
       }
       leaf configuration-read-error {
         type empty;
       }
     }
     container fpc-slot-to-forwarding-engine-addresses-map {
       description
         "All known FPC slot-to-Forwarding-Engine-addresses mappings";
       leaf-list map-entry {
         type string;
         description
           "Map of an FPC slot to Forwarding Engine addresses";
       }
       leaf map-read-error {
         type empty;
       }
     }
   }
   grouping vpn-localization-information-block {
     container vpn-info {
       leaf vpn-name {
         type string;
         description
           "Name of the routing table";
       }
       leaf vpn-is-localized {
         type string;
         description
           "Is the routing table localized";
       }
       leaf vpn-index {
         type int32;
         description
           "Index of the routing table";
       }
       leaf vpn-fpc-bitmap-conf {
         type string;
         description
           "FPC bitmap in config";
       }
       leaf vpn-fpc-bitmap-kern {
         type string;
         description
           "FPC bitmap in kernel";
       }
       leaf vpn-localization-status {
         type string;
         description
           "Localization status";
       }
       leaf vpn-localization-type {
         type string;
         description
           "Localization type";
       }
       leaf vpn-family {
         type string;
         description
           "Address family of the routing table";
       }
       leaf vpn-fpc-list-conf {
         type string;
         description
           "Local FPC list";
       }
       leaf vpn-fpc-list-kern {
         type string;
         description
           "Local FPC list";
       }
     }
   }
   grouping route-tracking-information-block {
     list route-tracking-table {
       leaf routing-table-name {
         type string;
         description
           "Routing table name";
       }
       container route-tracking-table-entries {
         list route-tracking-table-entry {
           leaf destination {
             type jt:ipprefix;
             description
               "RPM route destination";
           }
           leaf metric {
             type uint32;
             description
               "RPM route metric";
           }
           leaf preference {
             type uint32;
             description
               "RPM route preference";
           }
           leaf route-tag {
             type uint32;
             description
               "RPM route tag";
           }
           leaf routing-table-name {
             type string;
             description
               "Routing table name";
           }
           container rpm-route-next-hop-entries {
             list rpm-route-next-hop-entry {
               leaf next-hop {
                 type jt:ipaddr;
                 description
                   "RPM route next-hop";
               }
               leaf owner {
                 type string;
                 description
                   "Test owner name";
               }
               leaf test-name {
                 type string;
                 description
                   "Name of test";
               }
               leaf route-state {
                 type string;
                 description
                   "RPM tracked route state";
               }
               leaf next-hop-type {
                 type string;
                 description
                   "RPM route next-hop type (i.e., list or ucast)";
               }
             }
           }
         }
       }
     }
   }
   grouping service-mapping-information-block {
     container sm-overview {
       leaf tc-auto-create {
         type string;
         description
           "Auto creation of Transport class";
       }
     }
     list transport-class-information {
       leaf tc-name {
         type string;
         description
           "Auto generated name";
       }
       leaf tc-cfg-name {
         type string;
         description
           "Configured name";
       }
       leaf tc-color {
         type uint32;
         description
           "Color value, auto derives other attributes";
       }
       leaf tc-ref-cnt {
         type uint32;
         description
           "Reference count";
       }
       leaf tc-v4-prefix-cnt {
         type int32;
         description
           "Number of IPv4 prefixes in this Transport class RIB";
       }
       leaf tc-v6-prefix-cnt {
         type int32;
         description
           "Number of IPv6 prefixes in this Transport class RIB";
       }
       leaf tc-map-community {
         type string;
         description
           "BGP community that maps to default resolution scheme of this 
           Transport class";
       }
       leaf tc-rt-community {
         type string;
         description
           "The BGP Route Target Extended community identifying this 
           Transport class";
       }
       leaf tc-import-policy {
         type string;
         description
           "Transport Route Target import policy";
       }
       leaf tc-export-policy {
         type string;
         description
           "Transport Route Target export policy";
       }
       leaf tc-rt-instance {
         type string;
         description
           "The Routing instance helping with import, export of transport 
           routes";
       }
       leaf tc-flags {
         type string;
         description
           "Transport class interesting flags";
       }
       leaf tc-type {
         type string;
         description
           "Transport class type";
       }
     }
   }
   grouping instance-information-block {
     list instance-core {
       key "instance-name";
       leaf instance-name {
         type string;
       }
       leaf instance-type {
         type string;
       }
       list instance-rib {
         key "irib-name";
         leaf irib-name {
           type string;
         }
         leaf irib-active-count {
           type int32;
         }
         leaf irib-holddown-count {
           type int32;
         }
         leaf irib-hidden-count {
           type int32;
         }
         leaf irib-route-count {
           type int32;
         }
         leaf irib-restart-state {
           type string;
         }
         leaf irib-opaque-data {
           type uint64;
         }
       }
       container instance-localize {
         list instance-localize-scope {
           key "localize-scope";
           leaf localize-scope {
             type string;
           }
         }
         list instance-localize-interface {
           key "interface-name";
           leaf interface-name {
             type string;
             description
               "Name of interface";
           }
           leaf address-family {
             type string;
           }
           leaf nexthop-index {
             type int32;
           }
         }
       }
       leaf instance-description {
         type string;
       }
       leaf router-id {
         type jt:ipaddr;
       }
       leaf ipv6-router-id {
         type string;
       }
       leaf instance-state {
         type string;
       }
       leaf instance-restart-state {
         type string;
       }
       leaf instance-pathsel-timeout {
         type int32;
       }
       leaf instance-proto-gr-enabled {
         type string;
       }
       leaf instance-lsi-state {
         type string;
       }
       leaf pre-export-filter {
         type string;
       }
       list instance-vrf {
         key "route-distinguisher";
         leaf route-distinguisher {
           type string;
           description
             "Name of the route-distinguisher";
         }
         leaf vrf-import {
           type string;
         }
         leaf vrf-export {
           type string;
         }
         leaf vrf-import-target {
           type string;
         }
         leaf vrf-export-target {
           type string;
         }
         leaf vrf-label-allocation {
           type string;
         }
         leaf vrf-label-substitution {
           type string;
         }
         leaf fast-reroute-priority {
           type string;
         }
         leaf vrf-edge-protection-context-id {
           type jt:ipaddr;
         }
       }
       list instance-interface {
         key "interface-name";
         leaf interface-name {
           type string;
           description
             "Name of interface";
         }
       }
       list instance-vpls-meshgroup {
         key "meshgroup-name";
         leaf meshgroup-name {
           type string;
         }
         leaf route-distinguisher {
           type string;
           description
             "Name of the route-distinguisher";
         }
         leaf meshgroup-vrf-import {
           type string;
         }
         leaf meshgroup-vrf-export {
           type string;
         }
         leaf meshgroup-vrf-import-target {
           type string;
         }
         leaf meshgroup-vrf-export-target {
           type string;
         }
       }
       list instance-rib-extensive {
         key "irib-name";
         leaf irib-name {
           type string;
         }
         leaf irib-route-count {
           type int32;
         }
         leaf irib-active-count {
           type int32;
         }
         leaf irib-holddown-count {
           type int32;
         }
         leaf irib-hidden-count {
           type int32;
         }
         leaf irib-restart-state {
           type string;
         }
         leaf irib-opaque-data {
           type uint64;
         }
         leaf irib-ref-count {
           type int32;
         }
         leaf irib-rt-bit {
           type int32;
         }
         leaf irib-no-of-dest {
           type int32;
         }
         leaf irib-rtt-state {
           type string;
         }
         leaf irib-no-of-aux-routes {
           type int32;
         }
         leaf irib-flash-job-prio {
           type string;
         }
         leaf irib-snmp-job {
           type string;
         }
       }
     }
   }
   grouping operational-routing-instance-information-block {
     leaf-list instance-name {
       type string;
     }
   }
   grouping route-summary-information-block {
     leaf as-number {
       type int32;
     }
     leaf router-id {
       type jt:ipaddr;
     }
     leaf maximum-ecmp {
       type int32;
     }
     leaf note-network-services-mode {
       type string;
     }
     container routing-highwatermark {
       leaf rt-uniq-highwatermark {
         type int32;
         description
           "RIB unique destination routes high watermark";
       }
       leaf rt-uniq-highwatermark-ts {
         type string;
         description
           "RIB unique destination routes high watermark time stamp";
       }
       leaf rt-uniq-tavg-watermark {
         type int32;
         description
           "RIB unique destination routes time averaged watermark";
       }
       leaf rt-all-highwatermark {
         type int32;
         description
           "RIB routes high watermark";
       }
       leaf rt-all-highwatermark-ts {
         type string;
         description
           "RIB routes high watermark time stamp";
       }
       leaf rt-all-tavg-watermark {
         type int32;
         description
           "RIB routes time averaged watermark";
       }
       leaf rt-fib-highwatermark {
         type int32;
         description
           "FIB routes high watermark";
       }
       leaf rt-fib-highwatermark-ts {
         type string;
         description
           "FIB routes high watermark time stamp";
       }
       leaf rt-fib-tavg-watermark {
         type int32;
         description
           "FIB routes time averaged watermark";
       }
       leaf rt-vrf-highwatermark {
         type int32;
         description
           "VRF type routing instances high watermark";
       }
       leaf rt-vrf-highwatermark-ts {
         type string;
         description
           "VRF type routing instances high watermark";
       }
     }
     container route-table-error {
       leaf route-table-error-str {
         type string;
         description
           "Routing table error";
       }
     }
     list route-table {
       key "table-name";
       leaf table-name {
         type string;
         description
           "Unicast routing table";
       }
       leaf destination-count {
         type int32;
         description
           "Number of destinations in this rib";
       }
       leaf total-route-count {
         type int32;
       }
       leaf active-route-count {
         type int32;
         description
           "Active routes";
       }
       leaf holddown-route-count {
         type int32;
       }
       leaf hidden-route-count {
         type int32;
       }
       leaf restart-state {
         type string;
       }
       leaf family-prefix-max {
         type int32;
       }
       leaf family-prefix-threshold {
         type int32;
       }
       leaf family-prefix-label {
         type string;
       }
       leaf family-route-max {
         type int32;
       }
       leaf family-route-threshold {
         type int32;
       }
       leaf family-route-limit-label {
         type string;
       }
       leaf global-prefix-max {
         type int32;
       }
       leaf global-prefix-threshold {
         type int32;
       }
       leaf global-prefix-label {
         type string;
       }
       leaf global-route-max {
         type int32;
       }
       leaf global-route-threshold {
         type int32;
       }
       leaf global-route-limit-label {
         type string;
       }
       leaf prefix-max {
         type int32;
       }
       leaf prefix-threshold {
         type int32;
       }
       leaf prefix-label {
         type string;
       }
       leaf route-max {
         type int32;
       }
       leaf route-threshold {
         type int32;
       }
       leaf route-limit-label {
         type string;
       }
       list protocols {
         key "protocol-name";
         leaf protocol-name {
           type string;
         }
         leaf protocol-route-count {
           type int32;
           description
             "Total protocol routes";
         }
         leaf active-route-count {
           type int32;
           description
             "Active routes";
         }
       }
       list rt-prefix-dist {
         key "rt-prefix-length";
         leaf rt-prefix-length {
           type string;
         }
         leaf rt-prefix-count {
           type int32;
         }
       }
       list rt {
         key "rt-destination";
         leaf rt-destination {
           type string;
           description
             "Route prefixes awaiting ACK";
         }
         leaf rt-prefix-length {
           type string;
         }
         list rt-entry {
           leaf active-tag {
             type string;
             description
               "Visual indication of active state of this route entry";
           }
           leaf validation-state {
             type string;
             description
               "Validation-state of a route";
           }
           leaf protocol-name {
             type string;
           }
           leaf preference {
             type int32;
             description
               "Preference for the route";
           }
           leaf metric {
             type int32;
           }
           leaf metric2 {
             type int32;
           }
           leaf nh-type {
             type string;
             description
               "Special next hop: Reject, Blackhole, Receive, Multicast, 
               Local, or Unused";
           }
           leaf as-path {
             type string;
             description
               "Name of AS path regular expression (BGP only)";
           }
           leaf last-active {
             type empty;
             description
               "This route entry was the last active route entry";
           }
           leaf current-active {
             type empty;
             description
               "This route entry is currently active";
           }
           leaf bgp-rt-mult-nh-idx {
             type uint32;
             description
               "BGP multipath nexthop index";
           }
           leaf deleted {
             type empty;
           }
           leaf nh-erc-btid-id {
             type string;
             description
               "ERC Backtrace ID";
           }
           leaf nh-erc-btid-op {
             type string;
             description
               "ERC BTID Operation";
           }
           leaf nh-erc-btid-nreference {
             type int32;
             description
               "ERC Number of BTID References";
           }
           leaf nh-erc-btid-bt {
             type string;
             description
               "ERC BTID Backtrace ";
           }
           container route-record {
             leaf rt-recorded {
               type string;
             }
             leaf nh-address {
               type string;
               description
                 "Address of next hop";
             }
             leaf as-index {
               type int32;
             }
             leaf as-recorded {
               type string;
             }
             leaf com-index {
               type int32;
             }
             leaf com-recorded {
               type string;
             }
           }
           list route-data-dcf {
             key "trunk-id snmp-idx";
             leaf trunk-id {
               type int32;
               description
                 "Trunk Identifier associated with the LAG port";
             }
             leaf snmp-idx {
               type int32;
               description
                 "IFD SNMP index";
             }
             leaf ts {
               type int32;
               description
                 "Timestamp associated with the route";
             }
             leaf class-id {
               type int32;
               description
                 "Class identifier associated with the route";
             }
             leaf rt-flags {
               type string;
               description
                 "Flags associated with the route";
             }
             leaf rt-type {
               type string;
               description
                 "Route type associated with the route";
             }
             leaf rt-proto {
               type string;
               description
                 "Protocol associated with the route";
             }
             leaf rt-l2domain {
               type int32;
               description
                 "L2domain associated with the route";
             }
             leaf rt-mac-addr {
               type jt:mac-addr;
               description
                 "Mac address associated with the route";
             }
             list snpa {
               key "snpa-type";
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
             }
             leaf snpa-count {
               type int32;
               description
                 "Number of SNPAs in this route";
             }
             leaf snpa-length {
               type int32;
               description
                 "Total length of the SNPAs, in bytes";
             }
             container multicast-member-map-data {
               description
                 "Multicast member map";
               leaf multicast-root-hash {
                 type int32;
               }
               leaf multicast-core-hash {
                 type int32;
               }
               leaf multicast-edge-hash {
                 type int32;
               }
               leaf multicast-member-map {
                 type string;
               }
             }
             container layer3-multicast-data {
               description
                 "Layer3 multicast core key";
               leaf layer3-multicast-corekey {
                 type int32;
               }
             }
             container multicast-vsg-corekey-data {
               description
                 "Vsg multicast core key";
               leaf multicast-vsg-corekey-key {
                 type int32;
               }
               leaf multicast-vsg-corekey-len {
                 type int32;
               }
             }
           }
           container rtd-flow-dep {
             leaf flow-dep-state {
               type string;
             }
             leaf flow-origin {
               type jt:ipaddr;
               description
                 "Originator of the flow information";
             }
             leaf flow-next-as {
               type uint32;
               description
                 "Neighbor AS of the flow information";
             }
             container flow-ucast-rt {
               description
                 "Unicast route used for resolution";
               leaf flow-rtn-dest {
                 type jt:ipaddr;
                 description
                   "Destination address";
               }
               leaf flow-rtn-plen {
                 type int32;
                 description
                   "Prefix length";
               }
               leaf flow-rtn-state {
                 type string;
                 description
                   "Validation entry state";
               }
             }
           }
           container bgp-path-attributes {
             container attr-as-path {
               description
                 "AS Path Attribute";
               leaf attr-length {
                 type string;
               }
               leaf flags {
                 type string;
                 description
                   "Enabled trace flags";
               }
               leaf path-length {
                 type string;
               }
               leaf attr-value {
                 type string;
               }
             }
             container attr-as4-path {
               description
                 "4-byte AS Path Attribute";
               leaf attr-length {
                 type string;
               }
               leaf path-length {
                 type string;
               }
               leaf flags {
                 type string;
                 description
                   "Enabled trace flags";
               }
               leaf attr-value {
                 type string;
               }
             }
             container attr-as-path-effective {
               description
                 "Effective AS-Path Attribute";
               leaf attr-length {
                 type string;
               }
               leaf aspath-effective-string {
                 type string;
               }
               leaf path-length {
                 type string;
               }
               leaf attr-value {
                 type string;
               }
               leaf flags {
                 type string;
                 description
                   "Enabled trace flags";
               }
             }
             container attr-aggregator {
               description
                 "Aggregator Attribute";
               leaf attr-length {
                 type string;
               }
               leaf flags {
                 type string;
                 description
                   "Enabled trace flags";
               }
               leaf aggr-as-number {
                 type string;
               }
               leaf aggr-router-id {
                 type string;
               }
             }
             container attr-aggregator4 {
               description
                 "Aggregator4 Attribute";
               leaf attr-length {
                 type string;
               }
               leaf flags {
                 type string;
                 description
                   "Enabled trace flags";
               }
               leaf aggr-as-number {
                 type string;
               }
               leaf aggr-router-id {
                 type string;
               }
             }
             container attr-cluster-list {
               description
                 "Cluster List Attribute";
               leaf attr-length {
                 type string;
               }
               leaf attr-value {
                 type string;
               }
             }
             container attr-originator-id {
               description
                 "Originator Attribute";
               leaf attr-length {
                 type string;
               }
               leaf attr-value {
                 type string;
               }
             }
             leaf domain-path {
               type string;
             }
             leaf attr-otc {
               type int32;
               description
                 "Only-to-customer attribute";
             }
             container attr-unrecognized {
               description
                 "Unrecognized attributes";
               leaf attr-length {
                 type string;
               }
               leaf attr-flags {
                 type string;
               }
               leaf attr-code {
                 type string;
               }
               leaf attr-value {
                 type string;
               }
             }
           }
           container communities {
             leaf-list community {
               type string;
               description
                 "Basic community";
             }
             leaf-list extended-community {
               type string;
               description
                 "Extended community";
             }
             leaf-list ipv6-extended-community {
               type string;
               description
                 "IPv6 extended community";
             }
           }
           list bgp-tunnel-attribute {
             key "tunnel-attribute-type";
             description
               "Tunne encap attribute information";
             leaf tunnel-attribute-type {
               type string;
             }
             leaf tunnel-attribute-rpf {
               type empty;
             }
             leaf tunnel-attribute-color {
               type uint32;
             }
             leaf tunnel-attribute-destination {
               type jt:ipaddr;
             }
           }
           container attrset {
             container bgp-prefix-sid-attr {
               description
                 "BGP Prefix SID Attribute";
               container bgp-prefix-sid-attr-label-idx-tlv {
                 leaf bgp-prefix-sid-label-idx-index {
                   type int32;
                 }
                 leaf bgp-prefix-sid-attr-status {
                   type string;
                 }
               }
               container bgp-prefix-sid-attr-srgb-tlv {
                 list bgp-prefix-sid-srgb-block {
                   key "bgp-prefix-sid-srgb-block-start-label";
                   leaf bgp-prefix-sid-srgb-block-start-label {
                     type int32;
                   }
                   leaf bgp-prefix-sid-srgb-block-range {
                     type int32;
                   }
                 }
               }
               container bgp-prefix-sid-attr-service-tlv {
                 leaf bgp-prefix-sid-srv6-sid-value {
                   type jt:ipaddr;
                 }
                 leaf bgp-prefix-sid-attr-service-tlv-type {
                   type uint32;
                 }
                 leaf bgp-prefix-sid-attr-tlv-type {
                   type uint32;
                 }
                 leaf bgp-prefix-sid-srv6-sid-bh {
                   type uint32;
                 }
                 leaf bgp-prefix-sid-srv6-sid-bl {
                   type uint32;
                 }
                 leaf bgp-prefix-sid-srv6-sid-nl {
                   type uint32;
                 }
                 leaf bgp-prefix-sid-srv6-sid-fl {
                   type uint32;
                 }
                 leaf bgp-prefix-sid-srv6-sid-al {
                   type uint32;
                 }
                 leaf bgp-prefix-sid-srv6-sid-tl {
                   type uint32;
                 }
                 leaf bgp-prefix-sid-srv6-sid-to {
                   type uint32;
                 }
               }
               container bgp-prefix-sid-attr-unknown-tlvs {
                 list bgp-prefix-sid-attr-unknown-tlv {
                   key "bgp-prefix-sid-unknown-tlv-type";
                   leaf bgp-prefix-sid-unknown-tlv-type {
                     type uint32;
                   }
                   leaf bgp-prefix-sid-unknown-tlv-len {
                     type uint32;
                   }
                 }
               }
             }
             leaf attrset-as {
               type int32;
               description
                 "Originator AS";
             }
             leaf med {
               type int32;
               description
                 "Multiple exit discriminator";
             }
             leaf local-preference {
               type int32;
             }
             leaf as-path {
               type string;
               description
                 "Name of AS path regular expression (BGP only)";
             }
             leaf pmsi {
               type string;
               description
                 "P-multicast service interface";
             }
             leaf cluster-id {
               type string;
             }
             leaf originator {
               type string;
             }
             leaf connector {
               type string;
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
           }
           container link-state-information {
             container link-state-link {
               leaf link-name {
                 type string;
               }
               leaf color {
                 type int32;
               }
               leaf metric {
                 type int32;
               }
               leaf te-metric {
                 type int32;
                 description
                   "LSP TE metric";
               }
               leaf link-avg-delay {
                 type uint32;
               }
               leaf link-min-delay {
                 type uint32;
               }
               leaf link-max-delay {
                 type uint32;
               }
               leaf link-avg-delay-var {
                 type uint32;
               }
               leaf ldp-support {
                 type string;
               }
               leaf rsvpte-support {
                 type string;
               }
               leaf maximum-bw {
                 type uint64;
               }
               leaf reservable-bw {
                 type uint64;
               }
               container protections {
                 leaf-list protection-type {
                   type string;
                   description
                     "LSP protection desired";
                 }
               }
               container link-srlgs {
                 leaf-list link-srlg {
                   type string;
                 }
               }
               container unreserved-bws {
                 list unreserved-bw {
                   key "unreserved-bw-priority";
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   key "link-lan-adj-sid-label";
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   key "link-p2p-adj-sid-label";
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
               container link-bgp-peer-sids {
                 list link-bgp-peer-sid {
                   key "link-bgp-peer-sid-label";
                   leaf link-bgp-peer-sid-label {
                     type uint32;
                   }
                   leaf link-bgp-peer-sid-flags {
                     type string;
                   }
                   leaf link-bgp-peer-sid-weight {
                     type uint32;
                   }
                 }
               }
               container link-srv6-end-x-sids {
                 list link-srv6-end-x-sid {
                   key "link-srv6-end-x-sid-val";
                   leaf link-srv6-end-x-sid-type {
                     type string;
                   }
                   leaf link-srv6-end-x-sid-val {
                     type jt:ipv6addr;
                   }
                   leaf link-srv6-end-x-sid-flags {
                     type string;
                   }
                   leaf link-srv6-end-x-sid-weight {
                     type int32;
                   }
                   leaf link-srv6-end-x-sid-algo {
                     type int32;
                   }
                   leaf link-srv6-end-x-sid-func {
                     type string;
                   }
                   leaf link-srv6-end-x-sid-lan-neighbor-id {
                     type string;
                   }
                   container link-srv6-end-x-sid-sstlv {
                     leaf link-srv6-end-x-sid-sstlv-header {
                       type empty;
                     }
                     leaf link-srv6-end-x-sid-sstlv-blen {
                       type uint32;
                     }
                     leaf link-srv6-end-x-sid-sstlv-nlen {
                       type uint32;
                     }
                     leaf link-srv6-end-x-sid-sstlv-flen {
                       type uint32;
                     }
                     leaf link-srv6-end-x-sid-sstlv-alen {
                       type uint32;
                     }
                   }
                 }
               }
               container link-msd-types {
                 list link-msd-entry {
                   key "link-msd-type";
                   leaf link-msd-type {
                     type uint32;
                   }
                   leaf link-msd-value {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf-list node-area {
                   type string;
                 }
               }
               container node-ipv4-router-ids {
                 leaf-list node-ipv4-router-id {
                   type jt:ipaddr;
                 }
               }
               container node-ipv6-router-ids {
                 leaf-list node-ipv6-router-id {
                   type jt:ipaddr;
                 }
               }
               container node-topologies {
                 list node-topology {
                   key "id";
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   key "node-spring-srgb-block-start node-spring-srgb-block-range";
                   leaf node-spring-srgb-block-start {
                     type uint32;
                   }
                   leaf node-spring-srgb-block-range {
                     type uint32;
                   }
                   leaf node-spring-srgb-block-flags {
                     type string;
                   }
                 }
               }
               container node-msd-types {
                 list node-msd-entry {
                   key "node-msd-type";
                   leaf node-msd-type {
                     type uint32;
                   }
                   leaf node-msd-value {
                     type uint32;
                   }
                 }
               }
               container node-srv6-capability {
                 leaf node-srv6-capability-flag {
                   type uint32;
                 }
               }
               container node-spring-algorithms {
                 list node-spring-algorithm {
                   key "node-spring-algorithm-type";
                   leaf node-spring-algorithm-type {
                     type uint32;
                   }
                 }
               }
               container node-spring-falgo-defs {
                 list node-spring-falgo-def {
                   key "node-spring-falgo-def-algo";
                   leaf node-spring-falgo-def-algo {
                     type uint32;
                   }
                   leaf node-spring-falgo-def-metric-type {
                     type uint32;
                   }
                   leaf node-spring-falgo-def-calculation-type {
                     type uint32;
                   }
                   leaf node-spring-falgo-def-priority {
                     type uint32;
                   }
                   leaf node-spring-falgo-def-flags {
                     type string;
                   }
                   leaf node-spring-falgo-def-include-any {
                     type string;
                   }
                   leaf node-spring-falgo-def-exclude {
                     type string;
                   }
                   leaf node-spring-falgo-def-include-all {
                     type string;
                   }
                 }
               }
             }
             list link-state-te-policy-cp-segment {
             }
             container link-state-te-policy-cp {
               leaf link-state-te-policy-cp-name {
                 type string;
               }
               leaf link-state-te-policy-cp-flags {
                 type string;
               }
               leaf link-state-te-policy-cp-preference {
                 type uint32;
               }
               leaf link-state-te-policy-cp-priority {
                 type uint32;
               }
               leaf link-state-te-policy-cp-constraint-header {
                 type empty;
               }
               leaf link-state-te-policy-cp-constraint-flags {
                 type string;
               }
               leaf link-state-te-policy-cp-mtid {
                 type uint32;
               }
               leaf link-state-te-policy-cp-algo {
                 type uint32;
               }
               leaf link-state-te-policy-cp-exclude-any {
                 type string;
               }
               leaf link-state-te-policy-cp-include-any {
                 type string;
               }
               leaf link-state-te-policy-cp-include-all {
                 type string;
               }
               leaf link-state-te-policy-cp-bandwidth {
                 type uint32;
               }
               leaf link-state-te-policy-cp-bsid-flags {
                 type string;
               }
               leaf link-state-te-policy-cp-mpls-bsid {
                 type uint32;
               }
               leaf link-state-te-policy-cp-mpls-spec-bsid {
                 type uint32;
               }
               leaf link-state-te-policy-cp-segment-list-count {
                 type int32;
               }
               container link-state-te-policy-cp-srv6-bsid-info {
                 leaf link-state-te-policy-cp-srv6-bsid-flags {
                   type string;
                   description
                     "SRv6 BSID flags";
                 }
                 leaf link-state-te-policy-cp-srv6-bsid {
                   type jt:ipv6addr;
                   description
                     "SRv6 BSID";
                 }
                 leaf link-state-te-policy-cp-srv6-spec-bsid {
                   type jt:ipv6addr;
                   description
                     "Specified SRv6 BSID";
                 }
                 leaf link-state-te-policy-cp-srv6-bsid-ep-bhv {
                   type uint32;
                   description
                     "SRv6 BSID endpoint behavior";
                 }
                 leaf link-state-te-policy-cp-srv6-bsid-ep-bhv-flags {
                   type string;
                   description
                     "SRv6 BSID endpoint behavior flags";
                 }
                 leaf link-state-te-policy-cp-srv6-bsid-ep-bhv-algo {
                   type uint32;
                   description
                     "SRv6 BSID endpoint behavior algo";
                 }
                 leaf link-state-te-policy-cp-srv6-bsid-sstlv {
                   type string;
                   description
                     "SRv6 BSID endpoint behavior SSTLV";
                 }
               }
               list link-state-te-policy-cp-segment-list {
                 key "link-state-te-policy-cp-segment-list-index";
                 leaf link-state-te-policy-cp-segment-list-index {
                   type int32;
                 }
                 leaf link-state-te-policy-cp-segment-list-flags {
                   type string;
                 }
                 leaf link-state-te-policy-cp-segment-list-mtid {
                   type uint32;
                 }
                 leaf link-state-te-policy-cp-segment-list-weight {
                   type uint32;
                 }
                 leaf link-state-te-policy-cp-segment-list-algo {
                   type uint32;
                 }
                 leaf link-state-te-policy-cp-segment-list-metric-type {
                   type string;
                 }
                 leaf link-state-te-policy-cp-segment-list-metric-value {
                   type uint32;
                 }
                 leaf link-state-te-policy-cp-segment-count {
                   type int32;
                 }
                 leaf link-state-te-policy-cp-segment-header {
                   type empty;
                 }
                 list link-state-te-policy-cp-segment {
                   leaf link-state-te-policy-cp-mpls-segment-id {
                     type uint32;
                   }
                   leaf link-state-te-policy-cp-srv6-segment-id {
                     type jt:ipv6addr;
                   }
                   leaf link-state-te-policy-cp-segment-descriptor {
                     type jt:ipaddr;
                   }
                   leaf link-state-te-policy-cp-segment-flags {
                     type string;
                   }
                   leaf link-state-te-policy-cp-segment-ep-bhv {
                     type string;
                   }
                   leaf link-state-te-policy-cp-segment-ep-bhv-flags {
                     type uint32;
                   }
                   leaf link-state-te-policy-cp-segment-ep-bhv-algo {
                     type uint32;
                   }
                   container link-state-te-policy-cp-segment-sstlv {
                     leaf link-state-te-policy-cp-segment-sstlv-header {
                       type empty;
                     }
                     leaf link-state-te-policy-cp-segment-sstlv-blen {
                       type uint32;
                     }
                     leaf link-state-te-policy-cp-segment-sstlv-nlen {
                       type uint32;
                     }
                     leaf link-state-te-policy-cp-segment-sstlv-flen {
                       type uint32;
                     }
                     leaf link-state-te-policy-cp-segment-sstlv-alen {
                       type uint32;
                     }
                   }
                 }
               }
             }
             container link-state-prefix {
               leaf link-state-prefix-attr-flags {
                 type string;
               }
               leaf link-state-prefix-metric {
                 type uint32;
               }
               list link-state-prefix-sid {
                 key "link-state-prefix-sid-index link-state-prefix-sid-flags link-state-prefix-sid-algo";
                 leaf link-state-prefix-sid-index {
                   type uint32;
                 }
                 leaf link-state-prefix-sid-flags {
                   type string;
                 }
                 leaf link-state-prefix-sid-algo {
                   type string;
                 }
               }
               container link-state-prefix-srv6-locator {
                 leaf link-state-prefix-srv6-locator-flags {
                   type string;
                 }
                 leaf link-state-prefix-srv6-locator-algo {
                   type string;
                 }
                 leaf link-state-prefix-srv6-locator-metric {
                   type string;
                 }
               }
               list link-state-prefix-fapm {
                 key "link-state-prefix-fapm-algo";
                 leaf link-state-prefix-fapm-algo {
                   type uint32;
                 }
                 leaf link-state-prefix-fapm-metric {
                   type uint32;
                 }
               }
             }
             container link-state-srv6-endsid {
               container link-state-srv6-endsid-info {
                 leaf link-state-srv6-endsid-epb {
                   type string;
                 }
                 leaf link-state-srv6-endsid-flags {
                   type string;
                 }
                 leaf link-state-srv6-endsid-algo {
                   type string;
                 }
                 container link-state-srv6-endsid-sstlv {
                   leaf link-state-srv6-endsid-sstlv-header {
                     type empty;
                   }
                   leaf link-state-srv6-endsid-sstlv-blen {
                     type uint32;
                   }
                   leaf link-state-srv6-endsid-sstlv-nlen {
                     type uint32;
                   }
                   leaf link-state-srv6-endsid-sstlv-flen {
                     type uint32;
                   }
                   leaf link-state-srv6-endsid-sstlv-alen {
                     type uint32;
                   }
                 }
               }
             }
             container link-state-unknown-tlvs {
               list link-state-unknown-tlv {
                 key "unknown-type";
                 leaf unknown-type {
                   type uint32;
                 }
                 leaf unknown-length {
                   type uint32;
                 }
                 leaf unknown-bytes {
                   type string;
                 }
               }
             }
           }
           container aggregate {
             leaf aggregate-truncate {
               type string;
             }
             container aggregate-as-path {
               container bgp-path-attributes {
                 container attr-as-path {
                   description
                     "AS Path Attribute";
                   leaf attr-length {
                     type string;
                   }
                   leaf flags {
                     type string;
                     description
                       "Enabled trace flags";
                   }
                 }
                 container attr-as4-path {
                   description
                     "4-byte AS Path Attribute";
                   leaf attr-length {
                     type string;
                   }
                 }
                 container attr-as-path-effective {
                   description
                     "Effective AS-Path Attribute";
                   leaf attr-length {
                     type string;
                   }
                 }
                 container attr-aggregator {
                   description
                     "Aggregator Attribute";
                   leaf attr-length {
                     type string;
                   }
                 }
                 container attr-aggregator4 {
                   description
                     "Aggregator4 Attribute";
                   leaf attr-length {
                     type string;
                   }
                 }
                 container attr-cluster-list {
                   description
                     "Cluster List Attribute";
                   leaf attr-length {
                     type string;
                   }
                 }
                 container attr-originator-id {
                   description
                     "Originator Attribute";
                   leaf attr-length {
                     type string;
                   }
                 }
               }
               leaf as-path {
                 type string;
                 description
                   "Name of AS path regular expression (BGP only)";
               }
               leaf reference-count {
                 type int32;
                 description
                   "Reference count";
               }
               leaf as-path-length {
                 type int32;
               }
               leaf aggregate-truncate {
                 type string;
               }
             }
             leaf aggregate-flags {
               type string;
               description
                 "Flags on this aggregate route entry";
             }
             leaf aggregate-depth {
               type int32;
               description
                 "Depth of this aggregate";
             }
             leaf aggregate-active {
               type empty;
               description
                 "Present if this aggregate is active";
             }
             leaf aggregate-algo {
               type uint32;
               description
                 "Algorithm number";
             }
             leaf contributing-route-count {
               type int32;
               description
                 "Number of contributing routes in this aggregate";
             }
             leaf aggregate-policy-name {
               type string;
             }
             list aggregated-route {
               key "destination-prefix";
               leaf destination-prefix {
                 type string;
                 description
                   "Destination prefix and mask";
               }
               leaf protocol-name {
                 type string;
               }
             }
           }
           list kern-nhexpand {
             description
               "Next-hop gateway information";
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
           }
           container kern-nh-platform-layer-input {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           container kern-nh-platform-layer-output {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           list nh {
             description
               "Next-hop gateway information";
             leaf selected-next-hop {
               type empty;
               description
                 "Present if this next hop is selected";
             }
             leaf to {
               type string;
               description
                 "Neighbor address to which to send (next-hop address)";
             }
             leaf nh-indirect-fnh-type {
               type string;
               description
                 "Indirect pointing to a well-known nexthop";
             }
             leaf via {
               type string;
               description
                 "Reachable via a local interface";
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
             leaf nh-string {
               type string;
             }
             leaf nh-table-receive {
               type string;
               description
                 "Destination is a local address";
             }
             leaf nh-table {
               type string;
               description
                 "Indirect pointing to another table";
             }
             leaf nh-table-localized {
               type string;
               description
                 "Indirect pointing to a localized table";
             }
             leaf nh-localized-ifl {
               type string;
               description
                 "Indirect pointing to a localized ifl";
             }
             leaf lsp-name {
               type string;
               description
                 "Tunneled into an RSVP LSP";
             }
             leaf mpls-label {
               type string;
               description
                 "Label of MPLS packet";
             }
             leaf nh-local-interface {
               type string;
               description
                 "Destination is a local interface";
             }
             leaf nh-service {
               type string;
               description
                 "Next-hop service";
             }
             leaf nh-private-comp {
               type string;
               description
                 "Private Composite Next-hop";
             }
             leaf srv6-prefix-sid {
               type jt:ipaddr;
               description
                 "SRv6 prefixe sid value";
             }
             leaf srv6-encap-brief {
               type string;
               description
                 "IPV6 SR-header encapsulation";
             }
             leaf elnh-address {
               type string;
               description
                 "Address of Element Next-hop";
             }
             leaf localized-table {
               type string;
               description
                 "Name of localized table";
             }
             leaf ae-member-interface {
               type string;
               description
                 "AE Member interface";
             }
             leaf weight {
               type int32;
               description
                 "Next-hop weight";
             }
             leaf balance {
               type int32;
               description
                 "Next-hop balance";
             }
             leaf uflags {
               type string;
               description
                 "Next-hop uflags";
             }
             leaf filter {
               type string;
               description
                 "Next-hop firewall filter";
             }
             leaf session {
               type string;
               description
                 "Session ID Associated with this NH";
             }
             leaf statistics-id-group-terse {
               type string;
               description
                 "Statistics ID Group Associated with this NH";
             }
             leaf app-specific-opaque {
               type string;
               description
                 "Application specific opaque data dump";
             }
             leaf gw-opaque {
               type string;
               description
                 "Nexthops gateway opaque data handle";
             }
             leaf statistics-pkts-count {
               type int32;
               description
                 "Statistics packet count Associated with this NH";
             }
             leaf statistics-bytes-count {
               type int32;
               description
                 "Statistics bytes count Associated with this NH";
             }
             leaf ext-int-type {
               type string;
               description
                 "Next-hop type of equal-external-internal multipath";
             }
             leaf fc {
               type int32;
               description
                 "Forwarding-class";
             }
             leaf label-ttl-action {
               type string;
               description
                 "TTL action associated with labels";
             }
             leaf load-balance-label {
               type string;
               description
                 "Load balance action associated with labels";
             }
             leaf label-element {
               type string;
               description
                 "Pointer to the tag label element";
             }
             leaf label-element-parent {
               type string;
               description
                 "Pointer to the tag label element parent";
             }
             leaf label-element-refcount {
               type string;
               description
                 "Number of references to the tag label element";
             }
             leaf label-element-childcount {
               type string;
               description
                 "Number of child references to the tag label element";
             }
             leaf label-element-lspid {
               type string;
               description
                 "LSP ID of the tag label element";
             }
             leaf nh-service-pkt-dist {
               type string;
               description
                 "Multi services packet distribution type";
             }
             leaf nh-service-app-data {
               type string;
               description
                 "Multi services application specific data";
             }
             leaf nh-index {
               type uint32;
               description
                 "Next-hop index";
             }
             leaf nh-address {
               type string;
               description
                 "Address of next hop";
             }
             leaf nh-reference-count {
               type int32;
               description
                 "Number of references to this next hop";
             }
             leaf tunnel-composite-attr-type {
               type string;
               description
                 "Tunnel-Type for tunnel-composite-nexthop";
             }
             leaf tunnel-composite-attr-subtype {
               type string;
               description
                 "Tunnel-Subtype for tunnel-composite-nexthop";
             }
             leaf tunnel-composite-attr-reference-count {
               type int32;
               description
                 "Tunnel-reference-count for tunnel-composite-nexthop";
             }
             leaf tunnel-composite-attr-nh-id {
               type int32;
               description
                 "Tunnel-NextHop-Id for tunnel-composite-nexthop";
             }
             leaf tunnel-composite-attr-dest {
               type jt:ipaddr;
               description
                 "Tunnel-Destination for tunnel-composite-nexthop";
             }
             leaf tunnel-composite-attr-src {
               type jt:ipaddr;
               description
                 "Tunnel-Source for tunnel-composite-nexthop";
             }
             leaf tunnel-composite-attr-tunnel-endpoint {
               type jt:ipaddr;
               description
                 "Tunnel-Endpoint for tunnel-composite-nexthop";
             }
             leaf tunnel-composite-anchor-pfe {
               type string;
               description
                 "Anchor PFE name, if tunnel nexthop is localized";
             }
             leaf tunnel-composite-encap-rtb-id {
               type int32;
               description
                 "Tunnel encap routing table index";
             }
             leaf tunnel-composite-decap-rtb-id {
               type int32;
               description
                 "Tunnel decap routing table index";
             }
             leaf tunnel-composite-attr-ttl {
               type int32;
               description
                 "Tunnel-TTL for tunnel-composite-nexthop";
             }
             leaf tunnel-composite-attr-udp-port {
               type int32;
               description
                 "Tunnel-UDP-Destination port for tunnel-composite-nexthop";
             }
             leaf tunnel-composite-attr-fc-id {
               type int32;
               description
                 "Tunnel-Forwarding-Class-ID for tunnel-composite-nexthop";
             }
             leaf tunnel-composite-attr-tid {
               type int32;
               description
                 "Tunnel-Id for tunnel-composite-nexthop";
             }
             leaf tunnel-composite-attr-label {
               type string;
               description
                 "Tunnel-VPN-Label for tunnel-composite-nexthop";
             }
             leaf tunnel-composite-attr-label-ttl {
               type string;
               description
                 "Tunnel-VPN-Label-TTL for tunnel-composite-nexthop";
             }
             leaf tunnel-composite-attr-gre-key {
               type int32;
               description
                 "GRE key for tunnel-composite-nexthop";
             }
             leaf-list tunnel-composite-attr-segment-addr {
               type jt:ipaddr;
               description
                 "IPv6 segment-address";
             }
             leaf-list tunnel-composite-attr-sid {
               type int32;
               description
                 "IPv6 segment-sid";
             }
             leaf tunnel-composite-attr-vni {
               type int32;
               description
                 "Tunnel-VNI for tunnel-composite-nexthop in VxLAN";
             }
             leaf tunnel-composite-attr-dest-mac {
               type string;
               description
                 "Tunnel-Dest-Mac for tunnel-composite-nexthop in VxLAN";
             }
             leaf translate-composite-attr-type {
               type string;
               description
                 "Translation type for translate-composite-nexthop";
             }
             leaf translate-composite-attr-flags {
               type string;
               description
                 "Flags for translate-composite-nexthop";
             }
             leaf translate-composite-attr-reference-count {
               type int32;
               description
                 "Reference count for translate-composite-nexthop";
             }
             leaf translate-composite-attr-nh-id {
               type int32;
               description
                 "NextHop id for translate-composite-nexthop";
             }
             leaf translate-composite-attr-dest {
               type jt:ipaddr;
               description
                 "Translation destination for translate-composite-nexthop";
             }
             leaf translate-composite-attr-dest-plen {
               type int32;
               description
                 "Translation destination prefix length for 
                 translate-composite-nexthop";
             }
             leaf translate-composite-attr-src {
               type jt:ipaddr;
               description
                 "Translation source for translate-composite-nexthop";
             }
             leaf translate-composite-attr-src-plen {
               type int32;
               description
                 "Translation source prefix length for 
                 translate-composite-nexthop";
             }
             leaf translate-composite-attr-dest-alg-type {
               type string;
               description
                 "Destination algorithm type for translate-composite-nexthop";
             }
             leaf translate-composite-attr-src-alg-type {
               type string;
               description
                 "Source algorithm type for translate-composite-nexthop";
             }
             leaf translate-composite-attr-dest-vrf-id {
               type int32;
               description
                 "Destination vrf id for translate-composite-nexthop";
             }
             leaf translate-composite-attr-src-vrf-id {
               type int32;
               description
                 "Source vrf id for translate-composite-nexthop";
             }
             leaf translate-composite-attr-hoplimit {
               type int32;
               description
                 "Hoplimit for translate-composite-nexthop";
             }
             leaf translate-composite-attr-traffic-class {
               type int32;
               description
                 "Traffic class for translate-composite-nexthop";
             }
             leaf translate-composite-attr-ttl {
               type int32;
               description
                 "Ttl for translate-composite-nexthop";
             }
             leaf translate-composite-attr-tos {
               type int32;
               description
                 "Tos for translate-composite-nexthop";
             }
           }
           container protocol-nh {
             description
               "Protocol next hop";
             list nh {
               description
                 "Next-hop gateway information";
               container vxlan-header-rewrite {
                 description
                   "VXLAN tunnel rewrite information";
                 leaf vxlan-header-rewrite-mtu {
                   type int32;
                   description
                     "VXLAN tunnel MTU";
                 }
                 leaf vxlan-header-rewrite-flags {
                   type int32;
                   description
                     "VXLAN tunnel flags";
                 }
                 leaf vxlan-header-rewrite-encap-rtb-id {
                   type int32;
                   description
                     "VXLAN tunnel encapsulation table ID";
                 }
                 leaf vxlan-header-rewrite-decap-rtb-id {
                   type int32;
                   description
                     "VXLAN tunnel decapsulation table ID";
                 }
                 leaf vxlan-header-rewrite-encap-vnid {
                   type int32;
                   description
                     "VXLAN tunnel encapsulation VNI";
                 }
                 leaf vxlan-header-rewrite-decap-vnid {
                   type int32;
                   description
                     "VXLAN tunnel decapsulation VNI";
                 }
                 leaf vxlan-header-rewrite-svtep {
                   type jt:ipaddr;
                   description
                     "Source VTEP address";
                 }
                 leaf vxlan-header-rewrite-dvtep {
                   type jt:ipaddr;
                   description
                     "Destination VTEP address";
                 }
                 leaf vxlan-header-rewrite-smac {
                   type string;
                   description
                     "Source MAC address";
                 }
                 leaf vxlan-header-rewrite-dmac {
                   type string;
                   description
                     "Destination MAC address";
                 }
               }
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf nh-string {
                 type string;
               }
               leaf elnh-address {
                 type string;
                 description
                   "Address of Element Next-hop";
               }
               leaf to {
                 type string;
                 description
                   "Neighbor address to which to send (next-hop address)";
               }
               leaf via {
                 type string;
                 description
                   "Reachable via a local interface";
               }
               leaf localized-table {
                 type string;
                 description
                   "Name of localized table";
               }
               leaf ae-member-interface {
                 type string;
                 description
                   "AE Member interface";
               }
               leaf weight {
                 type int32;
                 description
                   "Next-hop weight";
               }
               leaf balance {
                 type int32;
                 description
                   "Next-hop balance";
               }
               leaf uflags {
                 type string;
                 description
                   "Next-hop uflags";
               }
               leaf filter {
                 type string;
                 description
                   "Next-hop firewall filter";
               }
               leaf selected-next-hop {
                 type empty;
                 description
                   "Present if this next hop is selected";
               }
               leaf session {
                 type string;
                 description
                   "Session ID Associated with this NH";
               }
               leaf statistics-id-group-terse {
                 type string;
                 description
                   "Statistics ID Group Associated with this NH";
               }
               leaf app-specific-opaque {
                 type string;
                 description
                   "Application specific opaque data dump";
               }
               leaf gw-opaque {
                 type string;
                 description
                   "Nexthops gateway opaque data handle";
               }
               leaf statistics-pkts-count {
                 type int32;
                 description
                   "Statistics packet count Associated with this NH";
               }
               leaf statistics-bytes-count {
                 type int32;
                 description
                   "Statistics bytes count Associated with this NH";
               }
               leaf ext-int-type {
                 type string;
                 description
                   "Next-hop type of equal-external-internal multipath";
               }
               leaf fc {
                 type int32;
                 description
                   "Forwarding-class";
               }
               leaf lsp-name {
                 type string;
                 description
                   "Tunneled into an RSVP LSP";
               }
               leaf mpls-label {
                 type string;
                 description
                   "Label of MPLS packet";
               }
               leaf label-ttl-action {
                 type string;
                 description
                   "TTL action associated with labels";
               }
               leaf load-balance-label {
                 type string;
                 description
                   "Load balance action associated with labels";
               }
               leaf label-element {
                 type string;
                 description
                   "Pointer to the tag label element";
               }
               leaf label-element-parent {
                 type string;
                 description
                   "Pointer to the tag label element parent";
               }
               leaf label-element-refcount {
                 type string;
                 description
                   "Number of references to the tag label element";
               }
               leaf label-element-childcount {
                 type string;
                 description
                   "Number of child references to the tag label element";
               }
               leaf label-element-lspid {
                 type string;
                 description
                   "LSP ID of the tag label element";
               }
               leaf nh-table-receive {
                 type string;
                 description
                   "Destination is a local address";
               }
               leaf nh-table {
                 type string;
                 description
                   "Indirect pointing to another table";
               }
               leaf nh-localized-ifl {
                 type string;
                 description
                   "Indirect pointing to a localized ifl";
               }
               leaf nh-local-interface {
                 type string;
                 description
                   "Destination is a local interface";
               }
               leaf nh-service {
                 type string;
                 description
                   "Next-hop service";
               }
               leaf nh-service-pkt-dist {
                 type string;
                 description
                   "Multi services packet distribution type";
               }
               leaf nh-service-app-data {
                 type string;
                 description
                   "Multi services application specific data";
               }
               leaf nh-private-comp {
                 type string;
                 description
                   "Private Composite Next-hop";
               }
               leaf nh-index {
                 type uint32;
                 description
                   "Next-hop index";
               }
               leaf nh-address {
                 type string;
                 description
                   "Address of next hop";
               }
               leaf nh-reference-count {
                 type int32;
                 description
                   "Number of references to this next hop";
               }
               leaf tunnel-composite-attr-type {
                 type string;
                 description
                   "Tunnel-Type for tunnel-composite-nexthop";
               }
               leaf tunnel-composite-attr-subtype {
                 type string;
                 description
                   "Tunnel-Subtype for tunnel-composite-nexthop";
               }
               leaf tunnel-composite-attr-reference-count {
                 type int32;
                 description
                   "Tunnel-reference-count for tunnel-composite-nexthop";
               }
               leaf tunnel-composite-attr-nh-id {
                 type int32;
                 description
                   "Tunnel-NextHop-Id for tunnel-composite-nexthop";
               }
               leaf tunnel-composite-attr-dest {
                 type jt:ipaddr;
                 description
                   "Tunnel-Destination for tunnel-composite-nexthop";
               }
               leaf tunnel-composite-attr-src {
                 type jt:ipaddr;
                 description
                   "Tunnel-Source for tunnel-composite-nexthop";
               }
               leaf tunnel-composite-attr-tunnel-endpoint {
                 type jt:ipaddr;
                 description
                   "Tunnel-Endpoint for tunnel-composite-nexthop";
               }
               leaf tunnel-composite-anchor-pfe {
                 type string;
                 description
                   "Anchor PFE name, if tunnel nexthop is localized";
               }
               leaf tunnel-composite-encap-rtb-id {
                 type int32;
                 description
                   "Tunnel encap routing table index";
               }
               leaf tunnel-composite-decap-rtb-id {
                 type int32;
                 description
                   "Tunnel decap routing table index";
               }
               leaf tunnel-composite-attr-ttl {
                 type int32;
                 description
                   "Tunnel-TTL for tunnel-composite-nexthop";
               }
               leaf tunnel-composite-attr-udp-port {
                 type int32;
                 description
                   "Tunnel-UDP-Destination port for tunnel-composite-nexthop";
               }
               leaf tunnel-composite-attr-fc-id {
                 type int32;
                 description
                   "Tunnel-Forwarding-Class-ID for tunnel-composite-nexthop";
               }
               leaf tunnel-composite-attr-tid {
                 type int32;
                 description
                   "Tunnel-Id for tunnel-composite-nexthop";
               }
               leaf tunnel-composite-attr-label {
                 type string;
                 description
                   "Tunnel-VPN-Label for tunnel-composite-nexthop";
               }
               leaf tunnel-composite-attr-label-ttl {
                 type string;
                 description
                   "Tunnel-VPN-Label-TTL for tunnel-composite-nexthop";
               }
               leaf tunnel-composite-attr-gre-key {
                 type int32;
                 description
                   "GRE key for tunnel-composite-nexthop";
               }
               leaf-list tunnel-composite-attr-segment-addr {
                 type jt:ipaddr;
                 description
                   "IPv6 segment-address";
               }
               leaf-list tunnel-composite-attr-sid {
                 type int32;
                 description
                   "IPv6 segment-sid";
               }
               leaf tunnel-composite-attr-vni {
                 type int32;
                 description
                   "Tunnel-VNI for tunnel-composite-nexthop in VxLAN";
               }
               leaf tunnel-composite-attr-dest-mac {
                 type string;
                 description
                   "Tunnel-Dest-Mac for tunnel-composite-nexthop in VxLAN";
               }
               leaf translate-composite-attr-type {
                 type string;
                 description
                   "Translation type for translate-composite-nexthop";
               }
               leaf translate-composite-attr-flags {
                 type string;
                 description
                   "Flags for translate-composite-nexthop";
               }
               leaf translate-composite-attr-reference-count {
                 type int32;
                 description
                   "Reference count for translate-composite-nexthop";
               }
               leaf translate-composite-attr-nh-id {
                 type int32;
                 description
                   "NextHop id for translate-composite-nexthop";
               }
               leaf translate-composite-attr-dest {
                 type jt:ipaddr;
                 description
                   "Translation destination for translate-composite-nexthop";
               }
               leaf translate-composite-attr-dest-plen {
                 type int32;
                 description
                   "Translation destination prefix length for 
                   translate-composite-nexthop";
               }
               leaf translate-composite-attr-src {
                 type jt:ipaddr;
                 description
                   "Translation source for translate-composite-nexthop";
               }
               leaf translate-composite-attr-src-plen {
                 type int32;
                 description
                   "Translation source prefix length for 
                   translate-composite-nexthop";
               }
               leaf translate-composite-attr-dest-alg-type {
                 type string;
                 description
                   "Destination algorithm type for 
                   translate-composite-nexthop";
               }
               leaf translate-composite-attr-src-alg-type {
                 type string;
                 description
                   "Source algorithm type for translate-composite-nexthop";
               }
               leaf translate-composite-attr-dest-vrf-id {
                 type int32;
                 description
                   "Destination vrf id for translate-composite-nexthop";
               }
               leaf translate-composite-attr-src-vrf-id {
                 type int32;
                 description
                   "Source vrf id for translate-composite-nexthop";
               }
               leaf translate-composite-attr-hoplimit {
                 type int32;
                 description
                   "Hoplimit for translate-composite-nexthop";
               }
               leaf translate-composite-attr-traffic-class {
                 type int32;
                 description
                   "Traffic class for translate-composite-nexthop";
               }
               leaf translate-composite-attr-ttl {
                 type int32;
                 description
                   "Ttl for translate-composite-nexthop";
               }
               leaf translate-composite-attr-tos {
                 type int32;
                 description
                   "Tos for translate-composite-nexthop";
               }
             }
             leaf to {
               type string;
               description
                 "Neighbor address to which to send (next-hop address)";
             }
             leaf metric {
               type int32;
             }
             leaf aigp {
               type string;
               description
                 "AIGP";
             }
             leaf balance {
               type int32;
               description
                 "Next-hop balance";
             }
             leaf flags {
               type string;
               description
                 "Enabled trace flags";
             }
             leaf res-state {
               type string;
               description
                 "Status of route resolution";
             }
             leaf res-tsp-idx {
               type int32;
               description
                 "TSP index of the path";
             }
             leaf-list res-path-aux {
               type string;
             }
             leaf-list res-path-aux-type {
               type string;
             }
             leaf-list res-path-aux-flags {
               type string;
             }
             leaf-list res-path-aux-rs-name {
               type string;
             }
             leaf-list res-path-aux-rs-ribs {
               type string;
             }
             leaf-list res-path-inode-flags {
               type string;
             }
             leaf-list res-path-flags {
               type string;
             }
             leaf-list res-path-fnh-link {
               type string;
             }
             leaf-list res-path-inh-link {
               type string;
             }
             leaf mpls-label {
               type string;
               description
                 "Label of MPLS packet";
             }
             leaf label-ttl-action {
               type string;
               description
                 "TTL action associated with labels";
             }
             leaf load-balance-label {
               type string;
               description
                 "Load balance action associated with labels";
             }
             leaf-list composite-nh {
               type string;
             }
             leaf-list pnh-statistics-id-group {
               type string;
               description
                 "Statistics ID Group Associated with this protocol NH";
             }
             leaf-list vpnlabel-nh {
               type string;
             }
             leaf-list indirect-nh {
               type string;
             }
             leaf ext-int-type {
               type string;
               description
                 "Next-hop type of equal-external-internal multipath";
             }
             leaf gw-opaque {
               type string;
               description
                 "Nexthops gateway opaque data handle";
             }
             leaf-list forwarding-nh-count {
               type int32;
               description
                 "Number of indirect path forwarding next hops";
             }
             leaf-list merged-forwarding-nh-count {
               type int32;
               description
                 "Number of indirect path forwarding next hops (Merged)";
             }
             leaf nh-type {
               type string;
               description
                 "Special next hop: Reject, Blackhole, Receive, Multicast, 
                 Local, or Unused";
             }
             leaf-list node-prefix {
               type string;
             }
             leaf-list node-prefix-length {
               type int32;
             }
             leaf-list originating-rib {
               type string;
               description
                 "Routing table from which this route was learned";
             }
             leaf-list node-metric {
               type int32;
             }
             leaf-list node-path-count {
               type int32;
               description
                 "Number of paths for this node";
             }
             leaf node-flags {
               type int32;
               description
                 "Flags for this node";
             }
             leaf-list node-address {
               type string;
             }
             leaf-list node-forwarding-nh-count {
               type int32;
             }
             leaf-list nh-subtype {
               type string;
               description
                 "Specified nexthop subtype";
             }
             leaf indirect-nh-count {
               type int32;
               description
                 "Number of indirect next hops";
             }
             leaf composite-nh-count {
               type int32;
               description
                 "Number of composite next hops";
             }
             container eth-header-rewrite {
               description
                 "Ethernet header rewrite information";
               leaf eth-header-rewrite-smac {
                 type string;
                 description
                   "Source MAC address";
               }
               leaf eth-header-rewrite-dmac {
                 type string;
                 description
                   "Destination MAC address";
               }
               leaf eth-header-rewrite-tpid {
                 type int32;
                 description
                   "Ethernet header TPID";
               }
               leaf eth-header-rewrite-tci {
                 type int32;
                 description
                   "Ethernet header TCI";
               }
               leaf eth-header-rewrite-vlan-id {
                 type int32;
                 description
                   "Ethernet header VLAN ID";
               }
               leaf eth-header-rewrite-ethertype {
                 type int32;
                 description
                   "Ethernet header ethertype";
               }
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container fully-resolved-tunnel {
               description
                 "GRE or UDP tunnel rewrite information";
               leaf fully-resolved-tunnel-type {
                 type string;
                 description
                   "Tunnel type";
               }
               leaf fully-resolved-tunnel-dest {
                 type jt:ipaddr;
                 description
                   "Tunnel Destination";
               }
               leaf fully-resolved-tunnel-src {
                 type jt:ipaddr;
                 description
                   "Tunnel Source";
               }
               leaf fully-resolved-tunnel-ep-addr {
                 type jt:ipaddr;
                 description
                   "Tunnel endpoint address";
               }
               leaf fully-resolved-tunnel-encap-rtb-id {
                 type int32;
                 description
                   "Tunnel encap routing table id";
               }
               leaf fully-resolved-tunnel-decap-rtb-id {
                 type int32;
                 description
                   "Tunnel decap routing table id";
               }
             }
           }
           container srte-policy-state {
             leaf sr-source {
               type string;
             }
             leaf sr-origin {
               type string;
             }
             leaf sr-preference {
               type uint32;
             }
             leaf sr-preference-override {
               type uint32;
             }
             leaf sr-route-distinguisher {
               type uint32;
             }
           }
           container srte-policy-information {
             container srte-policy {
               leaf srte-path-preference {
                 type uint32;
               }
               leaf srte-binding-sid {
                 type string;
               }
               leaf srte-adv-policy-name {
                 type string;
               }
               leaf srte-priority {
                 type uint32;
               }
               leaf srte-enlp {
                 type uint32;
               }
               leaf srte-tlv-recv-flags {
                 type string;
               }
               leaf srte-binding-sid-label-encoding {
                 type string;
               }
               list srte-segment-list {
                 leaf srte-segment-list-weight {
                   type uint32;
                 }
                 list srte-segment {
                   leaf srte-segment-label {
                     type uint32;
                   }
                   leaf srte-segment-label-ttl {
                     type string;
                     description
                       "SR Policy segment label ttl";
                   }
                   leaf srte-segment-type {
                     type string;
                     description
                       "SR Policy segment type";
                   }
                   leaf srte-segment-label-class {
                     type uint32;
                     description
                       "SR Policy segment label traffic-class";
                   }
                 }
               }
             }
           }
           container bgp-prefix-sid-attr {
             description
               "BGP Prefix SID Attribute";
             container bgp-prefix-sid-attr-label-idx-tlv {
               leaf bgp-prefix-sid-label-idx-index {
                 type int32;
               }
               leaf bgp-prefix-sid-attr-status {
                 type string;
               }
             }
             container bgp-prefix-sid-attr-srgb-tlv {
               list bgp-prefix-sid-srgb-block {
                 key "bgp-prefix-sid-srgb-block-start-label";
                 leaf bgp-prefix-sid-srgb-block-start-label {
                   type int32;
                 }
                 leaf bgp-prefix-sid-srgb-block-range {
                   type int32;
                 }
               }
             }
             container bgp-prefix-sid-attr-service-tlv {
               leaf bgp-prefix-sid-srv6-sid-value {
                 type jt:ipaddr;
               }
               leaf bgp-prefix-sid-attr-service-tlv-type {
                 type uint32;
               }
               leaf bgp-prefix-sid-attr-tlv-type {
                 type uint32;
               }
               leaf bgp-prefix-sid-srv6-sid-bh {
                 type uint32;
               }
               leaf bgp-prefix-sid-srv6-sid-bl {
                 type uint32;
               }
               leaf bgp-prefix-sid-srv6-sid-nl {
                 type uint32;
               }
               leaf bgp-prefix-sid-srv6-sid-fl {
                 type uint32;
               }
               leaf bgp-prefix-sid-srv6-sid-al {
                 type uint32;
               }
               leaf bgp-prefix-sid-srv6-sid-tl {
                 type uint32;
               }
               leaf bgp-prefix-sid-srv6-sid-to {
                 type uint32;
               }
             }
             container bgp-prefix-sid-attr-unknown-tlvs {
               list bgp-prefix-sid-attr-unknown-tlv {
                 key "bgp-prefix-sid-unknown-tlv-type";
                 leaf bgp-prefix-sid-unknown-tlv-type {
                   type uint32;
                 }
                 leaf bgp-prefix-sid-unknown-tlv-len {
                   type uint32;
                 }
               }
             }
           }
           container srte-policy-telemetry-statistics-state {
             leaf srte-policy-telemetry-statistics-state.heading {
               type string;
             }
             container srte-policy-telemetry-statistics-config {
               leaf ingress {
                 type empty;
                 description
                   "Flag indicating ingress statistics is configured";
               }
               leaf transit {
                 type empty;
                 description
                   "Flag indicating transit statistics is configured";
               }
             }
             list srte-policy-telemetry-statistics-sensor-information {
               leaf sensor-type {
                 type string;
               }
               leaf sensor-status {
                 type string;
               }
               leaf sensor-id {
                 type int32;
                 description
                   "Unique identifier for the sensor";
               }
             }
           }
           list flex-tunnel-profile {
             description
               "Flex V4/V6 route tunnel attribute information";
             container flex-tunnel-profile-info {
               description
                 "The tunnel profile information";
               leaf flex-tunnel-profile-num {
                 type int32;
                 description
                   "The tunnel profile number";
               }
               leaf flex-tunnel-profile-action {
                 type string;
                 description
                   "The action that this profile will be used for";
               }
               leaf flex-tunnel-profile-vni {
                 type int32;
                 description
                   "VXLAN Network Identifier (VNI)";
               }
               leaf flex-tunnel-profile-src-pfx {
                 type string;
                 description
                   "Source address and prefix length";
               }
               leaf flex-tunnel-profile-src-udp-port-range {
                 type string;
                 description
                   "Outer source UDP port range";
               }
               leaf flex-tunnel-profile-src-mac {
                 type string;
                 description
                   "Source MAC address, a 48-bit MAC value";
               }
               leaf flex-tunnel-profile-dest-pfx {
                 type string;
                 description
                   "Destination address";
               }
               leaf flex-tunnel-profile-dest-udp-port {
                 type int32;
                 description
                   "Outer destination UDP port";
               }
               leaf flex-tunnel-profile-dest-mac {
                 type string;
                 description
                   "Destination MAC address, a 48-bit MAC value";
               }
               leaf flex-tunnel-profile-flex-vxlan-flags {
                 type int32;
                 description
                   "Flex VxLAN flags";
               }
               leaf flex-tunnel-profile-reserved-24-bit-field {
                 type int32;
                 description
                   "VXLAN 24-bit reserved field as specified in RFC7348";
               }
               leaf flex-tunnel-profile-reserved-8-bit-field {
                 type int32;
                 description
                   "VXLAN 8-bit reserved field as specified in RFC7348";
               }
               container flex-tunnel-profile-stats {
                 description
                   "Statistics associated with tunnel";
                 leaf flex-tunnel-stats-pkts-count {
                   type int32;
                   description
                     "Packet count";
                 }
                 leaf flex-tunnel-stats-pps {
                   type int32;
                   description
                     "Packets per second";
                 }
                 leaf flex-tunnel-stats-bytes-count {
                   type int32;
                   description
                     "Byte count";
                 }
                 leaf flex-tunnel-stats-bps {
                   type int32;
                   description
                     "Bytes per second";
                 }
               }
             }
             leaf flex-tunnel-profile-string {
               type string;
               description
                 "The tunnel profile string";
             }
           }
           leaf preference2 {
             type int32;
           }
           leaf age {
             type string;
           }
           leaf med {
             type int32;
             description
               "Multiple exit discriminator";
           }
           leaf local-preference {
             type int32;
           }
           leaf rt-tag {
             type int32;
           }
           leaf rt-tag2 {
             type int32;
           }
           leaf learned-from {
             type jt:ipaddr;
             description
               "Peer address from which this route was learned";
           }
           leaf peer-as {
             type int32;
             description
               "Peer AS number";
           }
           leaf evpn-remote-mes {
             type jt:ipaddr;
             description
               "Remote PE";
           }
           leaf evpn-routing-instance-name {
             type string;
             description
               "Routing Instance";
           }
           leaf evpn-tag-rt-type {
             type string;
             description
               "Route Type";
           }
           leaf evpn-vlan-id {
             type int32;
             description
               "VLAN-ID";
           }
           leaf evpn-vpws-service-id {
             type int32;
             description
               "VPWS Service-Id";
           }
           leaf rt-evpn-esi {
             type string;
             description
               "ESI";
           }
           leaf evpn-isid {
             type int32;
             description
               "ISID";
           }
           leaf rt-evpn-bmac {
             type string;
             description
               "BMAC";
           }
           leaf bgp-rtarget-type {
             type string;
             description
               "BGP RT-Constrain route type";
           }
           leaf bgp-rtarget-generation {
             type uint32;
             description
               "BGP RT-Constrain generation";
           }
           leaf bgp-rtarget-for {
             type string;
             description
               "BGP RT-Constrain member";
           }
           leaf nh-index {
             type uint32;
             description
               "Next-hop index";
           }
           leaf transport-class {
             type string;
             description
               "Transport class name";
           }
           leaf nh-address {
             type string;
             description
               "Address of next hop";
           }
           leaf nh-reference-count {
             type int32;
             description
               "Number of references to this next hop";
           }
           leaf ext-int-intf-index {
             type int32;
             description
               "Interface index of equal-external-internal multipath";
           }
           leaf nh-session-id {
             type uint32;
             description
               "Nexthop session id";
           }
           leaf nh-key-opaque {
             type string;
             description
               "Nexthop key opaque handle";
           }
           leaf nh-non-key-opaque {
             type string;
             description
               "Nexthop non-key opaque handle";
           }
           leaf nh-key-opaque-dump {
             type string;
             description
               "Nexthop key opaque app dump";
           }
           leaf nh-non-key-opaque-dump {
             type string;
             description
               "Nexthop non-key opaque app dump";
           }
           leaf nh-flood-overflow {
             type empty;
             description
               "Flood nexthop exceeds maximum branches";
           }
           leaf nh-kernel-id {
             type int32;
             description
               "Table Id for this next hop";
           }
           leaf client-data {
             type string;
             description
               "Route server client details";
           }
           leaf route-distinguisher {
             type string;
             description
               "Name of the route-distinguisher";
           }
           leaf reason-for-invalid {
             type string;
           }
           leaf thread-name {
             type string;
           }
           leaf pmsi {
             type string;
             description
               "P-multicast service interface";
           }
           leaf connector {
             type string;
           }
           leaf color {
             type int32;
           }
           leaf color2 {
             type int32;
           }
           leaf prefix-segment-index {
             type int32;
           }
           leaf rt-isis-level {
             type int32;
           }
           leaf rt-isis-downbit {
             type int32;
           }
           leaf rt-entry-state {
             type string;
             description
               "State of this route entry";
           }
           leaf rt-fib-install-priority {
             type string;
             description
               "Route FIB installation priority";
           }
           leaf rt-ack-state {
             type string;
             description
               "Route acknowledgement state";
           }
           leaf rt-ack-ll-flag {
             type string;
             description
               "Status of route ACK flags";
           }
           leaf rt-ack-req-ts {
             type string;
             description
               "Time when ack request is sent";
           }
           leaf rt-ack-res-time {
             type uint32;
             description
               "Ack route response time";
           }
           leaf rt-ack-re-flash-time {
             type string;
             description
               "Time when ack is re flashed to protocols";
           }
           leaf rt-ack-re-flash-status {
             type string;
             description
               "Status of ACK re-flash to protocols";
           }
           leaf rt-ack-guid {
             type uint64;
             description
               "Ack route global identifier";
           }
           leaf rt-ack-olc {
             type uint64;
             description
               "Ack route global version";
           }
           leaf rt-ack-local-ver {
             type uint32;
             description
               "Ack route global version";
           }
           leaf rt-ack-and-err-flag {
             type uint32;
             description
               "Route ack and error flag";
           }
           leaf rt-ack-history {
             type uint32;
             description
               "Route ack history";
           }
           leaf pfe-err-state {
             type string;
             description
               "Route error state from PFE";
           }
           leaf pfe-err-time {
             type uint32;
             description
               "Route error receive time";
           }
           leaf rt-ver-id {
             type uint32;
             description
               "Route version ID";
           }
           leaf rt-entry-pim-state {
             type string;
             description
               "PIM state of this route entry";
           }
           leaf inactive-reason {
             type string;
             description
               "HFRR profile Inactive reason (if any)";
           }
           leaf local-as {
             type int32;
             description
               "Local AS number";
           }
           leaf med-plus-igp {
             type int32;
           }
           leaf rt-aigp {
             type uint64;
           }
           leaf rt-effective-aigp {
             type uint64;
             description
               "Effective AIGP value used by route selection";
           }
           leaf rt-effective-aigp-reason {
             type string;
             description
               "Reason why the effective AIGP value was selected";
           }
           leaf rt-resolving-aigp {
             type uint64;
           }
           leaf rt-effective-metric {
             type uint64;
             description
               "Effective metric value used by route selection";
           }
           leaf rt-effective-metric-reason {
             type string;
             description
               "Reason why the effective metric value was selected";
           }
           leaf rt-orr {
             type uint32;
           }
           leaf rt-actual-igp-metric {
             type uint32;
           }
           leaf rt-ospf-area {
             type string;
           }
           leaf task-name {
             type string;
             description
               "Name of this task";
           }
           leaf announce-bits {
             type int32;
           }
           leaf announce-tasks {
             type string;
           }
           leaf flow-id {
             type int32;
           }
           leaf bgp-rt-flag {
             type string;
             description
               "BGP route flag";
           }
           leaf label-base {
             type int32;
             description
               "Label base for l2vpn";
           }
           leaf label-range {
             type int32;
             description
               "Label range for l2vpn";
           }
           leaf l2vpn-status-vector {
             type string;
           }
           leaf label-offset {
             type int32;
             description
               "Label offset for l2vpn";
           }
           leaf remote-site {
             type int32;
             description
               "Remote site id";
           }
           leaf l2vpn-mesh-group {
             type string;
           }
           leaf vc-label {
             type int32;
             description
               "VC label";
           }
           leaf context-id {
             type jt:ipaddr;
             description
               "Context Identifier";
           }
           leaf route-control-word {
             type string;
             description
               "Control Word";
           }
           leaf mtu {
             type int32;
             description
               "MTU along an interface";
           }
           leaf cell-bundle-size {
             type int32;
             description
               "Cell bundle size";
           }
           leaf vlan-id {
             type int32;
           }
           leaf flow-label-transmit {
             type int32;
           }
           leaf flow-label-receive {
             type int32;
           }
           leaf tdm-payload-size {
             type int32;
           }
           leaf tdm-bitrate {
             type int32;
           }
           leaf pw-status-code {
             type int32;
           }
           leaf cac-bandwidth-failure {
             type empty;
             description
               "Call admission control failure due to insufficient bandwidth";
           }
           leaf vpn-label {
             type int32;
             description
               "VPN label";
           }
           leaf route-label {
             type int32;
             description
               "Route label";
           }
           leaf route-labels {
             type string;
             description
               "Route label";
           }
           leaf mac-route-esi {
             type string;
             description
               "ESI";
           }
           leaf evpn-igmp-flags {
             type int32;
             description
               "IGMP flags";
           }
           leaf evpn-mld-flags {
             type int32;
             description
               "MLD flags";
           }
           leaf evpn-leave-reserved {
             type int32;
             description
               "IGMP Leave Reserved Field";
           }
           leaf evpn-leave-mrt {
             type int32;
             description
               "IGMP Leave Max Response Time";
           }
           leaf overlay-gateway-address {
             type jt:ipaddr;
             description
               "Overlay gateway address";
           }
           leaf reroute-address {
             type jt:ipaddr;
             description
               "Reroute address";
           }
           leaf bgp-otc {
             type int32;
           }
           leaf peer-id {
             type jt:ipaddr;
           }
           leaf rt-entry-ext-pfx-attr-flags {
             type string;
             description
               "Route entry extended prefix attribute flags";
           }
           leaf rt-entry-ext-pfx-source-rtrid {
             type string;
             description
               "Route entry extended prefix source rtr id";
           }
           leaf path-id {
             type string;
           }
           leaf gateway {
             type string;
             description
               "Sourcing gateway";
           }
           leaf rtrib-primary {
             type string;
             description
               "Primary routing table";
           }
           leaf rib-export-rtrib-primary {
             type string;
             description
               "RIB export primary routing table";
           }
           leaf rtrib-secondary {
             type string;
             description
               "Secondary routing table";
           }
           leaf indirect-nh-count {
             type int32;
             description
               "Number of indirect next hops";
           }
           leaf composite-nh-count {
             type int32;
             description
               "Number of composite next hops";
           }
           leaf helper-nhid {
             type uint32;
             description
               "Helper nexthop index";
           }
           leaf helper-refcount {
             type int32;
             description
               "Reference count of those needing helper route";
           }
           leaf backup-pe-group-name {
             type string;
             description
               "Name of the backup PE group";
           }
           leaf designated-forwarder {
             type string;
             description
               "Indicates if we are the designated forwarder for this route";
           }
           leaf rt-entry-opaque-data {
             type string;
             description
               "Opaque data associated with the route entry";
           }
           leaf rt-stats-id-grp-single-line {
             type string;
             description
               "Stats-id-group associated with the route entry";
           }
           leaf rt-entry-ext-pfx-sid-data {
             type string;
             description
               "Route entry extended prefix sid data";
           }
           leaf hidden-reason {
             type string;
             description
               "Protocol's reason for hiding the route";
           }
           leaf bgp-bmp-send-flag-start {
             type string;
           }
           leaf bgp-bmp-send-flag-pre {
             type string;
           }
           leaf bgp-bmp-send-flag-post {
             type string;
           }
           leaf bgp-bmp-send-flag-ribout-prepolicy {
             type string;
           }
           leaf bgp-bmp-send-flag-ribout-postpolicy {
             type string;
           }
           leaf bgp-bmp-send-flag-station {
             type string;
           }
           leaf bgp-nnh-nodes {
             type string;
             description
               "Next-next-hop nodes";
           }
           leaf bgp-nh-nnh-map {
             type string;
             description
               "Next-hop to next-next-hop map";
           }
           leaf bgp-profile-creation-failure-reason {
             type string;
             description
               "Reason for failing to create profile for next-next-hop map";
           }
           leaf bgp-nh-nnh-entry {
             type string;
             description
               "Next-hop to next-next-hop entry";
           }
           leaf glb-profile {
             type string;
             description
               "GLB Profile";
           }
           leaf glb-profile-id {
             type uint32;
             description
               "GLB Profile ID";
           }
           leaf rt-entry-stats {
             type string;
             description
               "Route entry statistics data";
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container route-flap-damping {
             leaf last-merit {
               type int32;
               description
                 "Last merit value";
             }
             leaf merit {
               type int32;
               description
                 "Current merit value";
             }
             leaf damping-parameters {
               type string;
             }
             leaf default-damping-parameters {
               type empty;
               description
                 "Default damping parameters used";
             }
             leaf last-update {
               type string;
             }
             leaf first-update {
               type string;
             }
             leaf route-flap-count {
               type int32;
               description
                 "Number of times this route has flapped";
             }
             leaf suppressed {
               type empty;
               description
                 "This route is suppressed";
             }
             leaf reuse-time {
               type string;
               description
                 "Time until this route is reusable";
             }
             leaf reuse-preference {
               type int32;
               description
                 "Preference to use when this route is reused";
             }
             leaf expire-time {
               type string;
               description
                 "Time when this damping entry expires";
             }
           }
           container nhh {
             leaf nh-type {
               type string;
               description
                 "Special next hop: Reject, Blackhole, Receive, Multicast, 
                 Local, or Unused";
             }
             leaf nh-index {
               type uint32;
               description
                 "Next-hop index";
             }
             leaf transport-class {
               type string;
               description
                 "Transport class name";
             }
             leaf nh-address {
               type string;
               description
                 "Address of next hop";
             }
             leaf nh-reference-count {
               type int32;
               description
                 "Number of references to this next hop";
             }
             leaf ext-int-intf-index {
               type int32;
               description
                 "Interface index of equal-external-internal multipath";
             }
             leaf nh-session-id {
               type uint32;
               description
                 "Nexthop session id";
             }
             leaf nh-key-opaque {
               type string;
               description
                 "Nexthop key opaque handle";
             }
             leaf nh-non-key-opaque {
               type string;
               description
                 "Nexthop non-key opaque handle";
             }
             leaf nh-key-opaque-dump {
               type string;
               description
                 "Nexthop key opaque app dump";
             }
             leaf nh-non-key-opaque-dump {
               type string;
               description
                 "Nexthop non-key opaque app dump";
             }
             leaf nh-flood-overflow {
               type empty;
               description
                 "Flood nexthop exceeds maximum branches";
             }
             leaf nh-kernel-id {
               type int32;
               description
                 "Table Id for this next hop";
             }
           }
           list nh-expand {
             key "nhe-name nhe-handle";
             description
               "Next-hop gateway information";
             leaf nhe-name {
               type string;
               description
                 "Name of next-hop";
             }
             leaf nhe-handle {
               type string;
               description
                 "Nexthop pointer";
             }
             leaf nhe-index {
               type int32;
               description
                 "Next-hop index";
             }
             leaf nhe-to {
               type string;
               description
                 "Nexthop address";
             }
             leaf nhe-mbr-count {
               type int32;
               description
                 "Number of child nexhops";
             }
             leaf nhe-mpls-label {
               type string;
               description
                 "Label of MPLS packet";
             }
           }
           list rt-session-id {
             key "rt-session-id-value";
             description
               "Session-IDs associated with route";
             leaf rt-session-id-value {
               type int32;
               description
                 "Value of session-id";
             }
             leaf rt-session-id-version {
               type int32;
               description
                 "Version of session-id";
             }
           }
           container flex-rt-statistics {
             description
               "Statistics associated with route";
             leaf flex-rt-statistics-pkts-count {
               type int32;
               description
                 "Packet count";
             }
             leaf flex-rt-statistics-pps {
               type int32;
               description
                 "Pps";
             }
             leaf flex-rt-statistics-bytes-count {
               type int32;
               description
                 "Byte count";
             }
             leaf flex-rt-statistics-bps {
               type int32;
               description
                 "Bps";
             }
           }
           leaf bgp-group-name {
             type string;
           }
           leaf bgp-no-label-reason {
             type string;
           }
           leaf sr-policy-distinguisher {
             type uint32;
           }
           leaf sr-policy-color {
             type uint32;
           }
           leaf sr-policy-endpoint {
             type jt:ipaddr;
           }
           leaf bgp-metric-flags {
             type string;
             description
               "BGP metrics flags";
           }
           leaf bgp-output-queue-class {
             type string;
             description
               "BGP output queue class";
           }
           leaf cluster-id {
             type string;
           }
           leaf originator {
             type string;
           }
           leaf bgp-aigp {
             type string;
             description
               "Accumulated IGP Metric";
           }
           leaf bgp-elc {
             type empty;
             description
               "Entropy label capable";
           }
           leaf bgp-elc-v2 {
             type empty;
             description
               "Entropy label capable version 2";
           }
           leaf bgp-elc-v3 {
             type empty;
             description
               "Entropy label capable version 3";
           }
           leaf bgp-nhc-unknown-characteristics-len {
             type uint32;
             description
               "Total length of NHC unknown characteristics";
           }
           leaf bgp-nhc-nh-valid {
             type string;
             description
               "Whether next hop field matches route next hop";
           }
           leaf bgp-nhc-characteristic-code {
             type uint32;
             description
               "NHC characteristic code";
           }
           leaf bgp-nhc-characteristic-len {
             type uint32;
             description
               "NHC characteristic length";
           }
           leaf bgp-nhc-characteristic-val {
             type string;
             description
               "NHC characteristic value";
           }
         }
         list kern-nhexpand {
           key "kern-nhe-name kern-nhe-handle";
           description
             "Next-hop gateway information";
           container srv6-info {
             leaf srv6-info-srh-sid-mode {
               type string;
               description
                 "Reduced/non-reduced mode for SRH";
             }
             leaf srv6-info-packet-mode {
               type string;
               description
                 "Packet mode for SRV6-Tunnel";
             }
             leaf srv6-info-srh-last-sid {
               type string;
               description
                 "Remove last sid for ACX";
             }
             leaf srv6-info-dyn-tunnel {
               type string;
               description
                 "SRv6 tunnel created dynamically";
             }
             leaf srv6-cos-propagation {
               type string;
               description
                 "SRv6 CoS propagation";
             }
             leaf srv6-ttl-propagation {
               type string;
               description
                 "SRv6 TTL propagation";
             }
             leaf srv6-source {
               type jt:ipaddr;
               description
                 "Source IPv6 address";
             }
             leaf srv6-destination {
               type jt:ipaddr;
               description
                 "Destination IPv6 address";
             }
             list srv6-segment-list {
               key "srv6-segment-list-index";
               description
                 "SRH Segment list";
               leaf srv6-segment-list-index {
                 type uint32;
                 description
                   "SRH segment list index";
               }
               leaf srv6-segment-list-addr {
                 type jt:ipaddr;
                 description
                   "SRH segment address";
               }
             }
           }
           leaf kern-nhe-platform-layer-input {
             type empty;
             description
               "Platform layer input nexthop";
           }
           leaf kern-nhe-platform-layer-output {
             type empty;
             description
               "Platform layer output nexthop";
           }
           leaf kern-nhe-in-kernel {
             type empty;
             description
               "Nexthop install in kernel";
           }
           leaf kern-nhe-fib-channel {
             type string;
             description
               "Fib channel in which route is installed";
           }
           leaf kern-nhe-name {
             type string;
             description
               "Name of next-hop";
           }
           leaf kern-nhe-subtype {
             type string;
             description
               "Nexthop Subtype";
           }
           leaf kern-nhe-handle {
             type string;
             description
               "Nexthop pointer";
           }
           leaf kern-nhe-index {
             type int32;
             description
               "Next-hop index";
           }
           leaf kern-gw-flags {
             type string;
             description
               "Nexthop gateway flags";
           }
           leaf kern-gw-opaque {
             type string;
             description
               "Nexthop gateway opaque data handle";
           }
           leaf kern-key-opaque {
             type string;
             description
               "Nexthop key opaque data handle";
           }
           leaf kern-nhe-to {
             type string;
             description
               "Nexthop address";
           }
           leaf kern-nhe-mbr-count {
             type int32;
             description
               "Number of child nexhops";
           }
           leaf kern-nhe-mpls-label {
             type string;
             description
               "Label of MPLS packet";
           }
           leaf kern-nhe-pnh {
             type string;
             description
               "Protocol Nexthop address";
           }
           leaf kern-nhe-fib-nh-str {
             type string;
             description
               "FIB inh or cnh identifier";
           }
           leaf kern-nhe-sessionid {
             type int32;
             description
               "Session ID";
           }
           leaf kern-nhe-tunnel-type {
             type string;
             description
               "Tunnel type";
           }
           leaf kern-nhe-tunnel-src {
             type string;
             description
               "Tunnel Source address";
           }
           leaf kern-nhe-tunnel-dest {
             type string;
             description
               "Tunnel Destination address";
           }
           leaf kern-nhe-tunnel-ep {
             type string;
             description
               "Tunnel Endpoint address";
           }
           leaf kern-nhe-tunnel-vxlan-encap-vni {
             type int32;
             description
               "VxLAN tunnel encap vni";
           }
           leaf kern-nhe-tunnel-vxlan-decap-vni {
             type int32;
             description
               "VxLAN tunnel decap vni";
           }
           leaf kern-nhe-translate-type {
             type string;
             description
               "Translation type";
           }
           leaf kern-nhe-translate-src {
             type string;
             description
               "Translation Source address";
           }
           leaf kern-nhe-translate-src-plen {
             type int32;
             description
               "Translation Source address prefix length";
           }
           leaf kern-nhe-translate-dest {
             type string;
             description
               "Translation Destination address";
           }
           leaf kern-nhe-translate-dest-plen {
             type int32;
             description
               "Translation Destination address prefix length";
           }
           leaf kern-nhe-tunnel-encap-rtb-id {
             type int32;
             description
               "Tunnel encap routing table id";
           }
           leaf kern-nhe-tunnel-decap-rtb-id {
             type int32;
             description
               "Tunnel decap routing table id";
           }
           leaf kern-nhe-interface {
             type string;
             description
               "Interface";
           }
           leaf kern-nhe-slice-gencfg-id {
             type int32;
             description
               "Slice-Gencfg ID";
           }
           leaf kern-nhe-sliceid {
             type int32;
             description
               "Slice ID";
           }
           leaf kern-nhe-fwf {
             type string;
             description
               "Filter Name";
           }
           leaf kern-nhe-flex-tunnel-info {
             type string;
             description
               "Flex-tunnel information of nexthop";
           }
           leaf kern-nhe-flags {
             type string;
             description
               "Nexthop flags";
           }
           leaf kern-nhe-stats-id-group {
             type string;
             description
               "Statistics ID Group associated with nexthop";
           }
           leaf kern-nhe-reference-count {
             type int32;
             description
               "Nexthop reference count";
           }
           leaf kern-elnh-address {
             type string;
             description
               "Address of Element Next-hop";
           }
         }
         leaf rt-entry-count {
           type int32;
           description
             "Number of route entries in this route";
         }
         leaf rt-announced-count {
           type int32;
           description
             "Number of announced route entries";
         }
         leaf rt-state {
           type string;
           description
             "State of this route";
         }
         leaf-list tsi {
           type string;
           description
             "Task-specific information";
         }
         container communities {
           leaf-list community {
             type string;
             description
               "Basic community";
           }
           leaf-list extended-community {
             type string;
             description
               "Extended community";
           }
           leaf-list ipv6-extended-community {
             type string;
             description
               "IPv6 extended community";
           }
         }
         list bgp-tunnel-attribute {
           key "tunnel-attribute-type";
           description
             "Tunne encap attribute information";
           leaf tunnel-attribute-type {
             type string;
           }
           leaf tunnel-attribute-rpf {
             type empty;
           }
           leaf tunnel-attribute-color {
             type uint32;
           }
           leaf tunnel-attribute-destination {
             type jt:ipaddr;
           }
         }
       }
       container route-state-history {
         list route-state-history-elements {
           key "rt-history-time";
           leaf rt-history-time {
             type string;
           }
           leaf rt-history-event {
             type string;
           }
         }
       }
     }
   }
   grouping rtflow-dep-information-block {
     container rtflow-dep-table {
       leaf table-name {
         type string;
         description
           "Unicast routing table";
       }
       container fdep-node {
         leaf fdep-destination {
           type string;
           description
             "Destination prefix for tree node";
         }
         leaf fdep-prefixlen {
           type uint32;
           description
             "Destination prefix length for tree node";
         }
         container fdep-inode {
           leaf fdep-inode-color {
             type string;
           }
           leaf fdep-inode-consist {
             type string;
           }
           leaf fdep-inode-asn {
             type uint32;
             description
               "Neighbor AS for all more specific unicast routes";
           }
         }
         container fdep-rtnode {
           description
             "Entry that corresponding to a unicast route that is being 
             tracked";
           leaf rtnode-state {
             type string;
           }
           leaf rtnode-origin {
             type jt:ipaddr;
             description
               "Unicast route origin (BGP gateway address or originator 
               attribute";
           }
           leaf rtnode-next-as {
             type uint32;
             description
               "Neighbor AS for active unicast route";
           }
           leaf rtnode-refcount {
             type uint32;
             description
               "Dependent flow destinations";
           }
           leaf rtnode-flags {
             type string;
           }
         }
         container fdep-depnode {
           leaf dep-entries {
             type uint32;
             description
               "Number of flow routes with this destination address";
           }
           leaf dep-active {
             type uint32;
             description
               "Number of flow routes which match unicast origin";
           }
           leaf dep-rtnode-prefix {
             type jt:ipaddr;
             description
               "Prefix of unicast route used to resolve this flow 
               destination";
           }
           leaf dep-rtnode-prefixlen {
             type uint32;
             description
               "Prefix length of unicast route used to resolve this flow 
               destination";
           }
           leaf dep-flags {
             type string;
           }
         }
       }
     }
   }
   grouping route-resolution-information-block {
     list route-resolution-tree {
       key "tree-index";
       leaf tree-index {
         type int32;
         description
           "Index of the resolution tree";
       }
       leaf nodes {
         type int32;
         description
           "Number of resolution nodes in the tree";
       }
       leaf tree-reference-count {
         type int32;
         description
           "Reference count on the tree";
       }
       leaf tree-policy {
         type string;
         description
           "Import policy on the tree";
       }
       leaf urpf-count {
         type int32;
         description
           "URPF enabled count";
       }
       leaf pe-pe-cnh-status {
         type int32;
         description
           "PE-PE-CNH enabled";
       }
       leaf-list tree-contributing-ribs {
         type string;
         description
           "Name of routing table inserting routes in the tree";
       }
       container protocol-nh {
         description
           "Protocol next hop";
         leaf to {
           type string;
           description
             "Neighbor address to which to send (next-hop address)";
         }
         leaf metric {
           type int32;
         }
         leaf aigp {
           type string;
           description
             "AIGP";
         }
         leaf balance {
           type int32;
           description
             "Next-hop balance";
         }
         leaf flags {
           type string;
           description
             "Enabled trace flags";
         }
         leaf res-state {
           type string;
           description
             "Status of route resolution";
         }
         leaf res-tsp-idx {
           type int32;
           description
             "TSP index of the path";
         }
         leaf-list res-path-aux {
           type string;
         }
         leaf-list res-path-aux-type {
           type string;
         }
         leaf-list res-path-aux-flags {
           type string;
         }
         leaf-list res-path-aux-rs-name {
           type string;
         }
         leaf-list res-path-aux-rs-ribs {
           type string;
         }
         leaf-list res-path-inode-flags {
           type string;
         }
         leaf-list res-path-flags {
           type string;
         }
         leaf-list res-path-fnh-link {
           type string;
         }
         leaf-list res-path-inh-link {
           type string;
         }
         leaf mpls-label {
           type string;
           description
             "Label of MPLS packet";
         }
         leaf label-ttl-action {
           type string;
           description
             "TTL action associated with labels";
         }
         leaf load-balance-label {
           type string;
           description
             "Load balance action associated with labels";
         }
         leaf-list composite-nh {
           type string;
         }
         leaf-list pnh-statistics-id-group {
           type string;
           description
             "Statistics ID Group Associated with this protocol NH";
         }
         leaf-list vpnlabel-nh {
           type string;
         }
         leaf-list indirect-nh {
           type string;
         }
         leaf ext-int-type {
           type string;
           description
             "Next-hop type of equal-external-internal multipath";
         }
         leaf gw-opaque {
           type string;
           description
             "Nexthops gateway opaque data handle";
         }
         leaf-list forwarding-nh-count {
           type int32;
           description
             "Number of indirect path forwarding next hops";
         }
         leaf-list merged-forwarding-nh-count {
           type int32;
           description
             "Number of indirect path forwarding next hops (Merged)";
         }
         leaf nh-type {
           type string;
           description
             "Special next hop: Reject, Blackhole, Receive, Multicast, 
             Local, or Unused";
         }
         leaf-list node-prefix {
           type string;
         }
         leaf-list node-prefix-length {
           type int32;
         }
         leaf-list originating-rib {
           type string;
           description
             "Routing table from which this route was learned";
         }
         leaf-list node-metric {
           type int32;
         }
         leaf-list node-path-count {
           type int32;
           description
             "Number of paths for this node";
         }
         leaf node-flags {
           type int32;
           description
             "Flags for this node";
         }
         leaf-list node-address {
           type string;
         }
         leaf-list node-forwarding-nh-count {
           type int32;
         }
         leaf-list nh-subtype {
           type string;
           description
             "Specified nexthop subtype";
         }
         leaf indirect-nh-count {
           type int32;
           description
             "Number of indirect next hops";
         }
         leaf composite-nh-count {
           type int32;
           description
             "Number of composite next hops";
         }
         list nh {
           description
             "Next-hop gateway information";
           container vxlan-header-rewrite {
             description
               "VXLAN tunnel rewrite information";
             leaf vxlan-header-rewrite-mtu {
               type int32;
               description
                 "VXLAN tunnel MTU";
             }
             leaf vxlan-header-rewrite-flags {
               type int32;
               description
                 "VXLAN tunnel flags";
             }
             leaf vxlan-header-rewrite-encap-rtb-id {
               type int32;
               description
                 "VXLAN tunnel encapsulation table ID";
             }
             leaf vxlan-header-rewrite-decap-rtb-id {
               type int32;
               description
                 "VXLAN tunnel decapsulation table ID";
             }
             leaf vxlan-header-rewrite-encap-vnid {
               type int32;
               description
                 "VXLAN tunnel encapsulation VNI";
             }
             leaf vxlan-header-rewrite-decap-vnid {
               type int32;
               description
                 "VXLAN tunnel decapsulation VNI";
             }
             leaf vxlan-header-rewrite-svtep {
               type jt:ipaddr;
               description
                 "Source VTEP address";
             }
             leaf vxlan-header-rewrite-dvtep {
               type jt:ipaddr;
               description
                 "Destination VTEP address";
             }
             leaf vxlan-header-rewrite-smac {
               type string;
               description
                 "Source MAC address";
             }
             leaf vxlan-header-rewrite-dmac {
               type string;
               description
                 "Destination MAC address";
             }
           }
           container srv6-info {
             leaf srv6-info-srh-sid-mode {
               type string;
               description
                 "Reduced/non-reduced mode for SRH";
             }
             leaf srv6-info-packet-mode {
               type string;
               description
                 "Packet mode for SRV6-Tunnel";
             }
             leaf srv6-info-srh-last-sid {
               type string;
               description
                 "Remove last sid for ACX";
             }
             leaf srv6-info-dyn-tunnel {
               type string;
               description
                 "SRv6 tunnel created dynamically";
             }
             leaf srv6-cos-propagation {
               type string;
               description
                 "SRv6 CoS propagation";
             }
             leaf srv6-ttl-propagation {
               type string;
               description
                 "SRv6 TTL propagation";
             }
             leaf srv6-source {
               type jt:ipaddr;
               description
                 "Source IPv6 address";
             }
             leaf srv6-destination {
               type jt:ipaddr;
               description
                 "Destination IPv6 address";
             }
             list srv6-segment-list {
               key "srv6-segment-list-index";
               description
                 "SRH Segment list";
               leaf srv6-segment-list-index {
                 type uint32;
                 description
                   "SRH segment list index";
               }
               leaf srv6-segment-list-addr {
                 type jt:ipaddr;
                 description
                   "SRH segment address";
               }
             }
           }
         }
       }
     }
   }
   grouping route-resolution-unresolved-information-block {
     list route-resolution-unresolved {
       key "resolution-unresolved-tree-index";
       leaf resolution-unresolved-tree-index {
         type uint32;
       }
       leaf resolution-unresolved-tree-address {
         type string;
       }
       container protocol-nh {
         description
           "Protocol next hop";
         leaf to {
           type string;
           description
             "Neighbor address to which to send (next-hop address)";
         }
         leaf metric {
           type int32;
         }
         leaf aigp {
           type string;
           description
             "AIGP";
         }
         leaf balance {
           type int32;
           description
             "Next-hop balance";
         }
         leaf flags {
           type string;
           description
             "Enabled trace flags";
         }
         leaf res-state {
           type string;
           description
             "Status of route resolution";
         }
         leaf res-tsp-idx {
           type int32;
           description
             "TSP index of the path";
         }
         leaf-list res-path-aux {
           type string;
         }
         leaf-list res-path-aux-type {
           type string;
         }
         leaf-list res-path-aux-flags {
           type string;
         }
         leaf-list res-path-aux-rs-name {
           type string;
         }
         leaf-list res-path-aux-rs-ribs {
           type string;
         }
         leaf-list res-path-inode-flags {
           type string;
         }
         leaf-list res-path-flags {
           type string;
         }
         leaf-list res-path-fnh-link {
           type string;
         }
         leaf-list res-path-inh-link {
           type string;
         }
         leaf mpls-label {
           type string;
           description
             "Label of MPLS packet";
         }
         leaf label-ttl-action {
           type string;
           description
             "TTL action associated with labels";
         }
         leaf load-balance-label {
           type string;
           description
             "Load balance action associated with labels";
         }
         leaf-list composite-nh {
           type string;
         }
         leaf-list pnh-statistics-id-group {
           type string;
           description
             "Statistics ID Group Associated with this protocol NH";
         }
         leaf-list vpnlabel-nh {
           type string;
         }
         leaf-list indirect-nh {
           type string;
         }
         leaf ext-int-type {
           type string;
           description
             "Next-hop type of equal-external-internal multipath";
         }
         leaf gw-opaque {
           type string;
           description
             "Nexthops gateway opaque data handle";
         }
         leaf-list forwarding-nh-count {
           type int32;
           description
             "Number of indirect path forwarding next hops";
         }
         leaf-list merged-forwarding-nh-count {
           type int32;
           description
             "Number of indirect path forwarding next hops (Merged)";
         }
         leaf nh-type {
           type string;
           description
             "Special next hop: Reject, Blackhole, Receive, Multicast, 
             Local, or Unused";
         }
         leaf-list node-prefix {
           type string;
         }
         leaf-list node-prefix-length {
           type int32;
         }
         leaf-list originating-rib {
           type string;
           description
             "Routing table from which this route was learned";
         }
         leaf-list node-metric {
           type int32;
         }
         leaf-list node-path-count {
           type int32;
           description
             "Number of paths for this node";
         }
         leaf node-flags {
           type int32;
           description
             "Flags for this node";
         }
         leaf-list node-address {
           type string;
         }
         leaf-list node-forwarding-nh-count {
           type int32;
         }
         leaf-list nh-subtype {
           type string;
           description
             "Specified nexthop subtype";
         }
         leaf indirect-nh-count {
           type int32;
           description
             "Number of indirect next hops";
         }
         leaf composite-nh-count {
           type int32;
           description
             "Number of composite next hops";
         }
         list nh {
           description
             "Next-hop gateway information";
           container vxlan-header-rewrite {
             description
               "VXLAN tunnel rewrite information";
             leaf vxlan-header-rewrite-mtu {
               type int32;
               description
                 "VXLAN tunnel MTU";
             }
             leaf vxlan-header-rewrite-flags {
               type int32;
               description
                 "VXLAN tunnel flags";
             }
             leaf vxlan-header-rewrite-encap-rtb-id {
               type int32;
               description
                 "VXLAN tunnel encapsulation table ID";
             }
             leaf vxlan-header-rewrite-decap-rtb-id {
               type int32;
               description
                 "VXLAN tunnel decapsulation table ID";
             }
             leaf vxlan-header-rewrite-encap-vnid {
               type int32;
               description
                 "VXLAN tunnel encapsulation VNI";
             }
             leaf vxlan-header-rewrite-decap-vnid {
               type int32;
               description
                 "VXLAN tunnel decapsulation VNI";
             }
             leaf vxlan-header-rewrite-svtep {
               type jt:ipaddr;
               description
                 "Source VTEP address";
             }
             leaf vxlan-header-rewrite-dvtep {
               type jt:ipaddr;
               description
                 "Destination VTEP address";
             }
             leaf vxlan-header-rewrite-smac {
               type string;
               description
                 "Source MAC address";
             }
             leaf vxlan-header-rewrite-dmac {
               type string;
               description
                 "Destination MAC address";
             }
           }
           container srv6-info {
             leaf srv6-info-srh-sid-mode {
               type string;
               description
                 "Reduced/non-reduced mode for SRH";
             }
             leaf srv6-info-packet-mode {
               type string;
               description
                 "Packet mode for SRV6-Tunnel";
             }
             leaf srv6-info-srh-last-sid {
               type string;
               description
                 "Remove last sid for ACX";
             }
             leaf srv6-info-dyn-tunnel {
               type string;
               description
                 "SRv6 tunnel created dynamically";
             }
             leaf srv6-cos-propagation {
               type string;
               description
                 "SRv6 CoS propagation";
             }
             leaf srv6-ttl-propagation {
               type string;
               description
                 "SRv6 TTL propagation";
             }
             leaf srv6-source {
               type jt:ipaddr;
               description
                 "Source IPv6 address";
             }
             leaf srv6-destination {
               type jt:ipaddr;
               description
                 "Destination IPv6 address";
             }
             list srv6-segment-list {
               key "srv6-segment-list-index";
               description
                 "SRH Segment list";
               leaf srv6-segment-list-index {
                 type uint32;
                 description
                   "SRH segment list index";
               }
               leaf srv6-segment-list-addr {
                 type jt:ipaddr;
                 description
                   "SRH segment address";
               }
             }
           }
         }
       }
     }
     container protocol-nh {
       description
         "Protocol next hop";
       leaf to {
         type string;
         description
           "Neighbor address to which to send (next-hop address)";
       }
       leaf metric {
         type int32;
       }
       leaf aigp {
         type string;
         description
           "AIGP";
       }
       leaf balance {
         type int32;
         description
           "Next-hop balance";
       }
       leaf flags {
         type string;
         description
           "Enabled trace flags";
       }
       leaf res-state {
         type string;
         description
           "Status of route resolution";
       }
       leaf res-tsp-idx {
         type int32;
         description
           "TSP index of the path";
       }
       leaf-list res-path-aux {
         type string;
       }
       leaf-list res-path-aux-type {
         type string;
       }
       leaf-list res-path-aux-flags {
         type string;
       }
       leaf-list res-path-aux-rs-name {
         type string;
       }
       leaf-list res-path-aux-rs-ribs {
         type string;
       }
       leaf-list res-path-inode-flags {
         type string;
       }
       leaf-list res-path-flags {
         type string;
       }
       leaf-list res-path-fnh-link {
         type string;
       }
       leaf-list res-path-inh-link {
         type string;
       }
       leaf mpls-label {
         type string;
         description
           "Label of MPLS packet";
       }
       leaf label-ttl-action {
         type string;
         description
           "TTL action associated with labels";
       }
       leaf load-balance-label {
         type string;
         description
           "Load balance action associated with labels";
       }
       leaf-list composite-nh {
         type string;
       }
       leaf-list pnh-statistics-id-group {
         type string;
         description
           "Statistics ID Group Associated with this protocol NH";
       }
       leaf-list vpnlabel-nh {
         type string;
       }
       leaf-list indirect-nh {
         type string;
       }
       leaf ext-int-type {
         type string;
         description
           "Next-hop type of equal-external-internal multipath";
       }
       leaf gw-opaque {
         type string;
         description
           "Nexthops gateway opaque data handle";
       }
       leaf-list forwarding-nh-count {
         type int32;
         description
           "Number of indirect path forwarding next hops";
       }
       leaf-list merged-forwarding-nh-count {
         type int32;
         description
           "Number of indirect path forwarding next hops (Merged)";
       }
       leaf nh-type {
         type string;
         description
           "Special next hop: Reject, Blackhole, Receive, Multicast, Local, 
           or Unused";
       }
       leaf-list node-prefix {
         type string;
       }
       leaf-list node-prefix-length {
         type int32;
       }
       leaf-list originating-rib {
         type string;
         description
           "Routing table from which this route was learned";
       }
       leaf-list node-metric {
         type int32;
       }
       leaf-list node-path-count {
         type int32;
         description
           "Number of paths for this node";
       }
       leaf node-flags {
         type int32;
         description
           "Flags for this node";
       }
       leaf-list node-address {
         type string;
       }
       leaf-list node-forwarding-nh-count {
         type int32;
       }
       leaf-list nh-subtype {
         type string;
         description
           "Specified nexthop subtype";
       }
       leaf indirect-nh-count {
         type int32;
         description
           "Number of indirect next hops";
       }
       leaf composite-nh-count {
         type int32;
         description
           "Number of composite next hops";
       }
       list nh {
         description
           "Next-hop gateway information";
         container vxlan-header-rewrite {
           description
             "VXLAN tunnel rewrite information";
           leaf vxlan-header-rewrite-mtu {
             type int32;
             description
               "VXLAN tunnel MTU";
           }
           leaf vxlan-header-rewrite-flags {
             type int32;
             description
               "VXLAN tunnel flags";
           }
           leaf vxlan-header-rewrite-encap-rtb-id {
             type int32;
             description
               "VXLAN tunnel encapsulation table ID";
           }
           leaf vxlan-header-rewrite-decap-rtb-id {
             type int32;
             description
               "VXLAN tunnel decapsulation table ID";
           }
           leaf vxlan-header-rewrite-encap-vnid {
             type int32;
             description
               "VXLAN tunnel encapsulation VNI";
           }
           leaf vxlan-header-rewrite-decap-vnid {
             type int32;
             description
               "VXLAN tunnel decapsulation VNI";
           }
           leaf vxlan-header-rewrite-svtep {
             type jt:ipaddr;
             description
               "Source VTEP address";
           }
           leaf vxlan-header-rewrite-dvtep {
             type jt:ipaddr;
             description
               "Destination VTEP address";
           }
           leaf vxlan-header-rewrite-smac {
             type string;
             description
               "Source MAC address";
           }
           leaf vxlan-header-rewrite-dmac {
             type string;
             description
               "Destination MAC address";
           }
         }
         container srv6-info {
           leaf srv6-info-srh-sid-mode {
             type string;
             description
               "Reduced/non-reduced mode for SRH";
           }
           leaf srv6-info-packet-mode {
             type string;
             description
               "Packet mode for SRV6-Tunnel";
           }
           leaf srv6-info-srh-last-sid {
             type string;
             description
               "Remove last sid for ACX";
           }
           leaf srv6-info-dyn-tunnel {
             type string;
             description
               "SRv6 tunnel created dynamically";
           }
           leaf srv6-cos-propagation {
             type string;
             description
               "SRv6 CoS propagation";
           }
           leaf srv6-ttl-propagation {
             type string;
             description
               "SRv6 TTL propagation";
           }
           leaf srv6-source {
             type jt:ipaddr;
             description
               "Source IPv6 address";
           }
           leaf srv6-destination {
             type jt:ipaddr;
             description
               "Destination IPv6 address";
           }
           list srv6-segment-list {
             key "srv6-segment-list-index";
             description
               "SRH Segment list";
             leaf srv6-segment-list-index {
               type uint32;
               description
                 "SRH segment list index";
             }
             leaf srv6-segment-list-addr {
               type jt:ipaddr;
               description
                 "SRH segment address";
             }
           }
         }
       }
     }
   }
   grouping route-resolution-scheme-information-block {
     list route-resolution-scheme {
       key "rs-scheme-name";
       leaf rs-scheme-name {
         type string;
         description
           "Name of resolution scheme";
       }
       leaf rs-scheme-attr {
         type string;
         description
           "Attributes of resolution scheme";
       }
       leaf rs-scheme-ref-cnt {
         type int32;
         description
           "Number of references to this resolution scheme";
       }
       leaf rs-map-community {
         type int32;
         description
           "The BGP Community that maps to this resolution-scheme";
       }
       leaf rs-tree-handle {
         type string;
         description
           "Handle of the resolution tree";
       }
       leaf rs-tree-index {
         type int32;
         description
           "Index of the resolution tree";
       }
       leaf rs-nodes {
         type int32;
         description
           "Number of resolution nodes in the tree";
       }
       leaf rs-tree-flags {
         type string;
         description
           "Resolution rib preference for tree";
       }
       leaf rs-tree-policy {
         type string;
         description
           "Import policy on the tree";
       }
       leaf-list rs-transport-ribs {
         type string;
         description
           "Name of Transport RIBs";
       }
     }
   }
   grouping route-resolution-list-nh-information-block {
     list route-resolution-list-nh {
       leaf list-nh-indirect-nh {
         type string;
         description
           "Indirect-nexthop handle";
       }
       leaf-list list-nh-indirect-address {
         type jt:ipaddr;
         description
           "Indirect protocol nexthop address";
       }
       leaf list-nh-indirect-unmatch {
         type int32;
         description
           "No matching indirect next hop found";
       }
       leaf list-nh-indirect-deleted {
         type string;
         description
           "Indirect next hop removed from DB, discontinue walking the tree";
       }
     }
     list route-resolution-list-nh-node {
       leaf list-nh-multipath-route {
         type string;
         description
           "Multipath route entry";
       }
       leaf list-nh-multipath-address {
         type jt:ipaddr;
         description
           "Multipath route address";
       }
       leaf list-nh-multipath-node {
         type string;
         description
           "Multipath route resolver node";
       }
     }
     container route-resolution-list-nh-statistics {
       leaf list-nh-node-inh-add-total {
         type uint64;
         description
           "Total Indirect-nexthop added";
       }
       leaf list-nh-node-inh-delete-total {
         type uint64;
         description
           "Total Indirect-nexthop deleted";
       }
       leaf list-nh-node-inh-change-registered {
         type string;
         description
           "Indirect change hook registered";
       }
     }
   }
   grouping route-resolution-active-helpers-information-block {
     list route-resolution-active-helpers {
       leaf tree-index {
         type int32;
         description
           "Index of the resolution tree";
       }
       leaf nodes {
         type int32;
         description
           "Number of resolution nodes in the tree";
       }
       leaf tree-reference-count {
         type int32;
         description
           "Reference count on the tree";
       }
       leaf tree-policy {
         type string;
         description
           "Import policy on the tree";
       }
       leaf urpf-count {
         type int32;
         description
           "URPF enabled count";
       }
       leaf pe-pe-cnh-status {
         type int32;
         description
           "PE-PE-CNH enabled";
       }
       leaf-list tree-contributing-ribs {
         type string;
         description
           "Name of routing table inserting routes in the tree";
       }
     }
   }
   grouping route-resolution-active-helpers-statistics-block {
     list route-active-helper-statistics-tree {
       leaf tree-index {
         type int32;
         description
           "Index of the resolution tree";
       }
       leaf nodes {
         type int32;
         description
           "Number of resolution nodes in the tree";
       }
       leaf tree-reference-count {
         type int32;
         description
           "Reference count on the tree";
       }
       leaf tree-policy {
         type string;
         description
           "Import policy on the tree";
       }
       leaf urpf-count {
         type int32;
         description
           "URPF enabled count";
       }
       leaf pe-pe-cnh-status {
         type int32;
         description
           "PE-PE-CNH enabled";
       }
       leaf-list tree-contributing-ribs {
         type string;
         description
           "Name of routing table inserting routes in the tree";
       }
       list ah-node {
         leaf-list node-prefix {
           type string;
         }
         leaf-list node-prefix-length {
           type int32;
         }
         leaf-list originating-rib {
           type string;
           description
             "Routing table from which this route was learned";
         }
         leaf re-resolve-inh-list-change {
           type uint32;
         }
         leaf re-resolve-inh-change {
           type uint32;
         }
         leaf re-resolve-list-nh-child-nh-change {
           type uint32;
         }
         leaf re-resolve-list-nh-change-to-singular-nh {
           type uint32;
         }
         leaf re-resolve-more-specific-node-add {
           type uint32;
         }
         leaf re-resolve-change-in-helper-node-path-count {
           type uint32;
         }
         leaf re-resolve-rt-flash-add-type-1 {
           type uint32;
         }
         leaf re-resolve-rt-flash-add-type-2 {
           type uint32;
         }
         leaf re-resolve-change-in-helper-node {
           type uint32;
         }
         leaf re-resolve-policy-change {
           type uint32;
         }
         leaf re-resolve-global-config-changed {
           type uint32;
         }
         leaf re-resolve-rt-nhn-attrib-changed {
           type uint32;
         }
         leaf re-resolve-dyn-tunnel-related-type-1 {
           type uint32;
         }
         leaf re-resolve-dyn-tunnel-related-type-2 {
           type uint32;
         }
         leaf re-resolve-helper-node-delete {
           type uint32;
         }
         leaf re-resolve-rsvp-route-bw-change {
           type uint32;
         }
         leaf re-resolve-given-tsp-and-pnh {
           type uint32;
         }
         leaf re-resolve-rnni-not-found {
           type uint32;
         }
         leaf re-resolve-tree-stop {
           type uint32;
         }
         leaf re-resolve-backup-path-used {
           type uint32;
         }
         leaf re-resolve-unresolve-path {
           type uint32;
         }
         leaf re-resolve-queue-inode-dep {
           type uint32;
         }
         leaf re-resolve-sec-route-ind-res {
           type uint32;
         }
         leaf re-resolve-sec-route-no-ind-res {
           type uint32;
         }
         leaf re-resolve-resize-inode {
           type uint32;
         }
         leaf re-resolve-delete-route {
           type uint32;
         }
         leaf re-resolve-delete-sec-route {
           type uint32;
         }
         leaf re-resolve-optimize-reresolution {
           type uint32;
         }
       }
     }
   }
   grouping route-resolution-loop-information-block {
     list route-resolution-loop-event {
       container route-resolution-tree-id {
         leaf resolution-index {
           type uint32;
         }
       }
       list route-resolution-loop-event-item {
         key "route-resolution-loop-index";
         leaf route-resolution-loop-index {
           type int32;
         }
         leaf route-resolution-loop-event-timestamp {
           type string;
         }
         leaf route-resolution-loop-service-route {
           type string;
         }
         leaf route-resolution-loop-service-route-proto {
           type string;
         }
         leaf route-resolution-loop-service-route-ribid {
           type uint32;
         }
         leaf route-resolution-loop-helper-route {
           type string;
         }
         leaf route-resolution-loop-helper-route-proto {
           type string;
         }
         leaf route-resolution-loop-helper-route-ribid {
           type uint32;
         }
       }
     }
   }
   grouping route-reresolution-history-information-block {
     list route-reresolution-history-event {
       leaf tree-index {
         type int32;
         description
           "Index of the resolution tree";
       }
       list route-reresolution-event-item {
         key "route-reresolution-event-index";
         leaf route-reresolution-event-index {
           type int32;
         }
         leaf route-reresolution-event-timestamp {
           type string;
         }
         leaf route-reresolution-helper-route {
           type string;
         }
         leaf route-reresolution-helper-route-proto {
           type string;
         }
         leaf route-reresolution-helper-route-ribid {
           type uint32;
         }
         leaf route-reresolution-reason {
           type string;
         }
       }
     }
   }
   grouping route-prefix-length-distribution-block {
     list route-table {
       key "table-name";
       leaf table-name {
         type string;
         description
           "Unicast routing table";
       }
       list protocols {
         key "protocol-name";
         leaf protocol-name {
           type string;
         }
         leaf protocol-route-count {
           type int32;
           description
             "Total protocol routes";
         }
         leaf active-route-count {
           type int32;
           description
             "Active routes";
         }
       }
       list rt-prefix-dist {
         key "rt-prefix-length";
         leaf rt-prefix-length {
           type string;
         }
         leaf rt-prefix-count {
           type int32;
         }
       }
       list rt {
         key "rt-destination";
         leaf rt-destination {
           type string;
           description
             "Route prefixes awaiting ACK";
         }
         leaf rt-prefix-length {
           type string;
         }
         list rt-entry {
           leaf active-tag {
             type string;
             description
               "Visual indication of active state of this route entry";
           }
           leaf validation-state {
             type string;
             description
               "Validation-state of a route";
           }
           leaf protocol-name {
             type string;
           }
           leaf preference {
             type int32;
             description
               "Preference for the route";
           }
           leaf metric {
             type int32;
           }
           leaf metric2 {
             type int32;
           }
           leaf nh-type {
             type string;
             description
               "Special next hop: Reject, Blackhole, Receive, Multicast, 
               Local, or Unused";
           }
           leaf as-path {
             type string;
             description
               "Name of AS path regular expression (BGP only)";
           }
           leaf last-active {
             type empty;
             description
               "This route entry was the last active route entry";
           }
           leaf current-active {
             type empty;
             description
               "This route entry is currently active";
           }
           leaf bgp-rt-mult-nh-idx {
             type uint32;
             description
               "BGP multipath nexthop index";
           }
           leaf deleted {
             type empty;
           }
           leaf nh-erc-btid-id {
             type string;
             description
               "ERC Backtrace ID";
           }
           leaf nh-erc-btid-op {
             type string;
             description
               "ERC BTID Operation";
           }
           leaf nh-erc-btid-nreference {
             type int32;
             description
               "ERC Number of BTID References";
           }
           leaf nh-erc-btid-bt {
             type string;
             description
               "ERC BTID Backtrace ";
           }
           container route-record {
             leaf rt-recorded {
               type string;
             }
             leaf nh-address {
               type string;
               description
                 "Address of next hop";
             }
             leaf as-index {
               type int32;
             }
             leaf as-recorded {
               type string;
             }
             leaf com-index {
               type int32;
             }
             leaf com-recorded {
               type string;
             }
           }
           list route-data-dcf {
             key "trunk-id snmp-idx";
             leaf trunk-id {
               type int32;
               description
                 "Trunk Identifier associated with the LAG port";
             }
             leaf snmp-idx {
               type int32;
               description
                 "IFD SNMP index";
             }
             leaf ts {
               type int32;
               description
                 "Timestamp associated with the route";
             }
             leaf class-id {
               type int32;
               description
                 "Class identifier associated with the route";
             }
             leaf rt-flags {
               type string;
               description
                 "Flags associated with the route";
             }
             leaf rt-type {
               type string;
               description
                 "Route type associated with the route";
             }
             leaf rt-proto {
               type string;
               description
                 "Protocol associated with the route";
             }
             leaf rt-l2domain {
               type int32;
               description
                 "L2domain associated with the route";
             }
             leaf rt-mac-addr {
               type jt:mac-addr;
               description
                 "Mac address associated with the route";
             }
             list snpa {
               key "snpa-type";
               leaf snpa-type {
                 type string;
                 description
                   "Type of SNPA";
               }
               list pfe-port-snpa {
                 key "pfe-id";
                 description
                   "PFE Port SNPA";
                 leaf pfe-id {
                   type int32;
                 }
                 leaf port-id {
                   type int32;
                 }
               }
               container network-element-port-snpa {
                 description
                   "Network Element Port SNPA";
                 leaf port-id {
                   type int32;
                 }
               }
               container mstp-root-snpa {
                 description
                   "Multiple Spanning Tree Protocol Root SNPA";
                 leaf mstp-root-id {
                   type int32;
                 }
               }
               list gateway-snpa {
                 key "gateway-addr";
                 description
                   "Gateway SNPA";
                 leaf gateway-addr {
                   type jt:ipaddr;
                 }
               }
               container layer2-domain-port-snpa {
                 description
                   "Layer-2 Domain Port SNPA";
                 leaf port-id {
                   type int32;
                 }
               }
               container replication-block-snpa {
                 description
                   "Replication Block SNPA";
                 leaf replication-block-id {
                   type int32;
                 }
               }
               container replication-route-snpa {
                 description
                   "Replication Route SNPA";
                 leaf network-element-id {
                   type jt:ipaddr;
                 }
               }
               container layer2-multicast-port-snpa {
                 description
                   "Layer-2 Multicast Port SNPA";
                 leaf layer2-multicast-port-id {
                   type int32;
                 }
               }
               container inh-snpa {
                 description
                   "Indirection SNPA";
                 leaf inh-id {
                   type int32;
                 }
               }
             }
             leaf snpa-count {
               type int32;
               description
                 "Number of SNPAs in this route";
             }
             leaf snpa-length {
               type int32;
               description
                 "Total length of the SNPAs, in bytes";
             }
             container multicast-member-map-data {
               description
                 "Multicast member map";
               leaf multicast-root-hash {
                 type int32;
               }
               leaf multicast-core-hash {
                 type int32;
               }
               leaf multicast-edge-hash {
                 type int32;
               }
               leaf multicast-member-map {
                 type string;
               }
             }
             container layer3-multicast-data {
               description
                 "Layer3 multicast core key";
               leaf layer3-multicast-corekey {
                 type int32;
               }
             }
             container multicast-vsg-corekey-data {
               description
                 "Vsg multicast core key";
               leaf multicast-vsg-corekey-key {
                 type int32;
               }
               leaf multicast-vsg-corekey-len {
                 type int32;
               }
             }
           }
           container rtd-flow-dep {
             leaf flow-dep-state {
               type string;
             }
             leaf flow-origin {
               type jt:ipaddr;
               description
                 "Originator of the flow information";
             }
             leaf flow-next-as {
               type uint32;
               description
                 "Neighbor AS of the flow information";
             }
             container flow-ucast-rt {
               description
                 "Unicast route used for resolution";
               leaf flow-rtn-dest {
                 type jt:ipaddr;
                 description
                   "Destination address";
               }
               leaf flow-rtn-plen {
                 type int32;
                 description
                   "Prefix length";
               }
               leaf flow-rtn-state {
                 type string;
                 description
                   "Validation entry state";
               }
             }
           }
           container bgp-path-attributes {
             container attr-as-path {
               description
                 "AS Path Attribute";
               leaf attr-length {
                 type string;
               }
               leaf flags {
                 type string;
                 description
                   "Enabled trace flags";
               }
               leaf path-length {
                 type string;
               }
               leaf attr-value {
                 type string;
               }
             }
             container attr-as4-path {
               description
                 "4-byte AS Path Attribute";
               leaf attr-length {
                 type string;
               }
               leaf path-length {
                 type string;
               }
               leaf flags {
                 type string;
                 description
                   "Enabled trace flags";
               }
               leaf attr-value {
                 type string;
               }
             }
             container attr-as-path-effective {
               description
                 "Effective AS-Path Attribute";
               leaf attr-length {
                 type string;
               }
               leaf aspath-effective-string {
                 type string;
               }
               leaf path-length {
                 type string;
               }
               leaf attr-value {
                 type string;
               }
               leaf flags {
                 type string;
                 description
                   "Enabled trace flags";
               }
             }
             container attr-aggregator {
               description
                 "Aggregator Attribute";
               leaf attr-length {
                 type string;
               }
               leaf flags {
                 type string;
                 description
                   "Enabled trace flags";
               }
               leaf aggr-as-number {
                 type string;
               }
               leaf aggr-router-id {
                 type string;
               }
             }
             container attr-aggregator4 {
               description
                 "Aggregator4 Attribute";
               leaf attr-length {
                 type string;
               }
               leaf flags {
                 type string;
                 description
                   "Enabled trace flags";
               }
               leaf aggr-as-number {
                 type string;
               }
               leaf aggr-router-id {
                 type string;
               }
             }
             container attr-cluster-list {
               description
                 "Cluster List Attribute";
               leaf attr-length {
                 type string;
               }
               leaf attr-value {
                 type string;
               }
             }
             container attr-originator-id {
               description
                 "Originator Attribute";
               leaf attr-length {
                 type string;
               }
               leaf attr-value {
                 type string;
               }
             }
             leaf domain-path {
               type string;
             }
             leaf attr-otc {
               type int32;
               description
                 "Only-to-customer attribute";
             }
             container attr-unrecognized {
               description
                 "Unrecognized attributes";
               leaf attr-length {
                 type string;
               }
               leaf attr-flags {
                 type string;
               }
               leaf attr-code {
                 type string;
               }
               leaf attr-value {
                 type string;
               }
             }
           }
           container communities {
             leaf-list community {
               type string;
               description
                 "Basic community";
             }
             leaf-list extended-community {
               type string;
               description
                 "Extended community";
             }
             leaf-list ipv6-extended-community {
               type string;
               description
                 "IPv6 extended community";
             }
           }
           list bgp-tunnel-attribute {
             key "tunnel-attribute-type";
             description
               "Tunne encap attribute information";
             leaf tunnel-attribute-type {
               type string;
             }
             leaf tunnel-attribute-rpf {
               type empty;
             }
             leaf tunnel-attribute-color {
               type uint32;
             }
             leaf tunnel-attribute-destination {
               type jt:ipaddr;
             }
           }
           container attrset {
             container bgp-prefix-sid-attr {
               description
                 "BGP Prefix SID Attribute";
               container bgp-prefix-sid-attr-label-idx-tlv {
                 leaf bgp-prefix-sid-label-idx-index {
                   type int32;
                 }
                 leaf bgp-prefix-sid-attr-status {
                   type string;
                 }
               }
               container bgp-prefix-sid-attr-srgb-tlv {
                 list bgp-prefix-sid-srgb-block {
                   key "bgp-prefix-sid-srgb-block-start-label";
                   leaf bgp-prefix-sid-srgb-block-start-label {
                     type int32;
                   }
                   leaf bgp-prefix-sid-srgb-block-range {
                     type int32;
                   }
                 }
               }
               container bgp-prefix-sid-attr-service-tlv {
                 leaf bgp-prefix-sid-srv6-sid-value {
                   type jt:ipaddr;
                 }
                 leaf bgp-prefix-sid-attr-service-tlv-type {
                   type uint32;
                 }
                 leaf bgp-prefix-sid-attr-tlv-type {
                   type uint32;
                 }
                 leaf bgp-prefix-sid-srv6-sid-bh {
                   type uint32;
                 }
                 leaf bgp-prefix-sid-srv6-sid-bl {
                   type uint32;
                 }
                 leaf bgp-prefix-sid-srv6-sid-nl {
                   type uint32;
                 }
                 leaf bgp-prefix-sid-srv6-sid-fl {
                   type uint32;
                 }
                 leaf bgp-prefix-sid-srv6-sid-al {
                   type uint32;
                 }
                 leaf bgp-prefix-sid-srv6-sid-tl {
                   type uint32;
                 }
                 leaf bgp-prefix-sid-srv6-sid-to {
                   type uint32;
                 }
               }
               container bgp-prefix-sid-attr-unknown-tlvs {
                 list bgp-prefix-sid-attr-unknown-tlv {
                   key "bgp-prefix-sid-unknown-tlv-type";
                   leaf bgp-prefix-sid-unknown-tlv-type {
                     type uint32;
                   }
                   leaf bgp-prefix-sid-unknown-tlv-len {
                     type uint32;
                   }
                 }
               }
             }
             leaf attrset-as {
               type int32;
               description
                 "Originator AS";
             }
             leaf med {
               type int32;
               description
                 "Multiple exit discriminator";
             }
             leaf local-preference {
               type int32;
             }
             leaf as-path {
               type string;
               description
                 "Name of AS path regular expression (BGP only)";
             }
             leaf pmsi {
               type string;
               description
                 "P-multicast service interface";
             }
             leaf cluster-id {
               type string;
             }
             leaf originator {
               type string;
             }
             leaf connector {
               type string;
             }
             container communities {
               leaf-list community {
                 type string;
                 description
                   "Basic community";
               }
               leaf-list extended-community {
                 type string;
                 description
                   "Extended community";
               }
               leaf-list ipv6-extended-community {
                 type string;
                 description
                   "IPv6 extended community";
               }
             }
             list bgp-tunnel-attribute {
               key "tunnel-attribute-type";
               description
                 "Tunne encap attribute information";
               leaf tunnel-attribute-type {
                 type string;
               }
               leaf tunnel-attribute-rpf {
                 type empty;
               }
               leaf tunnel-attribute-color {
                 type uint32;
               }
               leaf tunnel-attribute-destination {
                 type jt:ipaddr;
               }
             }
           }
           container link-state-information {
             container link-state-link {
               leaf link-name {
                 type string;
               }
               leaf color {
                 type int32;
               }
               leaf metric {
                 type int32;
               }
               leaf te-metric {
                 type int32;
                 description
                   "LSP TE metric";
               }
               leaf link-avg-delay {
                 type uint32;
               }
               leaf link-min-delay {
                 type uint32;
               }
               leaf link-max-delay {
                 type uint32;
               }
               leaf link-avg-delay-var {
                 type uint32;
               }
               leaf ldp-support {
                 type string;
               }
               leaf rsvpte-support {
                 type string;
               }
               leaf maximum-bw {
                 type uint64;
               }
               leaf reservable-bw {
                 type uint64;
               }
               container protections {
                 leaf-list protection-type {
                   type string;
                   description
                     "LSP protection desired";
                 }
               }
               container link-srlgs {
                 leaf-list link-srlg {
                   type string;
                 }
               }
               container unreserved-bws {
                 list unreserved-bw {
                   key "unreserved-bw-priority";
                   leaf unreserved-bw-priority {
                     type uint32;
                   }
                   leaf unreserved-bw-value {
                     type string;
                   }
                 }
               }
               container link-state-link-opaque-attrs {
                 leaf link-state-link-opaque-attrs-length {
                   type uint32;
                 }
                 leaf link-state-link-opaque-attrs-bytes {
                   type string;
                 }
               }
               container link-adj-sids {
                 list link-lan-adj-sid {
                   key "link-lan-adj-sid-label";
                   leaf link-lan-adj-sid-af {
                     type string;
                   }
                   leaf link-lan-adj-sid-label {
                     type uint32;
                   }
                   leaf link-lan-adj-sid-flags {
                     type string;
                   }
                   leaf link-lan-adj-sid-weight {
                     type uint32;
                   }
                   leaf link-lan-adj-sid-neighbor {
                     type string;
                   }
                 }
                 list link-p2p-adj-sid {
                   key "link-p2p-adj-sid-label";
                   leaf link-p2p-adj-sid-af {
                     type string;
                   }
                   leaf link-p2p-adj-sid-label {
                     type uint32;
                   }
                   leaf link-p2p-adj-sid-flags {
                     type string;
                   }
                   leaf link-p2p-adj-sid-weight {
                     type uint32;
                   }
                 }
               }
               container link-bgp-peer-sids {
                 list link-bgp-peer-sid {
                   key "link-bgp-peer-sid-label";
                   leaf link-bgp-peer-sid-label {
                     type uint32;
                   }
                   leaf link-bgp-peer-sid-flags {
                     type string;
                   }
                   leaf link-bgp-peer-sid-weight {
                     type uint32;
                   }
                 }
               }
               container link-srv6-end-x-sids {
                 list link-srv6-end-x-sid {
                   key "link-srv6-end-x-sid-val";
                   leaf link-srv6-end-x-sid-type {
                     type string;
                   }
                   leaf link-srv6-end-x-sid-val {
                     type jt:ipv6addr;
                   }
                   leaf link-srv6-end-x-sid-flags {
                     type string;
                   }
                   leaf link-srv6-end-x-sid-weight {
                     type int32;
                   }
                   leaf link-srv6-end-x-sid-algo {
                     type int32;
                   }
                   leaf link-srv6-end-x-sid-func {
                     type string;
                   }
                   leaf link-srv6-end-x-sid-lan-neighbor-id {
                     type string;
                   }
                   container link-srv6-end-x-sid-sstlv {
                     leaf link-srv6-end-x-sid-sstlv-header {
                       type empty;
                     }
                     leaf link-srv6-end-x-sid-sstlv-blen {
                       type uint32;
                     }
                     leaf link-srv6-end-x-sid-sstlv-nlen {
                       type uint32;
                     }
                     leaf link-srv6-end-x-sid-sstlv-flen {
                       type uint32;
                     }
                     leaf link-srv6-end-x-sid-sstlv-alen {
                       type uint32;
                     }
                   }
                 }
               }
               container link-msd-types {
                 list link-msd-entry {
                   key "link-msd-type";
                   leaf link-msd-type {
                     type uint32;
                   }
                   leaf link-msd-value {
                     type uint32;
                   }
                 }
               }
             }
             container link-state-node {
               leaf node-name {
                 type string;
               }
               leaf area-border-router {
                 type string;
               }
               leaf external-router {
                 type string;
               }
               leaf attached {
                 type string;
               }
               leaf overload {
                 type string;
               }
               container node-areas {
                 leaf-list node-area {
                   type string;
                 }
               }
               container node-ipv4-router-ids {
                 leaf-list node-ipv4-router-id {
                   type jt:ipaddr;
                 }
               }
               container node-ipv6-router-ids {
                 leaf-list node-ipv6-router-id {
                   type jt:ipaddr;
                 }
               }
               container node-topologies {
                 list node-topology {
                   key "id";
                   leaf id {
                     type uint32;
                   }
                 }
               }
               container link-state-node-opaque-attrs {
                 leaf link-state-node-opaque-attrs-length {
                   type uint32;
                 }
                 leaf link-state-node-opaque-attrs-bytes {
                   type string;
                 }
               }
               container node-spring-capability {
                 list node-spring-srgb-block {
                   key "node-spring-srgb-block-start node-spring-srgb-block-range";
                   leaf node-spring-srgb-block-start {
                     type uint32;
                   }
                   leaf node-spring-srgb-block-range {
                     type uint32;
                   }
                   leaf node-spring-srgb-block-flags {
                     type string;
                   }
                 }
               }
               container node-msd-types {
                 list node-msd-entry {
                   key "node-msd-type";
                   leaf node-msd-type {
                     type uint32;
                   }
                   leaf node-msd-value {
                     type uint32;
                   }
                 }
               }
               container node-srv6-capability {
                 leaf node-srv6-capability-flag {
                   type uint32;
                 }
               }
               container node-spring-algorithms {
                 list node-spring-algorithm {
                   key "node-spring-algorithm-type";
                   leaf node-spring-algorithm-type {
                     type uint32;
                   }
                 }
               }
               container node-spring-falgo-defs {
                 list node-spring-falgo-def {
                   key "node-spring-falgo-def-algo";
                   leaf node-spring-falgo-def-algo {
                     type uint32;
                   }
                   leaf node-spring-falgo-def-metric-type {
                     type uint32;
                   }
                   leaf node-spring-falgo-def-calculation-type {
                     type uint32;
                   }
                   leaf node-spring-falgo-def-priority {
                     type uint32;
                   }
                   leaf node-spring-falgo-def-flags {
                     type string;
                   }
                   leaf node-spring-falgo-def-include-any {
                     type string;
                   }
                   leaf node-spring-falgo-def-exclude {
                     type string;
                   }
                   leaf node-spring-falgo-def-include-all {
                     type string;
                   }
                 }
               }
             }
             list link-state-te-policy-cp-segment {
             }
             container link-state-te-policy-cp {
               leaf link-state-te-policy-cp-name {
                 type string;
               }
               leaf link-state-te-policy-cp-flags {
                 type string;
               }
               leaf link-state-te-policy-cp-preference {
                 type uint32;
               }
               leaf link-state-te-policy-cp-priority {
                 type uint32;
               }
               leaf link-state-te-policy-cp-constraint-header {
                 type empty;
               }
               leaf link-state-te-policy-cp-constraint-flags {
                 type string;
               }
               leaf link-state-te-policy-cp-mtid {
                 type uint32;
               }
               leaf link-state-te-policy-cp-algo {
                 type uint32;
               }
               leaf link-state-te-policy-cp-exclude-any {
                 type string;
               }
               leaf link-state-te-policy-cp-include-any {
                 type string;
               }
               leaf link-state-te-policy-cp-include-all {
                 type string;
               }
               leaf link-state-te-policy-cp-bandwidth {
                 type uint32;
               }
               leaf link-state-te-policy-cp-bsid-flags {
                 type string;
               }
               leaf link-state-te-policy-cp-mpls-bsid {
                 type uint32;
               }
               leaf link-state-te-policy-cp-mpls-spec-bsid {
                 type uint32;
               }
               leaf link-state-te-policy-cp-segment-list-count {
                 type int32;
               }
               container link-state-te-policy-cp-srv6-bsid-info {
                 leaf link-state-te-policy-cp-srv6-bsid-flags {
                   type string;
                   description
                     "SRv6 BSID flags";
                 }
                 leaf link-state-te-policy-cp-srv6-bsid {
                   type jt:ipv6addr;
                   description
                     "SRv6 BSID";
                 }
                 leaf link-state-te-policy-cp-srv6-spec-bsid {
                   type jt:ipv6addr;
                   description
                     "Specified SRv6 BSID";
                 }
                 leaf link-state-te-policy-cp-srv6-bsid-ep-bhv {
                   type uint32;
                   description
                     "SRv6 BSID endpoint behavior";
                 }
                 leaf link-state-te-policy-cp-srv6-bsid-ep-bhv-flags {
                   type string;
                   description
                     "SRv6 BSID endpoint behavior flags";
                 }
                 leaf link-state-te-policy-cp-srv6-bsid-ep-bhv-algo {
                   type uint32;
                   description
                     "SRv6 BSID endpoint behavior algo";
                 }
                 leaf link-state-te-policy-cp-srv6-bsid-sstlv {
                   type string;
                   description
                     "SRv6 BSID endpoint behavior SSTLV";
                 }
               }
               list link-state-te-policy-cp-segment-list {
                 key "link-state-te-policy-cp-segment-list-index";
                 leaf link-state-te-policy-cp-segment-list-index {
                   type int32;
                 }
                 leaf link-state-te-policy-cp-segment-list-flags {
                   type string;
                 }
                 leaf link-state-te-policy-cp-segment-list-mtid {
                   type uint32;
                 }
                 leaf link-state-te-policy-cp-segment-list-weight {
                   type uint32;
                 }
                 leaf link-state-te-policy-cp-segment-list-algo {
                   type uint32;
                 }
                 leaf link-state-te-policy-cp-segment-list-metric-type {
                   type string;
                 }
                 leaf link-state-te-policy-cp-segment-list-metric-value {
                   type uint32;
                 }
                 leaf link-state-te-policy-cp-segment-count {
                   type int32;
                 }
                 leaf link-state-te-policy-cp-segment-header {
                   type empty;
                 }
                 list link-state-te-policy-cp-segment {
                   leaf link-state-te-policy-cp-mpls-segment-id {
                     type uint32;
                   }
                   leaf link-state-te-policy-cp-srv6-segment-id {
                     type jt:ipv6addr;
                   }
                   leaf link-state-te-policy-cp-segment-descriptor {
                     type jt:ipaddr;
                   }
                   leaf link-state-te-policy-cp-segment-flags {
                     type string;
                   }
                   leaf link-state-te-policy-cp-segment-ep-bhv {
                     type string;
                   }
                   leaf link-state-te-policy-cp-segment-ep-bhv-flags {
                     type uint32;
                   }
                   leaf link-state-te-policy-cp-segment-ep-bhv-algo {
                     type uint32;
                   }
                   container link-state-te-policy-cp-segment-sstlv {
                     leaf link-state-te-policy-cp-segment-sstlv-header {
                       type empty;
                     }
                     leaf link-state-te-policy-cp-segment-sstlv-blen {
                       type uint32;
                     }
                     leaf link-state-te-policy-cp-segment-sstlv-nlen {
                       type uint32;
                     }
                     leaf link-state-te-policy-cp-segment-sstlv-flen {
                       type uint32;
                     }
                     leaf link-state-te-policy-cp-segment-sstlv-alen {
                       type uint32;
                     }
                   }
                 }
               }
             }
             container link-state-prefix {
               leaf link-state-prefix-attr-flags {
                 type string;
               }
               leaf link-state-prefix-metric {
                 type uint32;
               }
               list link-state-prefix-sid {
                 key "link-state-prefix-sid-index link-state-prefix-sid-flags link-state-prefix-sid-algo";
                 leaf link-state-prefix-sid-index {
                   type uint32;
                 }
                 leaf link-state-prefix-sid-flags {
                   type string;
                 }
                 leaf link-state-prefix-sid-algo {
                   type string;
                 }
               }
               container link-state-prefix-srv6-locator {
                 leaf link-state-prefix-srv6-locator-flags {
                   type string;
                 }
                 leaf link-state-prefix-srv6-locator-algo {
                   type string;
                 }
                 leaf link-state-prefix-srv6-locator-metric {
                   type string;
                 }
               }
               list link-state-prefix-fapm {
                 key "link-state-prefix-fapm-algo";
                 leaf link-state-prefix-fapm-algo {
                   type uint32;
                 }
                 leaf link-state-prefix-fapm-metric {
                   type uint32;
                 }
               }
             }
             container link-state-srv6-endsid {
               container link-state-srv6-endsid-info {
                 leaf link-state-srv6-endsid-epb {
                   type string;
                 }
                 leaf link-state-srv6-endsid-flags {
                   type string;
                 }
                 leaf link-state-srv6-endsid-algo {
                   type string;
                 }
                 container link-state-srv6-endsid-sstlv {
                   leaf link-state-srv6-endsid-sstlv-header {
                     type empty;
                   }
                   leaf link-state-srv6-endsid-sstlv-blen {
                     type uint32;
                   }
                   leaf link-state-srv6-endsid-sstlv-nlen {
                     type uint32;
                   }
                   leaf link-state-srv6-endsid-sstlv-flen {
                     type uint32;
                   }
                   leaf link-state-srv6-endsid-sstlv-alen {
                     type uint32;
                   }
                 }
               }
             }
             container link-state-unknown-tlvs {
               list link-state-unknown-tlv {
                 key "unknown-type";
                 leaf unknown-type {
                   type uint32;
                 }
                 leaf unknown-length {
                   type uint32;
                 }
                 leaf unknown-bytes {
                   type string;
                 }
               }
             }
           }
           container aggregate {
             leaf aggregate-truncate {
               type string;
             }
             container aggregate-as-path {
               container bgp-path-attributes {
                 container attr-as-path {
                   description
                     "AS Path Attribute";
                   leaf attr-length {
                     type string;
                   }
                   leaf flags {
                     type string;
                     description
                       "Enabled trace flags";
                   }
                 }
                 container attr-as4-path {
                   description
                     "4-byte AS Path Attribute";
                   leaf attr-length {
                     type string;
                   }
                 }
                 container attr-as-path-effective {
                   description
                     "Effective AS-Path Attribute";
                   leaf attr-length {
                     type string;
                   }
                 }
                 container attr-aggregator {
                   description
                     "Aggregator Attribute";
                   leaf attr-length {
                     type string;
                   }
                 }
                 container attr-aggregator4 {
                   description
                     "Aggregator4 Attribute";
                   leaf attr-length {
                     type string;
                   }
                 }
                 container attr-cluster-list {
                   description
                     "Cluster List Attribute";
                   leaf attr-length {
                     type string;
                   }
                 }
                 container attr-originator-id {
                   description
                     "Originator Attribute";
                   leaf attr-length {
                     type string;
                   }
                 }
               }
               leaf as-path {
                 type string;
                 description
                   "Name of AS path regular expression (BGP only)";
               }
               leaf reference-count {
                 type int32;
                 description
                   "Reference count";
               }
               leaf as-path-length {
                 type int32;
               }
               leaf aggregate-truncate {
                 type string;
               }
             }
             leaf aggregate-flags {
               type string;
               description
                 "Flags on this aggregate route entry";
             }
             leaf aggregate-depth {
               type int32;
               description
                 "Depth of this aggregate";
             }
             leaf aggregate-active {
               type empty;
               description
                 "Present if this aggregate is active";
             }
             leaf aggregate-algo {
               type uint32;
               description
                 "Algorithm number";
             }
             leaf contributing-route-count {
               type int32;
               description
                 "Number of contributing routes in this aggregate";
             }
             leaf aggregate-policy-name {
               type string;
             }
             list aggregated-route {
               key "destination-prefix";
               leaf destination-prefix {
                 type string;
                 description
                   "Destination prefix and mask";
               }
               leaf protocol-name {
                 type string;
               }
             }
           }
           list kern-nhexpand {
             description
               "Next-hop gateway information";
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
           }
           container kern-nh-platform-layer-input {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           container kern-nh-platform-layer-output {
             list kern-nhexpand {
               description
                 "Next-hop gateway information";
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
             }
           }
           list nh {
             description
               "Next-hop gateway information";
             leaf selected-next-hop {
               type empty;
               description
                 "Present if this next hop is selected";
             }
             leaf to {
               type string;
               description
                 "Neighbor address to which to send (next-hop address)";
             }
             leaf nh-indirect-fnh-type {
               type string;
               description
                 "Indirect pointing to a well-known nexthop";
             }
             leaf via {
               type string;
               description
                 "Reachable via a local interface";
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container srv6-info {
               leaf srv6-info-srh-sid-mode {
                 type string;
                 description
                   "Reduced/non-reduced mode for SRH";
               }
               leaf srv6-info-packet-mode {
                 type string;
                 description
                   "Packet mode for SRV6-Tunnel";
               }
               leaf srv6-info-srh-last-sid {
                 type string;
                 description
                   "Remove last sid for ACX";
               }
               leaf srv6-info-dyn-tunnel {
                 type string;
                 description
                   "SRv6 tunnel created dynamically";
               }
               leaf srv6-cos-propagation {
                 type string;
                 description
                   "SRv6 CoS propagation";
               }
               leaf srv6-ttl-propagation {
                 type string;
                 description
                   "SRv6 TTL propagation";
               }
               leaf srv6-source {
                 type jt:ipaddr;
                 description
                   "Source IPv6 address";
               }
               leaf srv6-destination {
                 type jt:ipaddr;
                 description
                   "Destination IPv6 address";
               }
               list srv6-segment-list {
                 key "srv6-segment-list-index";
                 description
                   "SRH Segment list";
                 leaf srv6-segment-list-index {
                   type uint32;
                   description
                     "SRH segment list index";
                 }
                 leaf srv6-segment-list-addr {
                   type jt:ipaddr;
                   description
                     "SRH segment address";
                 }
               }
             }
             leaf nh-string {
               type string;
             }
             leaf nh-table-receive {
               type string;
               description
                 "Destination is a local address";
             }
             leaf nh-table {
               type string;
               description
                 "Indirect pointing to another table";
             }
             leaf nh-table-localized {
               type string;
               description
                 "Indirect pointing to a localized table";
             }
             leaf nh-localized-ifl {
               type string;
               description
                 "Indirect pointing to a localized ifl";
             }
             leaf lsp-name {
               type string;
               description
                 "Tunneled into an RSVP LSP";
             }
             leaf mpls-label {
               type string;
               description
                 "Label of MPLS packet";
             }
             leaf nh-local-interface {
               type string;
               description
                 "Destination is a local interface";
             }
             leaf nh-service {
               type string;
               description
                 "Next-hop service";
             }
             leaf nh-private-comp {
               type string;
               description
                 "Private Composite Next-hop";
             }
             leaf srv6-prefix-sid {
               type jt:ipaddr;
               description
                 "SRv6 prefixe sid value";
             }
             leaf srv6-encap-brief {
               type string;
               description
                 "IPV6 SR-header encapsulation";
             }
             leaf elnh-address {
               type string;
               description
                 "Address of Element Next-hop";
             }
             leaf localized-table {
               type string;
               description
                 "Name of localized table";
             }
             leaf ae-member-interface {
               type string;
               description
                 "AE Member interface";
             }
             leaf weight {
               type int32;
               description
                 "Next-hop weight";
             }
             leaf balance {
               type int32;
               description
                 "Next-hop balance";
             }
             leaf uflags {
               type string;
               description
                 "Next-hop uflags";
             }
             leaf filter {
               type string;
               description
                 "Next-hop firewall filter";
             }
             leaf session {
               type string;
               description
                 "Session ID Associated with this NH";
             }
             leaf statistics-id-group-terse {
               type string;
               description
                 "Statistics ID Group Associated with this NH";
             }
             leaf app-specific-opaque {
               type string;
               description
                 "Application specific opaque data dump";
             }
             leaf gw-opaque {
               type string;
               description
                 "Nexthops gateway opaque data handle";
             }
             leaf statistics-pkts-count {
               type int32;
               description
                 "Statistics packet count Associated with this NH";
             }
             leaf statistics-bytes-count {
               type int32;
               description
                 "Statistics bytes count Associated with this NH";
             }
             leaf ext-int-type {
               type string;
               description
                 "Next-hop type of equal-external-internal multipath";
             }
             leaf fc {
               type int32;
               description
                 "Forwarding-class";
             }
             leaf label-ttl-action {
               type string;
               description
                 "TTL action associated with labels";
             }
             leaf load-balance-label {
               type string;
               description
                 "Load balance action associated with labels";
             }
             leaf label-element {
               type string;
               description
                 "Pointer to the tag label element";
             }
             leaf label-element-parent {
               type string;
               description
                 "Pointer to the tag label element parent";
             }
             leaf label-element-refcount {
               type string;
               description
                 "Number of references to the tag label element";
             }
             leaf label-element-childcount {
               type string;
               description
                 "Number of child references to the tag label element";
             }
             leaf label-element-lspid {
               type string;
               description
                 "LSP ID of the tag label element";
             }
             leaf nh-service-pkt-dist {
               type string;
               description
                 "Multi services packet distribution type";
             }
             leaf nh-service-app-data {
               type string;
               description
                 "Multi services application specific data";
             }
             leaf nh-index {
               type uint32;
               description
                 "Next-hop index";
             }
             leaf nh-address {
               type string;
               description
                 "Address of next hop";
             }
             leaf nh-reference-count {
               type int32;
               description
                 "Number of references to this next hop";
             }
             leaf tunnel-composite-attr-type {
               type string;
               description
                 "Tunnel-Type for tunnel-composite-nexthop";
             }
             leaf tunnel-composite-attr-subtype {
               type string;
               description
                 "Tunnel-Subtype for tunnel-composite-nexthop";
             }
             leaf tunnel-composite-attr-reference-count {
               type int32;
               description
                 "Tunnel-reference-count for tunnel-composite-nexthop";
             }
             leaf tunnel-composite-attr-nh-id {
               type int32;
               description
                 "Tunnel-NextHop-Id for tunnel-composite-nexthop";
             }
             leaf tunnel-composite-attr-dest {
               type jt:ipaddr;
               description
                 "Tunnel-Destination for tunnel-composite-nexthop";
             }
             leaf tunnel-composite-attr-src {
               type jt:ipaddr;
               description
                 "Tunnel-Source for tunnel-composite-nexthop";
             }
             leaf tunnel-composite-attr-tunnel-endpoint {
               type jt:ipaddr;
               description
                 "Tunnel-Endpoint for tunnel-composite-nexthop";
             }
             leaf tunnel-composite-anchor-pfe {
               type string;
               description
                 "Anchor PFE name, if tunnel nexthop is localized";
             }
             leaf tunnel-composite-encap-rtb-id {
               type int32;
               description
                 "Tunnel encap routing table index";
             }
             leaf tunnel-composite-decap-rtb-id {
               type int32;
               description
                 "Tunnel decap routing table index";
             }
             leaf tunnel-composite-attr-ttl {
               type int32;
               description
                 "Tunnel-TTL for tunnel-composite-nexthop";
             }
             leaf tunnel-composite-attr-udp-port {
               type int32;
               description
                 "Tunnel-UDP-Destination port for tunnel-composite-nexthop";
             }
             leaf tunnel-composite-attr-fc-id {
               type int32;
               description
                 "Tunnel-Forwarding-Class-ID for tunnel-composite-nexthop";
             }
             leaf tunnel-composite-attr-tid {
               type int32;
               description
                 "Tunnel-Id for tunnel-composite-nexthop";
             }
             leaf tunnel-composite-attr-label {
               type string;
               description
                 "Tunnel-VPN-Label for tunnel-composite-nexthop";
             }
             leaf tunnel-composite-attr-label-ttl {
               type string;
               description
                 "Tunnel-VPN-Label-TTL for tunnel-composite-nexthop";
             }
             leaf tunnel-composite-attr-gre-key {
               type int32;
               description
                 "GRE key for tunnel-composite-nexthop";
             }
             leaf-list tunnel-composite-attr-segment-addr {
               type jt:ipaddr;
               description
                 "IPv6 segment-address";
             }
             leaf-list tunnel-composite-attr-sid {
               type int32;
               description
                 "IPv6 segment-sid";
             }
             leaf tunnel-composite-attr-vni {
               type int32;
               description
                 "Tunnel-VNI for tunnel-composite-nexthop in VxLAN";
             }
             leaf tunnel-composite-attr-dest-mac {
               type string;
               description
                 "Tunnel-Dest-Mac for tunnel-composite-nexthop in VxLAN";
             }
             leaf translate-composite-attr-type {
               type string;
               description
                 "Translation type for translate-composite-nexthop";
             }
             leaf translate-composite-attr-flags {
               type string;
               description
                 "Flags for translate-composite-nexthop";
             }
             leaf translate-composite-attr-reference-count {
               type int32;
               description
                 "Reference count for translate-composite-nexthop";
             }
             leaf translate-composite-attr-nh-id {
               type int32;
               description
                 "NextHop id for translate-composite-nexthop";
             }
             leaf translate-composite-attr-dest {
               type jt:ipaddr;
               description
                 "Translation destination for translate-composite-nexthop";
             }
             leaf translate-composite-attr-dest-plen {
               type int32;
               description
                 "Translation destination prefix length for 
                 translate-composite-nexthop";
             }
             leaf translate-composite-attr-src {
               type jt:ipaddr;
               description
                 "Translation source for translate-composite-nexthop";
             }
             leaf translate-composite-attr-src-plen {
               type int32;
               description
                 "Translation source prefix length for 
                 translate-composite-nexthop";
             }
             leaf translate-composite-attr-dest-alg-type {
               type string;
               description
                 "Destination algorithm type for translate-composite-nexthop";
             }
             leaf translate-composite-attr-src-alg-type {
               type string;
               description
                 "Source algorithm type for translate-composite-nexthop";
             }
             leaf translate-composite-attr-dest-vrf-id {
               type int32;
               description
                 "Destination vrf id for translate-composite-nexthop";
             }
             leaf translate-composite-attr-src-vrf-id {
               type int32;
               description
                 "Source vrf id for translate-composite-nexthop";
             }
             leaf translate-composite-attr-hoplimit {
               type int32;
               description
                 "Hoplimit for translate-composite-nexthop";
             }
             leaf translate-composite-attr-traffic-class {
               type int32;
               description
                 "Traffic class for translate-composite-nexthop";
             }
             leaf translate-composite-attr-ttl {
               type int32;
               description
                 "Ttl for translate-composite-nexthop";
             }
             leaf translate-composite-attr-tos {
               type int32;
               description
                 "Tos for translate-composite-nexthop";
             }
           }
           container protocol-nh {
             description
               "Protocol next hop";
             list nh {
               description
                 "Next-hop gateway information";
               container vxlan-header-rewrite {
                 description
                   "VXLAN tunnel rewrite information";
                 leaf vxlan-header-rewrite-mtu {
                   type int32;
                   description
                     "VXLAN tunnel MTU";
                 }
                 leaf vxlan-header-rewrite-flags {
                   type int32;
                   description
                     "VXLAN tunnel flags";
                 }
                 leaf vxlan-header-rewrite-encap-rtb-id {
                   type int32;
                   description
                     "VXLAN tunnel encapsulation table ID";
                 }
                 leaf vxlan-header-rewrite-decap-rtb-id {
                   type int32;
                   description
                     "VXLAN tunnel decapsulation table ID";
                 }
                 leaf vxlan-header-rewrite-encap-vnid {
                   type int32;
                   description
                     "VXLAN tunnel encapsulation VNI";
                 }
                 leaf vxlan-header-rewrite-decap-vnid {
                   type int32;
                   description
                     "VXLAN tunnel decapsulation VNI";
                 }
                 leaf vxlan-header-rewrite-svtep {
                   type jt:ipaddr;
                   description
                     "Source VTEP address";
                 }
                 leaf vxlan-header-rewrite-dvtep {
                   type jt:ipaddr;
                   description
                     "Destination VTEP address";
                 }
                 leaf vxlan-header-rewrite-smac {
                   type string;
                   description
                     "Source MAC address";
                 }
                 leaf vxlan-header-rewrite-dmac {
                   type string;
                   description
                     "Destination MAC address";
                 }
               }
               container srv6-info {
                 leaf srv6-info-srh-sid-mode {
                   type string;
                   description
                     "Reduced/non-reduced mode for SRH";
                 }
                 leaf srv6-info-packet-mode {
                   type string;
                   description
                     "Packet mode for SRV6-Tunnel";
                 }
                 leaf srv6-info-srh-last-sid {
                   type string;
                   description
                     "Remove last sid for ACX";
                 }
                 leaf srv6-info-dyn-tunnel {
                   type string;
                   description
                     "SRv6 tunnel created dynamically";
                 }
                 leaf srv6-cos-propagation {
                   type string;
                   description
                     "SRv6 CoS propagation";
                 }
                 leaf srv6-ttl-propagation {
                   type string;
                   description
                     "SRv6 TTL propagation";
                 }
                 leaf srv6-source {
                   type jt:ipaddr;
                   description
                     "Source IPv6 address";
                 }
                 leaf srv6-destination {
                   type jt:ipaddr;
                   description
                     "Destination IPv6 address";
                 }
                 list srv6-segment-list {
                   key "srv6-segment-list-index";
                   description
                     "SRH Segment list";
                   leaf srv6-segment-list-index {
                     type uint32;
                     description
                       "SRH segment list index";
                   }
                   leaf srv6-segment-list-addr {
                     type jt:ipaddr;
                     description
                       "SRH segment address";
                   }
                 }
               }
               leaf nh-string {
                 type string;
               }
               leaf elnh-address {
                 type string;
                 description
                   "Address of Element Next-hop";
               }
               leaf to {
                 type string;
                 description
                   "Neighbor address to which to send (next-hop address)";
               }
               leaf via {
                 type string;
                 description
                   "Reachable via a local interface";
               }
               leaf localized-table {
                 type string;
                 description
                   "Name of localized table";
               }
               leaf ae-member-interface {
                 type string;
                 description
                   "AE Member interface";
               }
               leaf weight {
                 type int32;
                 description
                   "Next-hop weight";
               }
               leaf balance {
                 type int32;
                 description
                   "Next-hop balance";
               }
               leaf uflags {
                 type string;
                 description
                   "Next-hop uflags";
               }
               leaf filter {
                 type string;
                 description
                   "Next-hop firewall filter";
               }
               leaf selected-next-hop {
                 type empty;
                 description
                   "Present if this next hop is selected";
               }
               leaf session {
                 type string;
                 description
                   "Session ID Associated with this NH";
               }
               leaf statistics-id-group-terse {
                 type string;
                 description
                   "Statistics ID Group Associated with this NH";
               }
               leaf app-specific-opaque {
                 type string;
                 description
                   "Application specific opaque data dump";
               }
               leaf gw-opaque {
                 type string;
                 description
                   "Nexthops gateway opaque data handle";
               }
               leaf statistics-pkts-count {
                 type int32;
                 description
                   "Statistics packet count Associated with this NH";
               }
               leaf statistics-bytes-count {
                 type int32;
                 description
                   "Statistics bytes count Associated with this NH";
               }
               leaf ext-int-type {
                 type string;
                 description
                   "Next-hop type of equal-external-internal multipath";
               }
               leaf fc {
                 type int32;
                 description
                   "Forwarding-class";
               }
               leaf lsp-name {
                 type string;
                 description
                   "Tunneled into an RSVP LSP";
               }
               leaf mpls-label {
                 type string;
                 description
                   "Label of MPLS packet";
               }
               leaf label-ttl-action {
                 type string;
                 description
                   "TTL action associated with labels";
               }
               leaf load-balance-label {
                 type string;
                 description
                   "Load balance action associated with labels";
               }
               leaf label-element {
                 type string;
                 description
                   "Pointer to the tag label element";
               }
               leaf label-element-parent {
                 type string;
                 description
                   "Pointer to the tag label element parent";
               }
               leaf label-element-refcount {
                 type string;
                 description
                   "Number of references to the tag label element";
               }
               leaf label-element-childcount {
                 type string;
                 description
                   "Number of child references to the tag label element";
               }
               leaf label-element-lspid {
                 type string;
                 description
                   "LSP ID of the tag label element";
               }
               leaf nh-table-receive {
                 type string;
                 description
                   "Destination is a local address";
               }
               leaf nh-table {
                 type string;
                 description
                   "Indirect pointing to another table";
               }
               leaf nh-localized-ifl {
                 type string;
                 description
                   "Indirect pointing to a localized ifl";
               }
               leaf nh-local-interface {
                 type string;
                 description
                   "Destination is a local interface";
               }
               leaf nh-service {
                 type string;
                 description
                   "Next-hop service";
               }
               leaf nh-service-pkt-dist {
                 type string;
                 description
                   "Multi services packet distribution type";
               }
               leaf nh-service-app-data {
                 type string;
                 description
                   "Multi services application specific data";
               }
               leaf nh-private-comp {
                 type string;
                 description
                   "Private Composite Next-hop";
               }
               leaf nh-index {
                 type uint32;
                 description
                   "Next-hop index";
               }
               leaf nh-address {
                 type string;
                 description
                   "Address of next hop";
               }
               leaf nh-reference-count {
                 type int32;
                 description
                   "Number of references to this next hop";
               }
               leaf tunnel-composite-attr-type {
                 type string;
                 description
                   "Tunnel-Type for tunnel-composite-nexthop";
               }
               leaf tunnel-composite-attr-subtype {
                 type string;
                 description
                   "Tunnel-Subtype for tunnel-composite-nexthop";
               }
               leaf tunnel-composite-attr-reference-count {
                 type int32;
                 description
                   "Tunnel-reference-count for tunnel-composite-nexthop";
               }
               leaf tunnel-composite-attr-nh-id {
                 type int32;
                 description
                   "Tunnel-NextHop-Id for tunnel-composite-nexthop";
               }
               leaf tunnel-composite-attr-dest {
                 type jt:ipaddr;
                 description
                   "Tunnel-Destination for tunnel-composite-nexthop";
               }
               leaf tunnel-composite-attr-src {
                 type jt:ipaddr;
                 description
                   "Tunnel-Source for tunnel-composite-nexthop";
               }
               leaf tunnel-composite-attr-tunnel-endpoint {
                 type jt:ipaddr;
                 description
                   "Tunnel-Endpoint for tunnel-composite-nexthop";
               }
               leaf tunnel-composite-anchor-pfe {
                 type string;
                 description
                   "Anchor PFE name, if tunnel nexthop is localized";
               }
               leaf tunnel-composite-encap-rtb-id {
                 type int32;
                 description
                   "Tunnel encap routing table index";
               }
               leaf tunnel-composite-decap-rtb-id {
                 type int32;
                 description
                   "Tunnel decap routing table index";
               }
               leaf tunnel-composite-attr-ttl {
                 type int32;
                 description
                   "Tunnel-TTL for tunnel-composite-nexthop";
               }
               leaf tunnel-composite-attr-udp-port {
                 type int32;
                 description
                   "Tunnel-UDP-Destination port for tunnel-composite-nexthop";
               }
               leaf tunnel-composite-attr-fc-id {
                 type int32;
                 description
                   "Tunnel-Forwarding-Class-ID for tunnel-composite-nexthop";
               }
               leaf tunnel-composite-attr-tid {
                 type int32;
                 description
                   "Tunnel-Id for tunnel-composite-nexthop";
               }
               leaf tunnel-composite-attr-label {
                 type string;
                 description
                   "Tunnel-VPN-Label for tunnel-composite-nexthop";
               }
               leaf tunnel-composite-attr-label-ttl {
                 type string;
                 description
                   "Tunnel-VPN-Label-TTL for tunnel-composite-nexthop";
               }
               leaf tunnel-composite-attr-gre-key {
                 type int32;
                 description
                   "GRE key for tunnel-composite-nexthop";
               }
               leaf-list tunnel-composite-attr-segment-addr {
                 type jt:ipaddr;
                 description
                   "IPv6 segment-address";
               }
               leaf-list tunnel-composite-attr-sid {
                 type int32;
                 description
                   "IPv6 segment-sid";
               }
               leaf tunnel-composite-attr-vni {
                 type int32;
                 description
                   "Tunnel-VNI for tunnel-composite-nexthop in VxLAN";
               }
               leaf tunnel-composite-attr-dest-mac {
                 type string;
                 description
                   "Tunnel-Dest-Mac for tunnel-composite-nexthop in VxLAN";
               }
               leaf translate-composite-attr-type {
                 type string;
                 description
                   "Translation type for translate-composite-nexthop";
               }
               leaf translate-composite-attr-flags {
                 type string;
                 description
                   "Flags for translate-composite-nexthop";
               }
               leaf translate-composite-attr-reference-count {
                 type int32;
                 description
                   "Reference count for translate-composite-nexthop";
               }
               leaf translate-composite-attr-nh-id {
                 type int32;
                 description
                   "NextHop id for translate-composite-nexthop";
               }
               leaf translate-composite-attr-dest {
                 type jt:ipaddr;
                 description
                   "Translation destination for translate-composite-nexthop";
               }
               leaf translate-composite-attr-dest-plen {
                 type int32;
                 description
                   "Translation destination prefix length for 
                   translate-composite-nexthop";
               }
               leaf translate-composite-attr-src {
                 type jt:ipaddr;
                 description
                   "Translation source for translate-composite-nexthop";
               }
               leaf translate-composite-attr-src-plen {
                 type int32;
                 description
                   "Translation source prefix length for 
                   translate-composite-nexthop";
               }
               leaf translate-composite-attr-dest-alg-type {
                 type string;
                 description
                   "Destination algorithm type for 
                   translate-composite-nexthop";
               }
               leaf translate-composite-attr-src-alg-type {
                 type string;
                 description
                   "Source algorithm type for translate-composite-nexthop";
               }
               leaf translate-composite-attr-dest-vrf-id {
                 type int32;
                 description
                   "Destination vrf id for translate-composite-nexthop";
               }
               leaf translate-composite-attr-src-vrf-id {
                 type int32;
                 description
                   "Source vrf id for translate-composite-nexthop";
               }
               leaf translate-composite-attr-hoplimit {
                 type int32;
                 description
                   "Hoplimit for translate-composite-nexthop";
               }
               leaf translate-composite-attr-traffic-class {
                 type int32;
                 description
                   "Traffic class for translate-composite-nexthop";
               }
               leaf translate-composite-attr-ttl {
                 type int32;
                 description
                   "Ttl for translate-composite-nexthop";
               }
               leaf translate-composite-attr-tos {
                 type int32;
                 description
                   "Tos for translate-composite-nexthop";
               }
             }
             leaf to {
               type string;
               description
                 "Neighbor address to which to send (next-hop address)";
             }
             leaf metric {
               type int32;
             }
             leaf aigp {
               type string;
               description
                 "AIGP";
             }
             leaf balance {
               type int32;
               description
                 "Next-hop balance";
             }
             leaf flags {
               type string;
               description
                 "Enabled trace flags";
             }
             leaf res-state {
               type string;
               description
                 "Status of route resolution";
             }
             leaf res-tsp-idx {
               type int32;
               description
                 "TSP index of the path";
             }
             leaf-list res-path-aux {
               type string;
             }
             leaf-list res-path-aux-type {
               type string;
             }
             leaf-list res-path-aux-flags {
               type string;
             }
             leaf-list res-path-aux-rs-name {
               type string;
             }
             leaf-list res-path-aux-rs-ribs {
               type string;
             }
             leaf-list res-path-inode-flags {
               type string;
             }
             leaf-list res-path-flags {
               type string;
             }
             leaf-list res-path-fnh-link {
               type string;
             }
             leaf-list res-path-inh-link {
               type string;
             }
             leaf mpls-label {
               type string;
               description
                 "Label of MPLS packet";
             }
             leaf label-ttl-action {
               type string;
               description
                 "TTL action associated with labels";
             }
             leaf load-balance-label {
               type string;
               description
                 "Load balance action associated with labels";
             }
             leaf-list composite-nh {
               type string;
             }
             leaf-list pnh-statistics-id-group {
               type string;
               description
                 "Statistics ID Group Associated with this protocol NH";
             }
             leaf-list vpnlabel-nh {
               type string;
             }
             leaf-list indirect-nh {
               type string;
             }
             leaf ext-int-type {
               type string;
               description
                 "Next-hop type of equal-external-internal multipath";
             }
             leaf gw-opaque {
               type string;
               description
                 "Nexthops gateway opaque data handle";
             }
             leaf-list forwarding-nh-count {
               type int32;
               description
                 "Number of indirect path forwarding next hops";
             }
             leaf-list merged-forwarding-nh-count {
               type int32;
               description
                 "Number of indirect path forwarding next hops (Merged)";
             }
             leaf nh-type {
               type string;
               description
                 "Special next hop: Reject, Blackhole, Receive, Multicast, 
                 Local, or Unused";
             }
             leaf-list node-prefix {
               type string;
             }
             leaf-list node-prefix-length {
               type int32;
             }
             leaf-list originating-rib {
               type string;
               description
                 "Routing table from which this route was learned";
             }
             leaf-list node-metric {
               type int32;
             }
             leaf-list node-path-count {
               type int32;
               description
                 "Number of paths for this node";
             }
             leaf node-flags {
               type int32;
               description
                 "Flags for this node";
             }
             leaf-list node-address {
               type string;
             }
             leaf-list node-forwarding-nh-count {
               type int32;
             }
             leaf-list nh-subtype {
               type string;
               description
                 "Specified nexthop subtype";
             }
             leaf indirect-nh-count {
               type int32;
               description
                 "Number of indirect next hops";
             }
             leaf composite-nh-count {
               type int32;
               description
                 "Number of composite next hops";
             }
             container eth-header-rewrite {
               description
                 "Ethernet header rewrite information";
               leaf eth-header-rewrite-smac {
                 type string;
                 description
                   "Source MAC address";
               }
               leaf eth-header-rewrite-dmac {
                 type string;
                 description
                   "Destination MAC address";
               }
               leaf eth-header-rewrite-tpid {
                 type int32;
                 description
                   "Ethernet header TPID";
               }
               leaf eth-header-rewrite-tci {
                 type int32;
                 description
                   "Ethernet header TCI";
               }
               leaf eth-header-rewrite-vlan-id {
                 type int32;
                 description
                   "Ethernet header VLAN ID";
               }
               leaf eth-header-rewrite-ethertype {
                 type int32;
                 description
                   "Ethernet header ethertype";
               }
             }
             container vxlan-header-rewrite {
               description
                 "VXLAN tunnel rewrite information";
               leaf vxlan-header-rewrite-mtu {
                 type int32;
                 description
                   "VXLAN tunnel MTU";
               }
               leaf vxlan-header-rewrite-flags {
                 type int32;
                 description
                   "VXLAN tunnel flags";
               }
               leaf vxlan-header-rewrite-encap-rtb-id {
                 type int32;
                 description
                   "VXLAN tunnel encapsulation table ID";
               }
               leaf vxlan-header-rewrite-decap-rtb-id {
                 type int32;
                 description
                   "VXLAN tunnel decapsulation table ID";
               }
               leaf vxlan-header-rewrite-encap-vnid {
                 type int32;
                 description
                   "VXLAN tunnel encapsulation VNI";
               }
               leaf vxlan-header-rewrite-decap-vnid {
                 type int32;
                 description
                   "VXLAN tunnel decapsulation VNI";
               }
               leaf vxlan-header-rewrite-svtep {
                 type jt:ipaddr;
                 description
                   "Source VTEP address";
               }
               leaf vxlan-header-rewrite-dvtep {
                 type jt:ipaddr;
                 description
                   "Destination VTEP address";
               }
               leaf vxlan-header-rewrite-smac {
                 type string;
                 description
                   "Source MAC address";
               }
               leaf vxlan-header-rewrite-dmac {
                 type string;
                 description
                   "Destination MAC address";
               }
             }
             container fully-resolved-tunnel {
               description
                 "GRE or UDP tunnel rewrite information";
               leaf fully-resolved-tunnel-type {
                 type string;
                 description
                   "Tunnel type";
               }
               leaf fully-resolved-tunnel-dest {
                 type jt:ipaddr;
                 description
                   "Tunnel Destination";
               }
               leaf fully-resolved-tunnel-src {
                 type jt:ipaddr;
                 description
                   "Tunnel Source";
               }
               leaf fully-resolved-tunnel-ep-addr {
                 type jt:ipaddr;
                 description
                   "Tunnel endpoint address";
               }
               leaf fully-resolved-tunnel-encap-rtb-id {
                 type int32;
                 description
                   "Tunnel encap routing table id";
               }
               leaf fully-resolved-tunnel-decap-rtb-id {
                 type int32;
                 description
                   "Tunnel decap routing table id";
               }
             }
           }
           container srte-policy-state {
             leaf sr-source {
               type string;
             }
             leaf sr-origin {
               type string;
             }
             leaf sr-preference {
               type uint32;
             }
             leaf sr-preference-override {
               type uint32;
             }
             leaf sr-route-distinguisher {
               type uint32;
             }
           }
           container srte-policy-information {
             container srte-policy {
               leaf srte-path-preference {
                 type uint32;
               }
               leaf srte-binding-sid {
                 type string;
               }
               leaf srte-adv-policy-name {
                 type string;
               }
               leaf srte-priority {
                 type uint32;
               }
               leaf srte-enlp {
                 type uint32;
               }
               leaf srte-tlv-recv-flags {
                 type string;
               }
               leaf srte-binding-sid-label-encoding {
                 type string;
               }
               list srte-segment-list {
                 leaf srte-segment-list-weight {
                   type uint32;
                 }
                 list srte-segment {
                   leaf srte-segment-label {
                     type uint32;
                   }
                   leaf srte-segment-label-ttl {
                     type string;
                     description
                       "SR Policy segment label ttl";
                   }
                   leaf srte-segment-type {
                     type string;
                     description
                       "SR Policy segment type";
                   }
                   leaf srte-segment-label-class {
                     type uint32;
                     description
                       "SR Policy segment label traffic-class";
                   }
                 }
               }
             }
           }
           container bgp-prefix-sid-attr {
             description
               "BGP Prefix SID Attribute";
             container bgp-prefix-sid-attr-label-idx-tlv {
               leaf bgp-prefix-sid-label-idx-index {
                 type int32;
               }
               leaf bgp-prefix-sid-attr-status {
                 type string;
               }
             }
             container bgp-prefix-sid-attr-srgb-tlv {
               list bgp-prefix-sid-srgb-block {
                 key "bgp-prefix-sid-srgb-block-start-label";
                 leaf bgp-prefix-sid-srgb-block-start-label {
                   type int32;
                 }
                 leaf bgp-prefix-sid-srgb-block-range {
                   type int32;
                 }
               }
             }
             container bgp-prefix-sid-attr-service-tlv {
               leaf bgp-prefix-sid-srv6-sid-value {
                 type jt:ipaddr;
               }
               leaf bgp-prefix-sid-attr-service-tlv-type {
                 type uint32;
               }
               leaf bgp-prefix-sid-attr-tlv-type {
                 type uint32;
               }
               leaf bgp-prefix-sid-srv6-sid-bh {
                 type uint32;
               }
               leaf bgp-prefix-sid-srv6-sid-bl {
                 type uint32;
               }
               leaf bgp-prefix-sid-srv6-sid-nl {
                 type uint32;
               }
               leaf bgp-prefix-sid-srv6-sid-fl {
                 type uint32;
               }
               leaf bgp-prefix-sid-srv6-sid-al {
                 type uint32;
               }
               leaf bgp-prefix-sid-srv6-sid-tl {
                 type uint32;
               }
               leaf bgp-prefix-sid-srv6-sid-to {
                 type uint32;
               }
             }
             container bgp-prefix-sid-attr-unknown-tlvs {
               list bgp-prefix-sid-attr-unknown-tlv {
                 key "bgp-prefix-sid-unknown-tlv-type";
                 leaf bgp-prefix-sid-unknown-tlv-type {
                   type uint32;
                 }
                 leaf bgp-prefix-sid-unknown-tlv-len {
                   type uint32;
                 }
               }
             }
           }
           container srte-policy-telemetry-statistics-state {
             leaf srte-policy-telemetry-statistics-state.heading {
               type string;
             }
             container srte-policy-telemetry-statistics-config {
               leaf ingress {
                 type empty;
                 description
                   "Flag indicating ingress statistics is configured";
               }
               leaf transit {
                 type empty;
                 description
                   "Flag indicating transit statistics is configured";
               }
             }
             list srte-policy-telemetry-statistics-sensor-information {
               leaf sensor-type {
                 type string;
               }
               leaf sensor-status {
                 type string;
               }
               leaf sensor-id {
                 type int32;
                 description
                   "Unique identifier for the sensor";
               }
             }
           }
           list flex-tunnel-profile {
             description
               "Flex V4/V6 route tunnel attribute information";
             container flex-tunnel-profile-info {
               description
                 "The tunnel profile information";
               leaf flex-tunnel-profile-num {
                 type int32;
                 description
                   "The tunnel profile number";
               }
               leaf flex-tunnel-profile-action {
                 type string;
                 description
                   "The action that this profile will be used for";
               }
               leaf flex-tunnel-profile-vni {
                 type int32;
                 description
                   "VXLAN Network Identifier (VNI)";
               }
               leaf flex-tunnel-profile-src-pfx {
                 type string;
                 description
                   "Source address and prefix length";
               }
               leaf flex-tunnel-profile-src-udp-port-range {
                 type string;
                 description
                   "Outer source UDP port range";
               }
               leaf flex-tunnel-profile-src-mac {
                 type string;
                 description
                   "Source MAC address, a 48-bit MAC value";
               }
               leaf flex-tunnel-profile-dest-pfx {
                 type string;
                 description
                   "Destination address";
               }
               leaf flex-tunnel-profile-dest-udp-port {
                 type int32;
                 description
                   "Outer destination UDP port";
               }
               leaf flex-tunnel-profile-dest-mac {
                 type string;
                 description
                   "Destination MAC address, a 48-bit MAC value";
               }
               leaf flex-tunnel-profile-flex-vxlan-flags {
                 type int32;
                 description
                   "Flex VxLAN flags";
               }
               leaf flex-tunnel-profile-reserved-24-bit-field {
                 type int32;
                 description
                   "VXLAN 24-bit reserved field as specified in RFC7348";
               }
               leaf flex-tunnel-profile-reserved-8-bit-field {
                 type int32;
                 description
                   "VXLAN 8-bit reserved field as specified in RFC7348";
               }
               container flex-tunnel-profile-stats {
                 description
                   "Statistics associated with tunnel";
                 leaf flex-tunnel-stats-pkts-count {
                   type int32;
                   description
                     "Packet count";
                 }
                 leaf flex-tunnel-stats-pps {
                   type int32;
                   description
                     "Packets per second";
                 }
                 leaf flex-tunnel-stats-bytes-count {
                   type int32;
                   description
                     "Byte count";
                 }
                 leaf flex-tunnel-stats-bps {
                   type int32;
                   description
                     "Bytes per second";
                 }
               }
             }
             leaf flex-tunnel-profile-string {
               type string;
               description
                 "The tunnel profile string";
             }
           }
           leaf preference2 {
             type int32;
           }
           leaf age {
             type string;
           }
           leaf med {
             type int32;
             description
               "Multiple exit discriminator";
           }
           leaf local-preference {
             type int32;
           }
           leaf rt-tag {
             type int32;
           }
           leaf rt-tag2 {
             type int32;
           }
           leaf learned-from {
             type jt:ipaddr;
             description
               "Peer address from which this route was learned";
           }
           leaf peer-as {
             type int32;
             description
               "Peer AS number";
           }
           leaf evpn-remote-mes {
             type jt:ipaddr;
             description
               "Remote PE";
           }
           leaf evpn-routing-instance-name {
             type string;
             description
               "Routing Instance";
           }
           leaf evpn-tag-rt-type {
             type string;
             description
               "Route Type";
           }
           leaf evpn-vlan-id {
             type int32;
             description
               "VLAN-ID";
           }
           leaf evpn-vpws-service-id {
             type int32;
             description
               "VPWS Service-Id";
           }
           leaf rt-evpn-esi {
             type string;
             description
               "ESI";
           }
           leaf evpn-isid {
             type int32;
             description
               "ISID";
           }
           leaf rt-evpn-bmac {
             type string;
             description
               "BMAC";
           }
           leaf bgp-rtarget-type {
             type string;
             description
               "BGP RT-Constrain route type";
           }
           leaf bgp-rtarget-generation {
             type uint32;
             description
               "BGP RT-Constrain generation";
           }
           leaf bgp-rtarget-for {
             type string;
             description
               "BGP RT-Constrain member";
           }
           leaf nh-index {
             type uint32;
             description
               "Next-hop index";
           }
           leaf transport-class {
             type string;
             description
               "Transport class name";
           }
           leaf nh-address {
             type string;
             description
               "Address of next hop";
           }
           leaf nh-reference-count {
             type int32;
             description
               "Number of references to this next hop";
           }
           leaf ext-int-intf-index {
             type int32;
             description
               "Interface index of equal-external-internal multipath";
           }
           leaf nh-session-id {
             type uint32;
             description
               "Nexthop session id";
           }
           leaf nh-key-opaque {
             type string;
             description
               "Nexthop key opaque handle";
           }
           leaf nh-non-key-opaque {
             type string;
             description
               "Nexthop non-key opaque handle";
           }
           leaf nh-key-opaque-dump {
             type string;
             description
               "Nexthop key opaque app dump";
           }
           leaf nh-non-key-opaque-dump {
             type string;
             description
               "Nexthop non-key opaque app dump";
           }
           leaf nh-flood-overflow {
             type empty;
             description
               "Flood nexthop exceeds maximum branches";
           }
           leaf nh-kernel-id {
             type int32;
             description
               "Table Id for this next hop";
           }
           leaf client-data {
             type string;
             description
               "Route server client details";
           }
           leaf route-distinguisher {
             type string;
             description
               "Name of the route-distinguisher";
           }
           leaf reason-for-invalid {
             type string;
           }
           leaf thread-name {
             type string;
           }
           leaf pmsi {
             type string;
             description
               "P-multicast service interface";
           }
           leaf connector {
             type string;
           }
           leaf color {
             type int32;
           }
           leaf color2 {
             type int32;
           }
           leaf prefix-segment-index {
             type int32;
           }
           leaf rt-isis-level {
             type int32;
           }
           leaf rt-isis-downbit {
             type int32;
           }
           leaf rt-entry-state {
             type string;
             description
               "State of this route entry";
           }
           leaf rt-fib-install-priority {
             type string;
             description
               "Route FIB installation priority";
           }
           leaf rt-ack-state {
             type string;
             description
               "Route acknowledgement state";
           }
           leaf rt-ack-ll-flag {
             type string;
             description
               "Status of route ACK flags";
           }
           leaf rt-ack-req-ts {
             type string;
             description
               "Time when ack request is sent";
           }
           leaf rt-ack-res-time {
             type uint32;
             description
               "Ack route response time";
           }
           leaf rt-ack-re-flash-time {
             type string;
             description
               "Time when ack is re flashed to protocols";
           }
           leaf rt-ack-re-flash-status {
             type string;
             description
               "Status of ACK re-flash to protocols";
           }
           leaf rt-ack-guid {
             type uint64;
             description
               "Ack route global identifier";
           }
           leaf rt-ack-olc {
             type uint64;
             description
               "Ack route global version";
           }
           leaf rt-ack-local-ver {
             type uint32;
             description
               "Ack route global version";
           }
           leaf rt-ack-and-err-flag {
             type uint32;
             description
               "Route ack and error flag";
           }
           leaf rt-ack-history {
             type uint32;
             description
               "Route ack history";
           }
           leaf pfe-err-state {
             type string;
             description
               "Route error state from PFE";
           }
           leaf pfe-err-time {
             type uint32;
             description
               "Route error receive time";
           }
           leaf rt-ver-id {
             type uint32;
             description
               "Route version ID";
           }
           leaf rt-entry-pim-state {
             type string;
             description
               "PIM state of this route entry";
           }
           leaf inactive-reason {
             type string;
             description
               "HFRR profile Inactive reason (if any)";
           }
           leaf local-as {
             type int32;
             description
               "Local AS number";
           }
           leaf med-plus-igp {
             type int32;
           }
           leaf rt-aigp {
             type uint64;
           }
           leaf rt-effective-aigp {
             type uint64;
             description
               "Effective AIGP value used by route selection";
           }
           leaf rt-effective-aigp-reason {
             type string;
             description
               "Reason why the effective AIGP value was selected";
           }
           leaf rt-resolving-aigp {
             type uint64;
           }
           leaf rt-effective-metric {
             type uint64;
             description
               "Effective metric value used by route selection";
           }
           leaf rt-effective-metric-reason {
             type string;
             description
               "Reason why the effective metric value was selected";
           }
           leaf rt-orr {
             type uint32;
           }
           leaf rt-actual-igp-metric {
             type uint32;
           }
           leaf rt-ospf-area {
             type string;
           }
           leaf task-name {
             type string;
             description
               "Name of this task";
           }
           leaf announce-bits {
             type int32;
           }
           leaf announce-tasks {
             type string;
           }
           leaf flow-id {
             type int32;
           }
           leaf bgp-rt-flag {
             type string;
             description
               "BGP route flag";
           }
           leaf label-base {
             type int32;
             description
               "Label base for l2vpn";
           }
           leaf label-range {
             type int32;
             description
               "Label range for l2vpn";
           }
           leaf l2vpn-status-vector {
             type string;
           }
           leaf label-offset {
             type int32;
             description
               "Label offset for l2vpn";
           }
           leaf remote-site {
             type int32;
             description
               "Remote site id";
           }
           leaf l2vpn-mesh-group {
             type string;
           }
           leaf vc-label {
             type int32;
             description
               "VC label";
           }
           leaf context-id {
             type jt:ipaddr;
             description
               "Context Identifier";
           }
           leaf route-control-word {
             type string;
             description
               "Control Word";
           }
           leaf mtu {
             type int32;
             description
               "MTU along an interface";
           }
           leaf cell-bundle-size {
             type int32;
             description
               "Cell bundle size";
           }
           leaf vlan-id {
             type int32;
           }
           leaf flow-label-transmit {
             type int32;
           }
           leaf flow-label-receive {
             type int32;
           }
           leaf tdm-payload-size {
             type int32;
           }
           leaf tdm-bitrate {
             type int32;
           }
           leaf pw-status-code {
             type int32;
           }
           leaf cac-bandwidth-failure {
             type empty;
             description
               "Call admission control failure due to insufficient bandwidth";
           }
           leaf vpn-label {
             type int32;
             description
               "VPN label";
           }
           leaf route-label {
             type int32;
             description
               "Route label";
           }
           leaf route-labels {
             type string;
             description
               "Route label";
           }
           leaf mac-route-esi {
             type string;
             description
               "ESI";
           }
           leaf evpn-igmp-flags {
             type int32;
             description
               "IGMP flags";
           }
           leaf evpn-mld-flags {
             type int32;
             description
               "MLD flags";
           }
           leaf evpn-leave-reserved {
             type int32;
             description
               "IGMP Leave Reserved Field";
           }
           leaf evpn-leave-mrt {
             type int32;
             description
               "IGMP Leave Max Response Time";
           }
           leaf overlay-gateway-address {
             type jt:ipaddr;
             description
               "Overlay gateway address";
           }
           leaf reroute-address {
             type jt:ipaddr;
             description
               "Reroute address";
           }
           leaf bgp-otc {
             type int32;
           }
           leaf peer-id {
             type jt:ipaddr;
           }
           leaf rt-entry-ext-pfx-attr-flags {
             type string;
             description
               "Route entry extended prefix attribute flags";
           }
           leaf rt-entry-ext-pfx-source-rtrid {
             type string;
             description
               "Route entry extended prefix source rtr id";
           }
           leaf path-id {
             type string;
           }
           leaf gateway {
             type string;
             description
               "Sourcing gateway";
           }
           leaf rtrib-primary {
             type string;
             description
               "Primary routing table";
           }
           leaf rib-export-rtrib-primary {
             type string;
             description
               "RIB export primary routing table";
           }
           leaf rtrib-secondary {
             type string;
             description
               "Secondary routing table";
           }
           leaf indirect-nh-count {
             type int32;
             description
               "Number of indirect next hops";
           }
           leaf composite-nh-count {
             type int32;
             description
               "Number of composite next hops";
           }
           leaf helper-nhid {
             type uint32;
             description
               "Helper nexthop index";
           }
           leaf helper-refcount {
             type int32;
             description
               "Reference count of those needing helper route";
           }
           leaf backup-pe-group-name {
             type string;
             description
               "Name of the backup PE group";
           }
           leaf designated-forwarder {
             type string;
             description
               "Indicates if we are the designated forwarder for this route";
           }
           leaf rt-entry-opaque-data {
             type string;
             description
               "Opaque data associated with the route entry";
           }
           leaf rt-stats-id-grp-single-line {
             type string;
             description
               "Stats-id-group associated with the route entry";
           }
           leaf rt-entry-ext-pfx-sid-data {
             type string;
             description
               "Route entry extended prefix sid data";
           }
           leaf hidden-reason {
             type string;
             description
               "Protocol's reason for hiding the route";
           }
           leaf bgp-bmp-send-flag-start {
             type string;
           }
           leaf bgp-bmp-send-flag-pre {
             type string;
           }
           leaf bgp-bmp-send-flag-post {
             type string;
           }
           leaf bgp-bmp-send-flag-ribout-prepolicy {
             type string;
           }
           leaf bgp-bmp-send-flag-ribout-postpolicy {
             type string;
           }
           leaf bgp-bmp-send-flag-station {
             type string;
           }
           leaf bgp-nnh-nodes {
             type string;
             description
               "Next-next-hop nodes";
           }
           leaf bgp-nh-nnh-map {
             type string;
             description
               "Next-hop to next-next-hop map";
           }
           leaf bgp-profile-creation-failure-reason {
             type string;
             description
               "Reason for failing to create profile for next-next-hop map";
           }
           leaf bgp-nh-nnh-entry {
             type string;
             description
               "Next-hop to next-next-hop entry";
           }
           leaf glb-profile {
             type string;
             description
               "GLB Profile";
           }
           leaf glb-profile-id {
             type uint32;
             description
               "GLB Profile ID";
           }
           leaf rt-entry-stats {
             type string;
             description
               "Route entry statistics data";
           }
           container connection-bandwidth {
             description
               "Bandwidth of a layer 2 connection";
             leaf connection-bandwidth.heading {
               type string;
               description
                 "Bandwidth of a layer 2 connection";
             }
             leaf bandwidth {
               type string;
             }
             leaf class-type {
               type int32;
             }
             leaf class-bandwidth {
               type int32;
             }
           }
           container route-flap-damping {
             leaf last-merit {
               type int32;
               description
                 "Last merit value";
             }
             leaf merit {
               type int32;
               description
                 "Current merit value";
             }
             leaf damping-parameters {
               type string;
             }
             leaf default-damping-parameters {
               type empty;
               description
                 "Default damping parameters used";
             }
             leaf last-update {
               type string;
             }
             leaf first-update {
               type string;
             }
             leaf route-flap-count {
               type int32;
               description
                 "Number of times this route has flapped";
             }
             leaf suppressed {
               type empty;
               description
                 "This route is suppressed";
             }
             leaf reuse-time {
               type string;
               description
                 "Time until this route is reusable";
             }
             leaf reuse-preference {
               type int32;
               description
                 "Preference to use when this route is reused";
             }
             leaf expire-time {
               type string;
               description
                 "Time when this damping entry expires";
             }
           }
           container nhh {
             leaf nh-type {
               type string;
               description
                 "Special next hop: Reject, Blackhole, Receive, Multicast, 
                 Local, or Unused";
             }
             leaf nh-index {
               type uint32;
               description
                 "Next-hop index";
             }
             leaf transport-class {
               type string;
               description
                 "Transport class name";
             }
             leaf nh-address {
               type string;
               description
                 "Address of next hop";
             }
             leaf nh-reference-count {
               type int32;
               description
                 "Number of references to this next hop";
             }
             leaf ext-int-intf-index {
               type int32;
               description
                 "Interface index of equal-external-internal multipath";
             }
             leaf nh-session-id {
               type uint32;
               description
                 "Nexthop session id";
             }
             leaf nh-key-opaque {
               type string;
               description
                 "Nexthop key opaque handle";
             }
             leaf nh-non-key-opaque {
               type string;
               description
                 "Nexthop non-key opaque handle";
             }
             leaf nh-key-opaque-dump {
               type string;
               description
                 "Nexthop key opaque app dump";
             }
             leaf nh-non-key-opaque-dump {
               type string;
               description
                 "Nexthop non-key opaque app dump";
             }
             leaf nh-flood-overflow {
               type empty;
               description
                 "Flood nexthop exceeds maximum branches";
             }
             leaf nh-kernel-id {
               type int32;
               description
                 "Table Id for this next hop";
             }
           }
           list nh-expand {
             key "nhe-name nhe-handle";
             description
               "Next-hop gateway information";
             leaf nhe-name {
               type string;
               description
                 "Name of next-hop";
             }
             leaf nhe-handle {
               type string;
               description
                 "Nexthop pointer";
             }
             leaf nhe-index {
               type int32;
               description
                 "Next-hop index";
             }
             leaf nhe-to {
               type string;
               description
                 "Nexthop address";
             }
             leaf nhe-mbr-count {
               type int32;
               description
                 "Number of child nexhops";
             }
             leaf nhe-mpls-label {
               type string;
               description
                 "Label of MPLS packet";
             }
           }
           list rt-session-id {
             key "rt-session-id-value";
             description
               "Session-IDs associated with route";
             leaf rt-session-id-value {
               type int32;
               description
                 "Value of session-id";
             }
             leaf rt-session-id-version {
               type int32;
               description
                 "Version of session-id";
             }
           }
           container flex-rt-statistics {
             description
               "Statistics associated with route";
             leaf flex-rt-statistics-pkts-count {
               type int32;
               description
                 "Packet count";
             }
             leaf flex-rt-statistics-pps {
               type int32;
               description
                 "Pps";
             }
             leaf flex-rt-statistics-bytes-count {
               type int32;
               description
                 "Byte count";
             }
             leaf flex-rt-statistics-bps {
               type int32;
               description
                 "Bps";
             }
           }
           leaf bgp-group-name {
             type string;
           }
           leaf bgp-no-label-reason {
             type string;
           }
           leaf sr-policy-distinguisher {
             type uint32;
           }
           leaf sr-policy-color {
             type uint32;
           }
           leaf sr-policy-endpoint {
             type jt:ipaddr;
           }
           leaf bgp-metric-flags {
             type string;
             description
               "BGP metrics flags";
           }
           leaf bgp-output-queue-class {
             type string;
             description
               "BGP output queue class";
           }
           leaf cluster-id {
             type string;
           }
           leaf originator {
             type string;
           }
           leaf bgp-aigp {
             type string;
             description
               "Accumulated IGP Metric";
           }
           leaf bgp-elc {
             type empty;
             description
               "Entropy label capable";
           }
           leaf bgp-elc-v2 {
             type empty;
             description
               "Entropy label capable version 2";
           }
           leaf bgp-elc-v3 {
             type empty;
             description
               "Entropy label capable version 3";
           }
           leaf bgp-nhc-unknown-characteristics-len {
             type uint32;
             description
               "Total length of NHC unknown characteristics";
           }
           leaf bgp-nhc-nh-valid {
             type string;
             description
               "Whether next hop field matches route next hop";
           }
           leaf bgp-nhc-characteristic-code {
             type uint32;
             description
               "NHC characteristic code";
           }
           leaf bgp-nhc-characteristic-len {
             type uint32;
             description
               "NHC characteristic length";
           }
           leaf bgp-nhc-characteristic-val {
             type string;
             description
               "NHC characteristic value";
           }
         }
         list kern-nhexpand {
           key "kern-nhe-name kern-nhe-handle";
           description
             "Next-hop gateway information";
           container srv6-info {
             leaf srv6-info-srh-sid-mode {
               type string;
               description
                 "Reduced/non-reduced mode for SRH";
             }
             leaf srv6-info-packet-mode {
               type string;
               description
                 "Packet mode for SRV6-Tunnel";
             }
             leaf srv6-info-srh-last-sid {
               type string;
               description
                 "Remove last sid for ACX";
             }
             leaf srv6-info-dyn-tunnel {
               type string;
               description
                 "SRv6 tunnel created dynamically";
             }
             leaf srv6-cos-propagation {
               type string;
               description
                 "SRv6 CoS propagation";
             }
             leaf srv6-ttl-propagation {
               type string;
               description
                 "SRv6 TTL propagation";
             }
             leaf srv6-source {
               type jt:ipaddr;
               description
                 "Source IPv6 address";
             }
             leaf srv6-destination {
               type jt:ipaddr;
               description
                 "Destination IPv6 address";
             }
             list srv6-segment-list {
               key "srv6-segment-list-index";
               description
                 "SRH Segment list";
               leaf srv6-segment-list-index {
                 type uint32;
                 description
                   "SRH segment list index";
               }
               leaf srv6-segment-list-addr {
                 type jt:ipaddr;
                 description
                   "SRH segment address";
               }
             }
           }
           leaf kern-nhe-platform-layer-input {
             type empty;
             description
               "Platform layer input nexthop";
           }
           leaf kern-nhe-platform-layer-output {
             type empty;
             description
               "Platform layer output nexthop";
           }
           leaf kern-nhe-in-kernel {
             type empty;
             description
               "Nexthop install in kernel";
           }
           leaf kern-nhe-fib-channel {
             type string;
             description
               "Fib channel in which route is installed";
           }
           leaf kern-nhe-name {
             type string;
             description
               "Name of next-hop";
           }
           leaf kern-nhe-subtype {
             type string;
             description
               "Nexthop Subtype";
           }
           leaf kern-nhe-handle {
             type string;
             description
               "Nexthop pointer";
           }
           leaf kern-nhe-index {
             type int32;
             description
               "Next-hop index";
           }
           leaf kern-gw-flags {
             type string;
             description
               "Nexthop gateway flags";
           }
           leaf kern-gw-opaque {
             type string;
             description
               "Nexthop gateway opaque data handle";
           }
           leaf kern-key-opaque {
             type string;
             description
               "Nexthop key opaque data handle";
           }
           leaf kern-nhe-to {
             type string;
             description
               "Nexthop address";
           }
           leaf kern-nhe-mbr-count {
             type int32;
             description
               "Number of child nexhops";
           }
           leaf kern-nhe-mpls-label {
             type string;
             description
               "Label of MPLS packet";
           }
           leaf kern-nhe-pnh {
             type string;
             description
               "Protocol Nexthop address";
           }
           leaf kern-nhe-fib-nh-str {
             type string;
             description
               "FIB inh or cnh identifier";
           }
           leaf kern-nhe-sessionid {
             type int32;
             description
               "Session ID";
           }
           leaf kern-nhe-tunnel-type {
             type string;
             description
               "Tunnel type";
           }
           leaf kern-nhe-tunnel-src {
             type string;
             description
               "Tunnel Source address";
           }
           leaf kern-nhe-tunnel-dest {
             type string;
             description
               "Tunnel Destination address";
           }
           leaf kern-nhe-tunnel-ep {
             type string;
             description
               "Tunnel Endpoint address";
           }
           leaf kern-nhe-tunnel-vxlan-encap-vni {
             type int32;
             description
               "VxLAN tunnel encap vni";
           }
           leaf kern-nhe-tunnel-vxlan-decap-vni {
             type int32;
             description
               "VxLAN tunnel decap vni";
           }
           leaf kern-nhe-translate-type {
             type string;
             description
               "Translation type";
           }
           leaf kern-nhe-translate-src {
             type string;
             description
               "Translation Source address";
           }
           leaf kern-nhe-translate-src-plen {
             type int32;
             description
               "Translation Source address prefix length";
           }
           leaf kern-nhe-translate-dest {
             type string;
             description
               "Translation Destination address";
           }
           leaf kern-nhe-translate-dest-plen {
             type int32;
             description
               "Translation Destination address prefix length";
           }
           leaf kern-nhe-tunnel-encap-rtb-id {
             type int32;
             description
               "Tunnel encap routing table id";
           }
           leaf kern-nhe-tunnel-decap-rtb-id {
             type int32;
             description
               "Tunnel decap routing table id";
           }
           leaf kern-nhe-interface {
             type string;
             description
               "Interface";
           }
           leaf kern-nhe-slice-gencfg-id {
             type int32;
             description
               "Slice-Gencfg ID";
           }
           leaf kern-nhe-sliceid {
             type int32;
             description
               "Slice ID";
           }
           leaf kern-nhe-fwf {
             type string;
             description
               "Filter Name";
           }
           leaf kern-nhe-flex-tunnel-info {
             type string;
             description
               "Flex-tunnel information of nexthop";
           }
           leaf kern-nhe-flags {
             type string;
             description
               "Nexthop flags";
           }
           leaf kern-nhe-stats-id-group {
             type string;
             description
               "Statistics ID Group associated with nexthop";
           }
           leaf kern-nhe-reference-count {
             type int32;
             description
               "Nexthop reference count";
           }
           leaf kern-elnh-address {
             type string;
             description
               "Address of Element Next-hop";
           }
         }
         leaf rt-entry-count {
           type int32;
           description
             "Number of route entries in this route";
         }
         leaf rt-announced-count {
           type int32;
           description
             "Number of announced route entries";
         }
         leaf rt-state {
           type string;
           description
             "State of this route";
         }
         leaf-list tsi {
           type string;
           description
             "Task-specific information";
         }
         container communities {
           leaf-list community {
             type string;
             description
               "Basic community";
           }
           leaf-list extended-community {
             type string;
             description
               "Extended community";
           }
           leaf-list ipv6-extended-community {
             type string;
             description
               "IPv6 extended community";
           }
         }
         list bgp-tunnel-attribute {
           key "tunnel-attribute-type";
           description
             "Tunne encap attribute information";
           leaf tunnel-attribute-type {
             type string;
           }
           leaf tunnel-attribute-rpf {
             type empty;
           }
           leaf tunnel-attribute-color {
             type uint32;
           }
           leaf tunnel-attribute-destination {
             type jt:ipaddr;
           }
         }
       }
       container route-state-history {
         list route-state-history-elements {
           key "rt-history-time";
           leaf rt-history-time {
             type string;
           }
           leaf rt-history-event {
             type string;
           }
         }
       }
     }
   }
   grouping rt-pfe-install-errors-block {
     list route-pfe-err {
       key "rt-prefix";
       leaf rt-prefix {
         type string;
       }
       leaf rt-err-category {
         type string;
       }
       leaf rt-handle {
         type string;
       }
       leaf rt-err-type {
         type string;
       }
       leaf rt-timestamp {
         type string;
       }
     }
   }
   grouping route-record-information-block {
     leaf jflow-enabled {
       type string;
     }
     leaf data-rec-field {
       type string;
     }
     leaf rt-rec-add {
       type uint32;
     }
     leaf rt-rec-del {
       type uint32;
     }
     leaf as-rec-add {
       type uint32;
     }
     leaf as-rec-del {
       type uint32;
     }
     leaf com-rec-add {
       type uint32;
     }
     leaf com-rec-del {
       type uint32;
     }
   }
   grouping rtexport-table-information-block {
     container rte-table {
       leaf table-name {
         type string;
         description
           "Unicast routing table";
       }
       leaf table-export-on {
         type string;
       }
       leaf table-usage {
         type int32;
         description
           "Number of exported routes";
       }
       leaf table-flags {
         type string;
       }
       leaf import-list {
         type string;
       }
     }
     container rte-target {
       leaf target-string {
         type string;
         description
           "Route target";
       }
       leaf family {
         type string;
       }
       leaf subaf {
         type string;
       }
       leaf import-count {
         type int32;
       }
       leaf export-count {
         type int32;
       }
       leaf import-list {
         type string;
       }
       leaf export-list {
         type string;
       }
     }
     container rte-instance {
       leaf instance-name {
         type string;
       }
       leaf rte-instance-type {
         type string;
       }
       leaf instance-flags {
         type string;
       }
       leaf instance-options {
         type string;
       }
       leaf import-policy {
         type string;
       }
       leaf export-policy {
         type string;
       }
     }
   }
   grouping rt-ribexport-table-information-block {
     container rtre-table {
       leaf table-name {
         type string;
         description
           "Unicast routing table";
       }
       leaf table-export-on {
         type string;
       }
       leaf table-usage {
         type int32;
         description
           "Number of exported routes";
       }
       leaf table-flags {
         type string;
       }
       leaf import-list {
         type string;
       }
       leaf rib-export-group {
         type string;
       }
     }
   }
   grouping rt-ribexport-instance-information-block {
     container rtre-instance {
       leaf instance-name {
         type string;
       }
       leaf rtre-instance-type {
         type string;
       }
       leaf instance-flags {
         type string;
       }
       leaf instance-refcount {
         type int32;
       }
     }
   }
 }
